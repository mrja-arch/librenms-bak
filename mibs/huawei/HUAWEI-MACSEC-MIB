--=================================================================
-- Copyright (C) 2025 by HUAWEI TECHNOLOGIES. All rights reserved
-- 
-- Description:HUAWEI MACSEC MIB
-- Reference:
-- Version: V4.01
-- History:
-- =================================================================

	HUAWEI-MACSEC-MIB DEFINITIONS ::= BEGIN
 
		IMPORTS
			hwDatacomm			
				FROM HUAWEI-MIB			
			OBJECT-GROUP, MODULE-COMPLIANCE, NOTIFICATION-GROUP			
				FROM SNMPv2-CONF			
			Unsigned32, OBJECT-TYPE, MODULE-IDENTITY, NOTIFICATION-TYPE			
				FROM SNMPv2-SMI
			RowStatus
        		FROM SNMPv2-TC;
	
	
		hwMACsec MODULE-IDENTITY 
			LAST-UPDATED "202509090900Z"		-- 09/09, 2025
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"This MIB describes objects used for MACsec."  
			REVISION  "202509090900Z"
															   DESCRIPTION 
				                                                                 "Add NOTIFICATION-TYPE of hwMacsecDynCakReAuthPacketLoss, hwMacsecDynCakReAuthPacketLossResume."
			REVISION  "202507280900Z"
															   DESCRIPTION 
				                                                                 "Add mib table hwMACsecProfile and modify table of hwMACsecPortCfgTable."
			REVISION  "202507101558Z"
															   DESCRIPTION 
				                                                                 "Add mib node hwMACsecPortRowStatus and modify name of hwMAcsecPortCryptographicAlgorithm to hwMACsecPortCryptographicAlgorithm."
			REVISION  "202506120841Z"
															   DESCRIPTION 
				                                                                 "Add mib node hwMACsecCak, hwMACsecPortMode, hwMACsecPolicy, hwMACsecMKALife, hwMAcsecPortCryptographicAlgorithm and modify MAX-ACCESS of hwMACsecPortNewCKN"
			REVISION  "202506041011Z"
															   DESCRIPTION 
				                                                                 "Remove hwMACsecSlotID from Entry."
			REVISION  "202505141011Z"
															   DESCRIPTION 
				                                                                 "Add NOTIFICATION-TYPE of hwMacsecRebootRequired, hwMacsecRebootRequiredResume."
			REVISION  "202207211521Z"
															   DESCRIPTION 
				                                                                 "Delete useless comments."
			REVISION  "202202231521Z"
															   DESCRIPTION 
				                                                                 "Modify MAX-ACCESS of  hwMacsecRcvRspTimeoutIfIndex,hwMacsecRcvRspTimeoutRole,hwMacsecRcvRspTimeoutLocalPort."
			REVISION  "202011232003Z"
															   DESCRIPTION 
				                                                                 "Add NOTIFICATION-TYPE of hwMACsecIfName, hwMACsecFailReason,hwMACsecFailNotify."

			REVISION  "201804231622Z"
															   DESCRIPTION 
				                                                                 "Add NOTIFICATION-TYPE of hwMACsecPortCipherPeer, hwMACsecPortCipher,hwCipherSwitchFailAlarm,hwMACsecCipherSwitchReason, hwMACsecCipherSwitchFailReason."

			REVISION  "201711031622Z"
															   DESCRIPTION 
				                                                                 "Add NOTIFICATION-TYPE of hwMacsecRcvRspTimeout, hwMacsecRcvRspTimeoutResume."
				
			REVISION  "201603101013Z"
															   DESCRIPTION 
				                                                                 "Modify MAX-ACCESS of  hwMACsecPortRole ,hwMACsecPortName,hwMACsecPortOldCKN,hwMACsecPortNewCKN."    

			REVISION  "201603101013Z"
																DESCRIPTION 
				                                                                 "This MIB describes objects used for MACsec." 


	
			::= { hwDatacomm 347 }
		   		    
	
--
-- Node definitions
--
	
		-- 1.3.6.1.4.1.2011.5.25.347.1
		hwMACsecMibObjects OBJECT IDENTIFIER ::= { hwMACsec 1 }
		
		-- 1.3.6.1.4.1.2011.5.25.347.1.1
		hwMACsecPortCfgTable OBJECT-TYPE
			SYNTAX SEQUENCE OF HwMACsecPortCfgEntry
			MAX-ACCESS not-accessible
			STATUS current
			DESCRIPTION
				"The port's MACsec configuration table."
			::= { hwMACsecMibObjects 1 }
		
		-- 1.3.6.1.4.1.2011.5.25.347.1.1.1
		hwMACsecPortCfgEntry OBJECT-TYPE
			SYNTAX HwMACsecPortCfgEntry
			MAX-ACCESS not-accessible
			STATUS current
			DESCRIPTION
				"An entry in the MACsec configuration table."
			INDEX { hwMACsecIfIndex }
			::= { hwMACsecPortCfgTable 1 }
		
		HwMACsecPortCfgEntry ::=
			SEQUENCE { 
				hwMACsecIfIndex
					Unsigned32,
				hwMACsecPortRole
					INTEGER,
				hwMACsecPortName
					OCTET STRING,
				hwMACsecPortOldCKN
					OCTET STRING,
				hwMACsecPortNewCKN
					OCTET STRING,
				hwMACsecPortCipherPeer
					OCTET STRING,
				hwMACsecPortCipher
					OCTET STRING,
				hwMACsecIfName
					OCTET STRING,
				hwMACsecFailReason
					OCTET STRING,
				hwMACsecCak
					OCTET STRING,
				hwMACsecPortProfileName
					OCTET STRING,
				hwMACsecPortRowStatus
					RowStatus
			 }

		-- 1.3.6.1.4.1.2011.5.25.347.1.1.1.1
		hwMACsecIfIndex OBJECT-TYPE
			SYNTAX Unsigned32
			MAX-ACCESS  not-accessible
			STATUS current
			DESCRIPTION
				"The interface index."
			::= { hwMACsecPortCfgEntry 1 }
		
		-- 1.3.6.1.4.1.2011.5.25.347.1.1.1.2
		hwMACsecPortRole OBJECT-TYPE
			SYNTAX INTEGER
				{
				nonkeyserver(1),
				keyserver(2)
				}
			MAX-ACCESS accessible-for-notify 
			STATUS current
			DESCRIPTION
				"Indicates the MKA role of the port.
				Options: 
				1. nonkeyserver(1) -indicates the MKA role of the port is supplicant.
				2. keyserver(2)    -indicates the MKA role of the port is key server. "
			DEFVAL { nonkeyserver }
			::= { hwMACsecPortCfgEntry 2 }
		
		-- 1.3.6.1.4.1.2011.5.25.347.1.1.1.3
		hwMACsecPortName OBJECT-TYPE
			SYNTAX OCTET STRING
			MAX-ACCESS accessible-for-notify 
			STATUS current
			DESCRIPTION
				"The port name."
			::= { hwMACsecPortCfgEntry 3 }
		
		-- 1.3.6.1.4.1.2011.5.25.347.1.1.1.4
		hwMACsecPortOldCKN OBJECT-TYPE
			SYNTAX OCTET STRING
			MAX-ACCESS accessible-for-notify 
			STATUS current
			DESCRIPTION
				"The using CKN of this port."
			::= { hwMACsecPortCfgEntry 4 }
		
		-- 1.3.6.1.4.1.2011.5.25.347.1.1.1.5
		hwMACsecPortNewCKN OBJECT-TYPE
			SYNTAX OCTET STRING
			MAX-ACCESS read-create 
			STATUS current
			DESCRIPTION
				"The configed CKN of this port."
			::= { hwMACsecPortCfgEntry 5 }
        
        -- 1.3.6.1.4.1.2011.5.25.347.1.1.1.6
		hwMACsecPortCipherPeer OBJECT-TYPE
			SYNTAX OCTET STRING
			MAX-ACCESS accessible-for-notify 
			STATUS current
			DESCRIPTION
				"The configed Cipher Suite of peer."
			::= { hwMACsecPortCfgEntry 6 }

        -- 1.3.6.1.4.1.2011.5.25.347.1.1.1.7
		hwMACsecPortCipher OBJECT-TYPE
			SYNTAX OCTET STRING
			MAX-ACCESS accessible-for-notify 
			STATUS current
			DESCRIPTION
				"The configed Cipher Suite of this port."
			::= { hwMACsecPortCfgEntry 7 }

		-- 1.3.6.1.4.1.2011.5.25.347.1.1.1.8
		hwMACsecIfName OBJECT-TYPE
			SYNTAX OCTET STRING
			MAX-ACCESS accessible-for-notify 
			STATUS current
			DESCRIPTION
				"The interface name."
			::= { hwMACsecPortCfgEntry 8 }

		-- 1.3.6.1.4.1.2011.5.25.347.1.1.1.9
		hwMACsecFailReason OBJECT-TYPE
			SYNTAX OCTET STRING
			MAX-ACCESS accessible-for-notify 
			STATUS current
			DESCRIPTION
				"The reason that MACsec failed to run on an interface."
			::= { hwMACsecPortCfgEntry 9 }

		-- 1.3.6.1.4.1.2011.5.25.347.1.1.1.10
		hwMACsecCak OBJECT-TYPE
			SYNTAX OCTET STRING (SIZE (32..188))
			MAX-ACCESS read-create
			STATUS current
			DESCRIPTION
				"The value of CAK."
			::= { hwMACsecPortCfgEntry 10 }

		-- 1.3.6.1.4.1.2011.5.25.347.1.1.1.11
		hwMACsecPortProfileName OBJECT-TYPE
			SYNTAX OCTET STRING
			MAX-ACCESS read-create
			STATUS current
			DESCRIPTION
				"The port profile name."
			::= { hwMACsecPortCfgEntry 11 }

		-- 1.3.6.1.4.1.2011.5.25.347.1.1.1.12
		hwMACsecPortRowStatus OBJECT-TYPE
			SYNTAX RowStatus
			MAX-ACCESS read-create
			STATUS current
			DESCRIPTION
				"The value of this object identifies the row status."
			::= { hwMACsecPortCfgEntry 12 }


		-- 1.3.6.1.4.1.2011.5.25.347.1.2
		hwMacsecRcvRspTimeoutTable OBJECT-TYPE
			SYNTAX SEQUENCE OF HwMacsecRcvRspTimeoutEntry
			MAX-ACCESS not-accessible
			STATUS current
			DESCRIPTION
				"No heartbeat response alarm list."
			::= { hwMACsecMibObjects 2 }
		
		-- 1.3.6.1.4.1.2011.5.25.347.1.2.1
		hwMacsecRcvRspTimeoutEntry OBJECT-TYPE
			SYNTAX HwMacsecRcvRspTimeoutEntry
			MAX-ACCESS not-accessible
			STATUS current
			DESCRIPTION
				"An entry in the no heartbeat response alarm list."
			INDEX { hwMacsecRcvRspTimeoutIfIndex, hwMacsecRcvRspTimeoutRole, hwMacsecRcvRspTimeoutLocalPort }
			::= { hwMacsecRcvRspTimeoutTable 1 }
		
		HwMacsecRcvRspTimeoutEntry ::=
			SEQUENCE {
				hwMacsecRcvRspTimeoutIfIndex
					Unsigned32,
				hwMacsecRcvRspTimeoutRole
					Unsigned32,
				hwMacsecRcvRspTimeoutLocalPort
					OCTET STRING
			 }

		-- 1.3.6.1.4.1.2011.5.25.347.1.2.1.1
		hwMacsecRcvRspTimeoutIfIndex OBJECT-TYPE
			SYNTAX Unsigned32
			MAX-ACCESS  accessible-for-notify
			STATUS current
			DESCRIPTION
				"Interface index."
			::= { hwMacsecRcvRspTimeoutEntry 1 }
			
		-- 1.3.6.1.4.1.2011.5.25.347.1.2.1.2
		hwMacsecRcvRspTimeoutRole OBJECT-TYPE
			SYNTAX Unsigned32
			MAX-ACCESS  accessible-for-notify
			STATUS current
			DESCRIPTION
				"Device role."
			::= { hwMacsecRcvRspTimeoutEntry 2 }
		
		-- 1.3.6.1.4.1.2011.5.25.347.1.2.1.3
		hwMacsecRcvRspTimeoutLocalPort OBJECT-TYPE
			SYNTAX OCTET STRING
			MAX-ACCESS  accessible-for-notify
			STATUS current
			DESCRIPTION
				"Local port."
			::= { hwMacsecRcvRspTimeoutEntry 3 }

		-- 1.3.6.1.4.1.2011.5.25.347.1.3
		hwMACsecProfileTable OBJECT-TYPE
			SYNTAX SEQUENCE OF HwMACsecProfileEntry
			MAX-ACCESS not-accessible
			STATUS current
			DESCRIPTION
				"MACsec profile table."
			::= { hwMACsecMibObjects 3 }

		-- 1.3.6.1.4.1.2011.5.25.347.1.3.1
		hwMACsecProfileEntry OBJECT-TYPE
			SYNTAX HwMACsecProfileEntry
			MAX-ACCESS not-accessible
			STATUS current
			DESCRIPTION
				"An entry in the MACsec profile table."
			INDEX { hwMACsecProfileId }
			::= { hwMACsecProfileTable 1 }
		
		HwMACsecProfileEntry ::=
			SEQUENCE { 
				hwMACsecProfileId
					Unsigned32,
				hwMACsecProfileName
					OCTET STRING,
				hwMACsecMode
					INTEGER,
				hwMACsecPolicy
					INTEGER,
				hwMACsecMKALife
					Unsigned32,
				hwMACsecCryptographicAlgorithm
					INTEGER,
				hwMACsecProfileRowStatus
					RowStatus
			 }

		-- 1.3.6.1.4.1.2011.5.25.347.1.3.1.1
		hwMACsecProfileId OBJECT-TYPE
			SYNTAX Unsigned32
			MAX-ACCESS  not-accessible
			STATUS current
			DESCRIPTION
				"The index of MACsec profile."
			::= { hwMACsecProfileEntry 1 }

		-- 1.3.6.1.4.1.2011.5.25.347.1.3.1.2
		hwMACsecProfileName OBJECT-TYPE
			SYNTAX OCTET STRING
			MAX-ACCESS read-only
			STATUS current
			DESCRIPTION
				"The profile name."
			::= { hwMACsecProfileEntry 2 }
		
		-- 1.3.6.1.4.1.2011.5.25.347.1.3.1.3
		hwMACsecMode OBJECT-TYPE
			SYNTAX INTEGER
			{
				none(0),
				normal(1),
				integrityOnly(2)
			}
			MAX-ACCESS read-create
			STATUS current
			DESCRIPTION
				"The MACsec mode."
			DEFVAL { normal }
			::= { hwMACsecProfileEntry 3 }

		-- 1.3.6.1.4.1.2011.5.25.347.1.3.1.4
		hwMACsecPolicy OBJECT-TYPE
			SYNTAX INTEGER
			{
				mustSecure(0),
				shouldSecure(1)
			}
			MAX-ACCESS read-create
			STATUS current
			DESCRIPTION
				"The MACsec policy."
			DEFVAL { mustSecure }
			::= { hwMACsecProfileEntry 4 }

		-- 1.3.6.1.4.1.2011.5.25.347.1.3.1.5
		hwMACsecMKALife OBJECT-TYPE
			SYNTAX Unsigned32 (6..60)
			MAX-ACCESS read-create
			STATUS current
			DESCRIPTION
				"The MKA session timeout interval."
			DEFVAL { 6 }
			::= { hwMACsecProfileEntry 5 }

		-- 1.3.6.1.4.1.2011.5.25.347.1.3.1.6
		hwMACsecCryptographicAlgorithm OBJECT-TYPE
			SYNTAX INTEGER
			{
				aesCmac128(0),
				aesCmac256(1)
			}
			MAX-ACCESS read-create
			STATUS current
			DESCRIPTION
				"The MKA key generation algorithm."
			DEFVAL { aesCmac128 }
			::= { hwMACsecProfileEntry 6 }
		
		-- 1.3.6.1.4.1.2011.5.25.347.1.3.1.7
		hwMACsecProfileRowStatus OBJECT-TYPE
			SYNTAX RowStatus
			MAX-ACCESS read-create
			STATUS current
			DESCRIPTION
				"The value of this object identifies the row status."
			::= { hwMACsecProfileEntry 7 }
		

		-- 1.3.6.1.4.1.2011.5.25.347.2
		hwMACsecTraps OBJECT IDENTIFIER ::= { hwMACsec 2 }
		
		-- 1.3.6.1.4.1.2011.5.25.347.2.1
		hwMACsecTrapOID OBJECT IDENTIFIER ::= { hwMACsecTraps 1 }
		
		-- 1.3.6.1.4.1.2011.5.25.347.2.1.1
		hwMACsecCKNSwitchReason OBJECT-TYPE
			SYNTAX OCTET STRING
			MAX-ACCESS accessible-for-notify
			STATUS current
			DESCRIPTION
				"The reason of CKN switching."
			::= { hwMACsecTrapOID 1 }
		
		-- 1.3.6.1.4.1.2011.5.25.347.2.1.2
		hwMACsecCKNSwitchFailReason OBJECT-TYPE
			SYNTAX OCTET STRING
			MAX-ACCESS accessible-for-notify
			STATUS current
			DESCRIPTION
				"The reason of CKN switching failed."
			::= { hwMACsecTrapOID 2 }
        
        -- 1.3.6.1.4.1.2011.5.25.347.2.1.3
		hwMACsecCipherSwitchReason OBJECT-TYPE
			SYNTAX OCTET STRING
			MAX-ACCESS accessible-for-notify
			STATUS current
			DESCRIPTION
				"The reason of Cipher Suite switching."
			::= { hwMACsecTrapOID 3 }
		
		-- 1.3.6.1.4.1.2011.5.25.347.2.1.4
		hwMACsecCipherSwitchFailReason OBJECT-TYPE
			SYNTAX OCTET STRING
			MAX-ACCESS accessible-for-notify
			STATUS current
			DESCRIPTION
				"The reason of Cipher Suite switching failed."
			::= { hwMACsecTrapOID 4 }

		-- 1.3.6.1.4.1.2011.5.25.347.2.1.5
		hwMACsecSlotID OBJECT-TYPE
			SYNTAX Unsigned32
			MAX-ACCESS accessible-for-notify
			STATUS current
			DESCRIPTION
				"Slot ID of the device."
			::= { hwMACsecTrapOID 5 }

		-- 1.3.6.1.4.1.2011.5.25.347.2.2
		hwCKNSwitchFailAlarm NOTIFICATION-TYPE
			OBJECTS { hwMACsecPortRole, hwMACsecPortName, hwMACsecPortOldCKN, hwMACsecPortNewCKN, hwMACsecCKNSwitchReason, hwMACsecCKNSwitchFailReason }
			STATUS current
			DESCRIPTION 
				"Failed to switch the CKN."
			::= { hwMACsecTraps 2 }

			
		-- 1.3.6.1.4.1.2011.5.25.347.2.3
		hwMacsecRcvRspTimeout NOTIFICATION-TYPE
			OBJECTS {hwMacsecRcvRspTimeoutIfIndex, hwMacsecRcvRspTimeoutRole, hwMacsecRcvRspTimeoutLocalPort}
			STATUS current
			DESCRIPTION 
				"No heartbeat response alarm list."
			::= { hwMACsecTraps 3 }
			
		-- 1.3.6.1.4.1.2011.5.25.347.2.4
		hwMacsecRcvRspTimeoutResume NOTIFICATION-TYPE
			OBJECTS {hwMacsecRcvRspTimeoutIfIndex, hwMacsecRcvRspTimeoutRole, hwMacsecRcvRspTimeoutLocalPort}
			STATUS current
			DESCRIPTION 
				"No heartbeat response alarm resume list."
			::= { hwMACsecTraps 4 }
			
		-- 1.3.6.1.4.1.2011.5.25.347.2.5
		hwCipherSwitchFailAlarm NOTIFICATION-TYPE
			OBJECTS { hwMACsecPortRole, hwMACsecPortName, hwMACsecPortCipherPeer, hwMACsecPortCipher, hwMACsecCipherSwitchReason, hwMACsecCipherSwitchFailReason }
			STATUS current
			DESCRIPTION 
				"Failed to switch the cipher suite."
			::= { hwMACsecTraps 5 }
			
		-- 1.3.6.1.4.1.2011.5.25.347.2.6
		hwMACsecFailNotify NOTIFICATION-TYPE
			OBJECTS { hwMACsecIfName, hwMACsecFailReason }
			STATUS current
			DESCRIPTION 
				"Failed to run on an interface."
			::= { hwMACsecTraps 6 }

		-- 1.3.6.1.4.1.2011.5.25.347.2.7
		hwMacsecRebootRequired NOTIFICATION-TYPE
			OBJECTS { hwMACsecSlotID }
			STATUS current
			DESCRIPTION 
				"MACsec requires to reboot alarm."
			::= { hwMACsecTraps 7 }

		-- 1.3.6.1.4.1.2011.5.25.347.2.8
		hwMacsecRebootRequiredResume NOTIFICATION-TYPE
			OBJECTS { hwMACsecSlotID }
			STATUS current
			DESCRIPTION 
				"MACsec requires to reboot alarm resume."
			::= { hwMACsecTraps 8 }

		-- 1.3.6.1.4.1.2011.5.25.347.2.9
		hwMacsecDynCakReAuthPacketLoss NOTIFICATION-TYPE
			OBJECTS { hwMACsecPortRole, hwMACsecPortName}
			STATUS current
			DESCRIPTION 
				"Packet loss alarm occurred due to dot1x reauthentication if the dynamic CAK mode is configured for MACsec."
			::= { hwMACsecTraps 9 }

		-- 1.3.6.1.4.1.2011.5.25.347.2.10
		hwMacsecDynCakReAuthPacketLossResume NOTIFICATION-TYPE
			OBJECTS { hwMACsecPortRole, hwMACsecPortName }
			STATUS current
			DESCRIPTION 
				"Cleared the packet loss alarm occurred due to dot1x reauthentication if the dynamic CAK mode is configured for MACsec."
			::= { hwMACsecTraps 10 }

		-- 1.3.6.1.4.1.2011.5.25.347.3
		hwMACsecConformance OBJECT IDENTIFIER ::= { hwMACsec 3 }
		
		-- 1.3.6.1.4.1.2011.5.25.347.3.1
		hwMACsecMibGroups MODULE-COMPLIANCE
			STATUS current
			DESCRIPTION 
				"The compliance statement for systems supporting this module."
			MODULE -- this module
				MANDATORY-GROUPS { hwMACsecBindGroup, hwMACsecTrapGroup }
			::= { hwMACsecConformance 1 }
		
		-- 1.3.6.1.4.1.2011.5.25.347.3.1.1
		hwMACsecBindGroup OBJECT-GROUP
			OBJECTS { hwMACsecPortRole, hwMACsecCKNSwitchReason, hwMACsecPortName, hwMACsecPortNewCKN, hwMACsecPortOldCKN, hwMACsecPortRowStatus, hwMACsecPortProfileName,
				hwMACsecCKNSwitchFailReason, hwMACsecPortCipherPeer, hwMACsecPortCipher, hwMACsecCipherSwitchReason, hwMACsecCipherSwitchFailReason, hwMACsecSlotID,
				hwMACsecCak, hwMACsecCryptographicAlgorithm, hwMACsecFailReason, hwMACsecIfName, hwMACsecMKALife, hwMACsecPolicy, hwMACsecMode, hwMACsecProfileName, 
				hwMACsecProfileRowStatus, hwMacsecRcvRspTimeoutIfIndex, hwMacsecRcvRspTimeoutLocalPort, hwMacsecRcvRspTimeoutRole}
			STATUS current
			DESCRIPTION 
				"The MACsec module's Bind group."
			::= { hwMACsecMibGroups 1 }
		
		-- 1.3.6.1.4.1.2011.5.25.347.3.1.2
		hwMACsecTrapGroup NOTIFICATION-GROUP
			NOTIFICATIONS { hwCKNSwitchFailAlarm,hwMacsecRcvRspTimeout,hwMacsecRcvRspTimeoutResume,hwCipherSwitchFailAlarm,hwMACsecFailNotify,hwMacsecRebootRequired,hwMacsecRebootRequiredResume,hwMacsecDynCakReAuthPacketLoss,hwMacsecDynCakReAuthPacketLossResume }
			STATUS current
			DESCRIPTION 
				"The MACsec module's Notification group."
			::= { hwMACsecMibGroups 2 }
	END

--
-- HUAWEI-MACSEC-MIB.my
--
