-- ============================================================================
-- Copyright (C) 2025 by HUAWEI TECHNOLOGIES. All rights reserved.
-- Description: 
-- Reference: None
-- Version: V1.01
-- ============================================================================
--
-- HUAWEI-ENTITY-COMPONENT-MIB.mib
-- MIB generated by Visual MIB Builder Version 4.0 Build 341
-- Friday, September 27, 2024 at 16:41:48

    HUAWEI-ENTITY-COMPONENT-MIB DEFINITIONS ::= BEGIN

        IMPORTS
            hwDatacomm
                FROM HUAWEI-MIB
            Integer32, Unsigned32, Counter64, OBJECT-TYPE, MODULE-IDENTITY, NOTIFICATION-TYPE
                FROM SNMPv2-SMI;


        -- 1.3.6.1.4.1.2011.5.25.31
        hwEntityComponentMIB MODULE-IDENTITY 
            LAST-UPDATED "202501240000Z"
            ORGANIZATION 
                "Huawei Technologies Co.,Ltd."
            CONTACT-INFO 
                "Huawei Industrial Base
                 Bantian, Longgang
                 Shenzhen 518129
                 People's Republic of China
                 Website: http://www.huawei.com
                 Email: support@huawei.com"
        DESCRIPTION
                "The private mib file includes component information of the device."

        REVISION  "202501240000Z"
        DESCRIPTION  "V1.01, modify HWComponentType"
        REVISION  "202409270000Z"
        DESCRIPTION  "V1.00, Create the file"

        -- 1.3.6.1.4.1.2011.5.25.383
        ::= { hwDatacomm 383 }

--
-- Textual conventions
--

        HWComponentType ::= TEXTUAL-CONVENTION
            STATUS current
            DESCRIPTION
                "Component type from 1-8."
            REFERENCE
                "N/A"
            SYNTAX INTEGER
                {
                    cpu(1),
                    forward(2),
                    switch(3),
                    clock(4),
                    memory(5),
                    flash(6),
                    phychip(7),
                    powerC(8),
                    invalid(65535)
                }

--
-- Node definitions
--
        -- 1.3.6.1.4.1.2011.5.25.383.1
        hwEntityCompObjects OBJECT IDENTIFIER ::= { hwEntityComponentMIB 1 }

        -- 1.3.6.1.4.1.2011.5.25.383.1.1
        hwEntityComponent OBJECT IDENTIFIER ::= { hwEntityCompObjects 1 }

        -- 1.3.6.1.4.1.2011.5.25.383.1.1.1
        hwCompLicense OBJECT-TYPE
            SYNTAX OCTET STRING
            MAX-ACCESS read-write
            STATUS current
            DESCRIPTION
                "The access license that the user enters via the set operation."
            ::= { hwEntityComponent 1 }

        -- 1.3.6.1.4.1.2011.5.25.383.1.1.2
        hwEntityComponentTable OBJECT-TYPE
            SYNTAX SEQUENCE OF HwEntityComponentEntry
            MAX-ACCESS not-accessible
            STATUS current
            DESCRIPTION
                "This table contains one row per physical entity."
            ::= { hwEntityComponent 2 }

        hwEntityComponentEntry OBJECT-TYPE
            SYNTAX HwEntityComponentEntry
            MAX-ACCESS not-accessible
            STATUS current
            DESCRIPTION
                "Information about a particular physical entity.
                Each entry provides objects (hwCompChassisID,
                hwCompSlotID, hwCompCardID, hwCompTypeID,
                hwCompIndex) to index data, and objects
                (hwCompKeyPos, hwCompBoardName, hwCompTypeName,
                hwCompTypeCount) to record component data."
            INDEX { hwCompChassisID, hwCompSlotID, hwCompCardID, hwCompTypeID, hwCompIndex }
            ::= { hwEntityComponentTable 1 }

        HwEntityComponentEntry ::=
            SEQUENCE { 
                hwCompChassisID
                    Unsigned32,
                hwCompSlotID
                    Unsigned32,
                hwCompCardID
                    Unsigned32,
                hwCompTypeID
                    HWComponentType,
                hwCompIndex
                    Unsigned32,
                hwCompKeyPos
                    Unsigned32,
                hwCompBoardName
                    OCTET STRING,
                hwCompTypeName
                    OCTET STRING,
                hwCompTypeCount
                    OCTET STRING
            }
        hwCompChassisID OBJECT-TYPE
            SYNTAX Unsigned32
            MAX-ACCESS not-accessible
            STATUS current
            DESCRIPTION
                "Chassis ID of the board or card."
            ::= { hwEntityComponentEntry 1 }

        hwCompSlotID OBJECT-TYPE
            SYNTAX Unsigned32
            MAX-ACCESS not-accessible
            STATUS current
            DESCRIPTION
                "Slot ID of the board or card."
            ::= { hwEntityComponentEntry 2 }

        hwCompCardID OBJECT-TYPE
            SYNTAX Unsigned32
            MAX-ACCESS not-accessible
            STATUS current
            DESCRIPTION
                "Card ID on the board."
            ::= { hwEntityComponentEntry 3 }

        hwCompTypeID OBJECT-TYPE
            SYNTAX HWComponentType
            MAX-ACCESS not-accessible
            STATUS current
            DESCRIPTION
                "Component type of the board or card."
            ::= { hwEntityComponentEntry 4 }

        hwCompIndex OBJECT-TYPE
            SYNTAX Unsigned32
            MAX-ACCESS not-accessible
            STATUS current
            DESCRIPTION
                "Component index of the board or card, range from 1-8."
            ::= { hwEntityComponentEntry 5 }

        hwCompKeyPos OBJECT-TYPE
            SYNTAX Unsigned32
            MAX-ACCESS read-only
            STATUS current
            DESCRIPTION
                "Key position of the secret key list, range from 1-100."
            ::= { hwEntityComponentEntry 6 }

        hwCompBoardName OBJECT-TYPE
            SYNTAX OCTET STRING
            MAX-ACCESS read-only
            STATUS current
            DESCRIPTION
                "Board name or card name."
            ::= { hwEntityComponentEntry 7 }

        hwCompTypeName OBJECT-TYPE
            SYNTAX OCTET STRING
            MAX-ACCESS read-only
            STATUS current
            DESCRIPTION
                "Component type name of the board or card."
            ::= { hwEntityComponentEntry 8 }

        hwCompTypeCount OBJECT-TYPE
            SYNTAX OCTET STRING
            MAX-ACCESS read-only
            STATUS current
            DESCRIPTION
                "Number of component on the board or card."
            ::= { hwEntityComponentEntry 9 }

        hwEntityComponentMIBConformance OBJECT IDENTIFIER ::= { hwEntityComponentMIB 2 }

        hwEntityComponentMIBCompliances OBJECT IDENTIFIER ::= { hwEntityComponentMIBConformance 1 }

        hwEntityComponentMIBCompliance MODULE-COMPLIANCE
            STATUS current
            DESCRIPTION 
                "Compliance statement for agents that provide full support for 
                hwEntityComponentMIB."
            MODULE -- this module
                MANDATORY-GROUPS { hwEntityComponentMIBInfoGroup }
            ::= { hwEntityComponentMIBCompliances 1 }

        hwEntityComponentMIBGroups OBJECT IDENTIFIER ::= { hwEntityComponentMIBConformance 2 }

        hwEntityComponentMIBInfoGroup OBJECT-GROUP
            OBJECTS { hwCompLicense,
                      hwCompKeyPos,
                      hwCompBoardName,
                      hwCompTypeName,
                      hwCompTypeCount
                    }
            STATUS current
            DESCRIPTION 
                "Group for base device information."
            ::= { hwEntityComponentMIBGroups 1 }

    END
