-- OPTIX-RTN-ODU-MGR-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-RTN-ODU-MGR-MIB DEFINITIONS ::= BEGIN
    IMPORTS
        OBJECT-GROUP,MODULE-COMPLIANCE
            FROM SNMPv2-CONF
        Unsigned32,Integer32,OBJECT-TYPE,MODULE-IDENTITY,NOTIFICATION-TYPE
            FROM SNMPv2-SMI
        TEXTUAL-CONVENTION
            FROM SNMPv2-TC
        optixProvisionRtn
            FROM OPTIX-OID-MIB
        ;

    optixRtnOduMgr MODULE-IDENTITY
        LAST-UPDATED "201204160935Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This module is used to configure and query RF unit parameters for a radio link, including the RF unit frequency, power, and working status."
        REVISION "201204160935Z"
        DESCRIPTION
            "The initial revision of this MIB module1."
        ::={ optixProvisionRtn 4 }

    OPTIXRtnCombineMode ::= TEXTUAL-CONVENTION
        STATUS current
        DESCRIPTION
            "Indicates the combine mode of a RFU-SD board."
        SYNTAX INTEGER
        {
            main(0),
            slave(1),
            combine(2)
        }

    OPTIXRtnFiberEqualState ::= TEXTUAL-CONVENTION
        STATUS current
        DESCRIPTION
            "Indicates RFU-SD fiber equal state."
        SYNTAX INTEGER
        {
            start(1)
        }

    OPTIXRtnOduWorkStateType ::= TEXTUAL-CONVENTION
        STATUS current
        DESCRIPTION
            "Indicates the working status of RF unit. Values: 0: muted 1: unmuted"
        SYNTAX INTEGER
        {
            mute(0),
            unmute(1)
        }

    -- 1.3.6.1.4.1.2011.2.25.4.40.4.10
    optixODU OBJECT IDENTIFIER ::= { optixRtnOduMgr 10 }

    -- 1.3.6.1.4.1.2011.2.25.4.40.4.10.10
    optixRtnOduIndexTable OBJECT-TYPE
        SYNTAX SEQUENCE OF OptixRtnOduIndexEntry
        MAX-ACCESS not-accessible
        STATUS current
        DESCRIPTION
            "Serves as the public index table for attribute tables related to an RF unit."
        ::= { optixODU 10 }

    -- 1.3.6.1.4.1.2011.2.25.4.40.4.10.10.1
    optixRtnOduIndexEntry OBJECT-TYPE
        SYNTAX OptixRtnOduIndexEntry
        MAX-ACCESS not-accessible
        STATUS current
        DESCRIPTION
            "Indicates the index entry for an RF unit."
        INDEX{ optixRtnOduIndex1,optixRtnOduIndex2 }
        ::= { optixRtnOduIndexTable 1 }

    OptixRtnOduIndexEntry ::=
        SEQUENCE {
            optixRtnOduIndex1
                Unsigned32,
            optixRtnOduIndex2
                Unsigned32,
            optixRtnOduIndex3
                Unsigned32
        }

    -- 1.3.6.1.4.1.2011.2.25.4.40.4.10.10.1.1
    optixRtnOduIndex1 OBJECT-TYPE
        SYNTAX Unsigned32
        MAX-ACCESS not-accessible
        STATUS current
        DESCRIPTION
            "Indicates the RF unit board ID."
        ::= { optixRtnOduIndexEntry 1 }

    -- 1.3.6.1.4.1.2011.2.25.4.40.4.10.10.1.2
    optixRtnOduIndex2 OBJECT-TYPE
        SYNTAX Unsigned32
        MAX-ACCESS read-only
        STATUS current
        DESCRIPTION
            "Indicates the subboard ID."
        ::= { optixRtnOduIndexEntry 2 }

    -- 1.3.6.1.4.1.2011.2.25.4.40.4.10.10.1.3
    optixRtnOduIndex3 OBJECT-TYPE
        SYNTAX Unsigned32
        MAX-ACCESS read-only
        STATUS current
        DESCRIPTION
            "Indicates the Port ID."
        ::= { optixRtnOduIndexEntry 3 }
		
    -- 1.3.6.1.4.1.2011.2.25.4.40.4.10.11
    optixRtnOduGeneralAttrTable OBJECT-TYPE
        SYNTAX SEQUENCE OF OptixRtnOduGeneralAttrEntry
        MAX-ACCESS not-accessible
        STATUS current
        DESCRIPTION
            "Indicates the table of general attributes of an ODU."
        ::= { optixODU 11 }

    -- 1.3.6.1.4.1.2011.2.25.4.40.4.10.11.1
    optixRtnOduGeneralAttrEntry OBJECT-TYPE
        SYNTAX OptixRtnOduGeneralAttrEntry
        MAX-ACCESS not-accessible
        STATUS current
        DESCRIPTION
            "Indicates an entry of general attributes of an ODU."
        INDEX{ optixRtnOduIndex1,optixRtnOduIndex2,optixRtnOduIndex3 }
        ::= { optixRtnOduGeneralAttrTable 1 }

    OptixRtnOduGeneralAttrEntry ::=
        SEQUENCE {
            optixRtnOduFademarginAlmTh
                Unsigned32,
            optixRtnOduCurrentFilter
                Unsigned32,
            optixRtnOduAllFilterListInfo
                OCTET STRING,
            optixRtnOduLoopMode
                INTEGER
        }

    -- 1.3.6.1.4.1.2011.2.25.4.40.4.10.11.1.1
    optixRtnOduFademarginAlmTh OBJECT-TYPE
        SYNTAX Unsigned32
        MAX-ACCESS read-write
        STATUS current
        DESCRIPTION
            "Indicates the alarming threshold in the unit of 0.1 dB."
        ::= { optixRtnOduGeneralAttrEntry 1 }

    -- 1.3.6.1.4.1.2011.2.25.4.40.4.10.11.1.2
    optixRtnOduCurrentFilter OBJECT-TYPE
        SYNTAX Unsigned32
        MAX-ACCESS read-write
        STATUS current
        DESCRIPTION
            "Indicates the filter, expressed in KHz."
        ::= { optixRtnOduGeneralAttrEntry 2 }

    -- 1.3.6.1.4.1.2011.2.25.4.40.4.10.11.1.3
    optixRtnOduAllFilterListInfo OBJECT-TYPE
        SYNTAX OCTET STRING
        MAX-ACCESS read-only
        STATUS current
        DESCRIPTION
            "Indicates the supported filter list. Every 4 bytes represent a filter, expressed in KHz."
        ::= { optixRtnOduGeneralAttrEntry 3 }

    -- 1.3.6.1.4.1.2011.2.25.4.40.4.10.11.1.4
    optixRtnOduLoopMode OBJECT-TYPE
        SYNTAX INTEGER
        {
            noloop(0),
            inloop(1),
			outloop(2),
			masterinloop(3),
			slaveinloop(4)
			
        }
        MAX-ACCESS read-write
        STATUS current
        DESCRIPTION
            "Indicates the loop mode:
	    0:no loop
	    1:in loop
	    2:out loop"
        ::= { optixRtnOduGeneralAttrEntry 4 }		
		
    -- 1.3.6.1.4.1.2011.2.25.4.40.4.10.13
    optixRtnOduFactoryInfoTable  OBJECT-TYPE
	SYNTAX SEQUENCE OF OptixRtnOduFactoryInfoEntry
	MAX-ACCESS not-accessible
	STATUS current
	DESCRIPTION
	    "Query ODU manufacturers information."
	::= { optixODU 13 }
    -- 1.3.6.1.4.1.2011.2.25.4.40.4.10.13.1	
    optixRtnOduFactoryInfoEntry	OBJECT-TYPE
	SYNTAX OptixRtnOduFactoryInfoEntry
	MAX-ACCESS not-accessible
	STATUS current
	DESCRIPTION
		"Query ODU manufacturers information."
	INDEX{ optixRtnOduIndex1,optixRtnOduIndex2 }
	::= { optixRtnOduFactoryInfoTable 1 }
        
    OptixRtnOduFactoryInfoEntry ::= 
	SEQUENCE {
		optixRtnOduFactoryInfo
	OCTET STRING
	}

    -- 1.3.6.1.4.1.2011.2.25.4.40.4.10.13.1.1	
    optixRtnOduFactoryInfo OBJECT-TYPE
	SYNTAX OCTET STRING
	MAX-ACCESS read-only
	STATUS current
	DESCRIPTION
		"Indicates the information of ODU manufacturers."
	::= { optixRtnOduFactoryInfoEntry 1 }
	
	
     -- 1.3.6.1.4.1.2011.2.25.4.40.4.10.16
     optixRtnOduPowerSwitchTable OBJECT-TYPE
        SYNTAX SEQUENCE OF OptixRtnOduPowerSwitchEntry
        MAX-ACCESS not-accessible
        STATUS current
        DESCRIPTION
            "Describes the RF unit transmit and receive frequencies."
        ::= { optixODU 16 }

    -- 1.3.6.1.4.1.2011.2.25.4.40.4.10.16.1
     optixRtnOduPowerSwitchEntry  OBJECT-TYPE
     	SYNTAX OptixRtnOduPowerSwitchEntry
        MAX-ACCESS not-accessible
        STATUS current
        DESCRIPTION
            "Indicates the parameter entry for power switch."
        INDEX{ optixRtnOduIndex1,optixRtnOduIndex2,optixRtnOduIndex3 }
        ::= { optixRtnOduPowerSwitchTable 1 }

    OptixRtnOduPowerSwitchEntry ::=
    	SEQUENCE{
    	    optixOduPowerSwitch
    	    	INTEGER	
    	}
  
    -- 1.3.6.1.4.1.2011.2.25.4.40.4.10.16.1.1
  	optixOduPowerSwitch OBJECT-TYPE
  	    SYNTAX INTEGER {
  	          disable(0),
  	          enable(1)
   	    }
        MAX-ACCESS read-write
        STATUS current
        DESCRIPTION
            "Indicates the transmit power switch"
        ::= { optixRtnOduPowerSwitchEntry 1 }

	
    -- 1.3.6.1.4.1.2011.2.25.4.40.4.10.20
    optixRtnOduFrequencyTable OBJECT-TYPE
        SYNTAX SEQUENCE OF OptixRtnOduFrequencyEntry
        MAX-ACCESS not-accessible
        STATUS current
        DESCRIPTION
            "Describes the RF unit transmit and receive frequencies."
        ::= { optixODU 20 }

    -- 1.3.6.1.4.1.2011.2.25.4.40.4.10.20.1
    optixRtnOduFrequencyEntry OBJECT-TYPE
        SYNTAX OptixRtnOduFrequencyEntry
        MAX-ACCESS not-accessible
        STATUS current
        DESCRIPTION
            "Indicates the parameter entry for the RF unit transmit and receive frequencies."
        INDEX{ optixRtnOduIndex1,optixRtnOduIndex2 }
        ::= { optixRtnOduFrequencyTable 1 }

    OptixRtnOduFrequencyEntry ::=
        SEQUENCE {
            optixRtnOduCfgTxFreq
                Unsigned32,
            optixRtnOduCfgTRSpacing
                Unsigned32,
            optixRtnOduActualTxFreq
                Unsigned32,
            optixRtnOduActualRxFreq
                Unsigned32,
            optixRtnOduMinTxFreq
                Unsigned32,
            optixRtnOduMaxTxFreq
                Unsigned32,
	    optixRtnOduRealRTRSpacing
            	Unsigned32
        }
    -- 1.3.6.1.4.1.2011.2.25.4.40.4.10.20.1.1
     optixRtnOduCfgTxFreq OBJECT-TYPE
        SYNTAX Unsigned32
        MAX-ACCESS read-write
        STATUS current
        DESCRIPTION
            "Indicates the transmit frequency of an RF unit. When frequencies of the transmitter/receiver at both ends match, signals can be transmitted and received successfully. Unit: kHz"
        ::= { optixRtnOduFrequencyEntry 1 }
	
   
    -- 1.3.6.1.4.1.2011.2.25.4.40.4.10.20.1.2
    optixRtnOduCfgTRSpacing OBJECT-TYPE
        SYNTAX Unsigned32
        MAX-ACCESS read-write
        STATUS current
        DESCRIPTION
            "Indicates the TR spacing of an RF unit board to avoid interference. Unit: kHz"
        ::= { optixRtnOduFrequencyEntry 2 }

    -- 1.3.6.1.4.1.2011.2.25.4.40.4.10.20.1.3
    optixRtnOduActualTxFreq OBJECT-TYPE
        SYNTAX Unsigned32
        MAX-ACCESS read-only
        STATUS current
        DESCRIPTION
            "Indicates the actual transmit frequency of an RF unit. Unit: kHz"
        ::= { optixRtnOduFrequencyEntry 3 }

    -- 1.3.6.1.4.1.2011.2.25.4.40.4.10.20.1.4
    optixRtnOduActualRxFreq OBJECT-TYPE
        SYNTAX Unsigned32
        MAX-ACCESS read-only
        STATUS current
        DESCRIPTION
            "Indicates the actual receive frequency of an RF unit. Unit: kHz"
        ::= { optixRtnOduFrequencyEntry 4 }

    -- 1.3.6.1.4.1.2011.2.25.4.40.4.10.20.1.5
    optixRtnOduMinTxFreq OBJECT-TYPE
        SYNTAX Unsigned32
        MAX-ACCESS read-only
        STATUS current
        DESCRIPTION
            "Indicates the minimum range of an RF unit frequency point. Unit: kHz"
        ::= { optixRtnOduFrequencyEntry 5 }

    -- 1.3.6.1.4.1.2011.2.25.4.40.4.10.20.1.6
    optixRtnOduMaxTxFreq OBJECT-TYPE
        SYNTAX Unsigned32
        MAX-ACCESS read-only
        STATUS current
        DESCRIPTION
            "Indicates the maximum range of an RF unit frequency point. Unit: kHz"
        ::= { optixRtnOduFrequencyEntry 6 }
	
    -- 1.3.6.1.4.1.2011.2.25.4.40.4.10.20.1.7
    optixRtnOduRealRTRSpacing OBJECT-TYPE
        SYNTAX Unsigned32
        MAX-ACCESS read-only
        STATUS current
        DESCRIPTION
            "Indicates the real TR spacing of an RF unit. Unit: kHz"
        ::= { optixRtnOduFrequencyEntry 7 }
	
    --1,3,6,1,4,1,2011,2,25,4,40,4,10,23
    optixRtnOduAmTxpowerTable OBJECT-TYPE
    	 SYNTAX SEQUENCE OF OptixRtnOduAmTxpowerEntry
        MAX-ACCESS not-accessible
        STATUS current
        DESCRIPTION
            "Describes parameters of the txpower range."
        ::= { optixODU 23 }
	
    --1,3,6,1,4,1,2011,2,25,4,40,4,10,23.1
    optixRtnOduAmTxpowerEntry OBJECT-TYPE
    	SYNTAX OptixRtnOduAmTxpowerEntry
        MAX-ACCESS not-accessible
        STATUS current
        DESCRIPTION
            "Indicates the parameter entry for the txpower range."
        INDEX{ optixRtnOduIndex1,optixRtnOduIndex2,optixRtnOduIndex3 }
        ::= { optixRtnOduAmTxpowerTable 1 }
	
    OptixRtnOduAmTxpowerEntry ::=
    	SEQUENCE {
    	    optixRtnOduAcm
	            OCTET STRING
	           	}
    
    --1,3,6,1,4,1,2011,2,25,4,40,4,10,23.1.1
    optixRtnOduAcm  OBJECT-TYPE
        SYNTAX  OCTET STRING 
	    MAX-ACCESS read-only
        STATUS current
        DESCRIPTION
	    "this leaf sis AM modle."
	::={optixRtnOduAmTxpowerEntry 1}
	


		
    -- 1.3.6.1.4.1.2011.2.25.4.40.4.10.30
    optixRtnOduPowerTable OBJECT-TYPE
        SYNTAX SEQUENCE OF OptixRtnOduPowerEntry
        MAX-ACCESS not-accessible
        STATUS current
        DESCRIPTION
            "Describes parameters of the RF unit transmit and receive power."
        ::= { optixODU 30 }

    -- 1.3.6.1.4.1.2011.2.25.4.40.4.10.30.1
    optixRtnOduPowerEntry OBJECT-TYPE
        SYNTAX OptixRtnOduPowerEntry
        MAX-ACCESS not-accessible
        STATUS current
        DESCRIPTION
            "Indicates the parameter entry for the RF unit transmit and receive powers."
        INDEX{ optixRtnOduIndex1,optixRtnOduIndex2 }
        ::= { optixRtnOduPowerTable 1 }

    OptixRtnOduPowerEntry ::=
        SEQUENCE {
            optixRtnOduCfgTxPower
                Integer32,
            optixRtnOduCfgToBeRxPower
                Integer32,
            optixRtnOduTxPowerHighTh
                Integer32,
            optixRtnOduTxPowerLowTH
                Integer32,
            optixRtnOduRxPowerHighTh
                Integer32,
            optixRtnOduRxPowerLowTH
                Integer32,
            optixRtnOduCfgMaxTxpower
                Integer32,
            optixRtnOduActualTxPower
                Integer32,
            optixRtnOduActualRxPower
                Integer32,
            optixRtnOduMaxTxpower
                Integer32,
            optixRtnOduMinTxpower
                Integer32
        }

    -- 1.3.6.1.4.1.2011.2.25.4.40.4.10.30.1.1
    optixRtnOduCfgTxPower OBJECT-TYPE
        SYNTAX Integer32
        MAX-ACCESS read-write
        STATUS current
        DESCRIPTION
            "Indicates the transmit power of an RF port. Signed type Value range: -100 to +350 Unit: 0.1 dBm"
        DEFVAL{ 100 }
        ::= { optixRtnOduPowerEntry 1 }

    -- 1.3.6.1.4.1.2011.2.25.4.40.4.10.30.1.2
    optixRtnOduCfgToBeRxPower OBJECT-TYPE
        SYNTAX Integer32
        MAX-ACCESS read-write
        STATUS current
        DESCRIPTION
            "Indicates the power expected to receive by an RF port. Unit: 0.1 dBm"
        ::= { optixRtnOduPowerEntry 2 }

    -- 1.3.6.1.4.1.2011.2.25.4.40.4.10.30.1.3
    optixRtnOduTxPowerHighTh OBJECT-TYPE
        SYNTAX Integer32
        MAX-ACCESS read-write
        STATUS current
        DESCRIPTION
            "Indicates the upper threshold of the transmit power. Signed type The value range: -100 to +350 Unit: 0.1 dBm"
        DEFVAL{ 350 }
        ::= { optixRtnOduPowerEntry 3 }

    -- 1.3.6.1.4.1.2011.2.25.4.40.4.10.30.1.4
    optixRtnOduTxPowerLowTH OBJECT-TYPE
        SYNTAX Integer32
        MAX-ACCESS read-write
        STATUS current
        DESCRIPTION
            "Indicates the lower threshold of the transmit power. Signed type The value range: -100 to +350 Unit: 0.1 dBm"
        DEFVAL{ 350 }
        ::= { optixRtnOduPowerEntry 4 }

    -- 1.3.6.1.4.1.2011.2.25.4.40.4.10.30.1.5
    optixRtnOduRxPowerHighTh OBJECT-TYPE
        SYNTAX Integer32
        MAX-ACCESS read-write
        STATUS current
        DESCRIPTION
            "Indicates the upper threshold of the receive power. Signed type Unit: 0.1 dBm"
        ::= { optixRtnOduPowerEntry 5 }

    -- 1.3.6.1.4.1.2011.2.25.4.40.4.10.30.1.6
    optixRtnOduRxPowerLowTH OBJECT-TYPE
        SYNTAX Integer32
        MAX-ACCESS read-write
        STATUS current
        DESCRIPTION
            "Indicates the lower threshold of the receive power. Signed type Unit: 0.1 dBm"
        ::= { optixRtnOduPowerEntry 6 }

    -- 1.3.6.1.4.1.2011.2.25.4.40.4.10.30.1.7
    optixRtnOduCfgMaxTxpower OBJECT-TYPE
        SYNTAX Integer32
        MAX-ACCESS read-write
        STATUS current
        DESCRIPTION
            "Indicates the maximum transmit power of an RF unit board. When the ACM function is disabled, the maximum transmit power in the current mode is returned. When the ACM function is enabled, the maximum transmit power in the guaranteed capacity modulation mode is returned."
        ::= { optixRtnOduPowerEntry 7 }

    -- 1.3.6.1.4.1.2011.2.25.4.40.4.10.30.1.8
    optixRtnOduActualTxPower OBJECT-TYPE
        SYNTAX Integer32
        MAX-ACCESS read-only
        STATUS current
        DESCRIPTION
            "Indicates the actual transmit power of an RF port. Signed type Unit: 0.1 dBm"
        ::= { optixRtnOduPowerEntry 8 }

    -- 1.3.6.1.4.1.2011.2.25.4.40.4.10.30.1.9
    optixRtnOduActualRxPower OBJECT-TYPE
        SYNTAX Integer32
        MAX-ACCESS read-only
        STATUS current
        DESCRIPTION
            "Indicates the actual receive power of an RF port. Signed type Unit: 0.1 dBm"
        ::= { optixRtnOduPowerEntry 9 }

    -- 1.3.6.1.4.1.2011.2.25.4.40.4.10.30.1.10
    optixRtnOduMaxTxpower OBJECT-TYPE
        SYNTAX Integer32
        MAX-ACCESS read-only
        STATUS current
        DESCRIPTION
            "Indicates the maximum value of the actual transmit power. Signed type Unit: 0.1 dBm"
        ::= { optixRtnOduPowerEntry 10 }

    -- 1.3.6.1.4.1.2011.2.25.4.40.4.10.30.1.11
    optixRtnOduMinTxpower OBJECT-TYPE
        SYNTAX Integer32
        MAX-ACCESS read-only
        STATUS current
        DESCRIPTION
            "Indicates the minimum value of the actual transmit power. Signed type Unit: 0.1 dBm"
        ::= { optixRtnOduPowerEntry 11 }


		
    -- 1.3.6.1.4.1.2011.2.25.4.40.4.10.40
    optixRtnOduWorkStateTable OBJECT-TYPE
        SYNTAX SEQUENCE OF OptixRtnOduWorkStateEntry
        MAX-ACCESS not-accessible
        STATUS current
        DESCRIPTION
            "Indicates the current emission status of an RF unit board."
        ::= { optixODU 40 }

    -- 1.3.6.1.4.1.2011.2.25.4.40.4.10.40.1
    optixRtnOduWorkStateEntry OBJECT-TYPE
        SYNTAX OptixRtnOduWorkStateEntry
        MAX-ACCESS not-accessible
        STATUS current
        DESCRIPTION
            "Indicates the transmission status entry for an RF unit."
        INDEX{ optixRtnOduIndex1,optixRtnOduIndex2 }
        ::= { optixRtnOduWorkStateTable 1 }

    OptixRtnOduWorkStateEntry ::=
        SEQUENCE {
            optixRtnOduConfigWorkState
                OPTIXRtnOduWorkStateType,
            optixRtnOduActualWorkState
                INTEGER
        }

    -- 1.3.6.1.4.1.2011.2.25.4.40.4.10.40.1.1
    optixRtnOduConfigWorkState OBJECT-TYPE
        SYNTAX OPTIXRtnOduWorkStateType
        MAX-ACCESS read-write
        STATUS current
        DESCRIPTION
            "Indicates the transmission status of an RF transmitter. Values: 0: muted 1: unmuted"
        DEFVAL{ 1 }
        ::= { optixRtnOduWorkStateEntry 1 }

    -- 1.3.6.1.4.1.2011.2.25.4.40.4.10.40.1.2
    optixRtnOduActualWorkState OBJECT-TYPE
        SYNTAX INTEGER
        {
            mute(0),
            unmute(1)
        }
        MAX-ACCESS read-only
        STATUS current
        DESCRIPTION
            "Indicates the transmission actual status of an RF transmitter. Values: 0: muted 1: unmuted"
        ::= { optixRtnOduWorkStateEntry 2 }

    -- 1.3.6.1.4.1.2011.2.25.4.40.4.10.43
    optixRtnRegOduLHFreqScanTable OBJECT-TYPE
	SYNTAX SEQUENCE OF OptixRtnRegOduLHFreqScanEntry
	MAX-ACCESS not-accessible
	STATUS current
	DESCRIPTION
	"Describes the information about RF unit, frequency scanning , and obtaining of interfering frequency."
	::= { optixODU 43 }  

 -- 1.3.6.1.4.1.2011.2.25.4.40.4.10.43.1
    optixRtnRegOduLHFreqScanEntry OBJECT-TYPE
        SYNTAX OptixRtnRegOduLHFreqScanEntry
        MAX-ACCESS not-accessible
        STATUS current
        DESCRIPTION
            "Indicates the parameter entry for RF unit frequency scanning."
        INDEX{ optixRtnOduIndex1,optixRtnOduIndex2,optixRtnOduIndex3}
        ::= { optixRtnRegOduLHFreqScanTable 1 }
	
    OptixRtnRegOduLHFreqScanEntry ::=
        SEQUENCE {
            optixRtnOduLHScanFreqInterference
                INTEGER,
            optixRtnOduLHScanFreqLeakage
                INTEGER,
            optixRtnOduLHScanFreqIntermodulation
                INTEGER,
            optixRtnOduLHScanFreqStaFreq
                INTEGER,
            optixRtnOduLHScanFreqEndFreq
                INTEGER,
            optixRtnOduLHScanFreqStep
                INTEGER,
            optixRtnOduLHScanFreqBandWidth
                INTEGER,
            optixRtnOduLHScanFreqNumber
                INTEGER,
            optixRtnOduLHScanFreqBids
                OCTET STRING
        }
	
	
    -- 1.3.6.1.4.1.2011.2.25.4.40.4.10.43.1.4
    optixRtnOduLHScanFreqInterference OBJECT-TYPE
        SYNTAX INTEGER
	{
	    no(0),
	    yes(1),
	    unknown(-1)	
	}
        MAX-ACCESS read-only
        STATUS current
        DESCRIPTION
            "Indicates the  information of Interference."
        ::= { optixRtnRegOduLHFreqScanEntry 4 }
 
    -- 1.3.6.1.4.1.2011.2.25.4.40.4.10.43.1.5
    optixRtnOduLHScanFreqLeakage OBJECT-TYPE
        SYNTAX INTEGER
	{
	    no(0),
	    yes(1),
	    unknown(-1)	
	}
        MAX-ACCESS read-only
        STATUS current
        DESCRIPTION
            "Indicates the  information of Leakage."
        ::= { optixRtnRegOduLHFreqScanEntry 5 }
	
    -- 1.3.6.1.4.1.2011.2.25.4.40.4.10.43.1.6
    optixRtnOduLHScanFreqIntermodulation OBJECT-TYPE
        SYNTAX INTEGER
	{
	    no(0),
	    yes(1),
	    unknown(-1)	
	}
        MAX-ACCESS read-only
        STATUS current
        DESCRIPTION
            "Indicates the  information of Intermodulation."
        ::= { optixRtnRegOduLHFreqScanEntry 6}
	
	
    -- 1.3.6.1.4.1.2011.2.25.4.40.4.10.43.1.7
    optixRtnOduLHScanFreqStaFreq OBJECT-TYPE
        SYNTAX INTEGER
        MAX-ACCESS read-write
        STATUS current
        DESCRIPTION
            "Indicates the  frequence of starting scanning ."
        ::= { optixRtnRegOduLHFreqScanEntry 7}
	
    -- 1.3.6.1.4.1.2011.2.25.4.40.4.10.43.1.8
    optixRtnOduLHScanFreqEndFreq OBJECT-TYPE
        SYNTAX INTEGER
        MAX-ACCESS read-write
        STATUS current
        DESCRIPTION
            "Indicates the  frequence of ending scanning."
        ::= { optixRtnRegOduLHFreqScanEntry 8}
	
    -- 1.3.6.1.4.1.2011.2.25.4.40.4.10.43.1.9
    optixRtnOduLHScanFreqStep OBJECT-TYPE
        SYNTAX INTEGER
	{
	    step1p5m(10),
	    step1p75m(11),
	    step3p5m(12),
	    step7m(13),
	    step14m(14)
	}
        MAX-ACCESS read-write
        STATUS current
        DESCRIPTION
            "Indicates the  step of scanning frequence."
        ::= { optixRtnRegOduLHFreqScanEntry 9}

    -- 1.3.6.1.4.1.2011.2.25.4.40.4.10.43.1.10
    optixRtnOduLHScanFreqBandWidth OBJECT-TYPE
        SYNTAX INTEGER
	{
	    bw3P5M(1),
            bw7M(2),
            bw14M(3),
            bw28M(4),
            bw40M(5),
            bw56M(6),
            bwFCC30M(7),
            bwFCC40M(8),
            bwFCC50M(9),
            bw250M(10),
            bw500M(11),
            bw750M(12),
            bw62P5M(16),
            bw125M(17),
            bw112M(23),
            bwFCC10M(24),
            bwFCC20M(25),
            bwFCC60M(28)
	}
        MAX-ACCESS read-write
        STATUS current
        DESCRIPTION
            "Indicates the  bandwidth of scanning frequence."
        ::= { optixRtnRegOduLHFreqScanEntry 10}	
	
    -- 1.3.6.1.4.1.2011.2.25.4.40.4.10.43.1.11
    optixRtnOduLHScanFreqNumber OBJECT-TYPE
        SYNTAX INTEGER
        MAX-ACCESS read-write
        STATUS current
        DESCRIPTION
            "Indicates the  number of scanning frequence."
        ::= { optixRtnRegOduLHFreqScanEntry 11}	
	
    -- 1.3.6.1.4.1.2011.2.25.4.40.4.10.43.1.12
    optixRtnOduLHScanFreqBids OBJECT-TYPE
        SYNTAX OCTET STRING
        MAX-ACCESS read-write
        STATUS current
        DESCRIPTION
            "Indicates the  board IDs of scanning frequence. format:number,bid1,bid2,...,"
        ::= { optixRtnRegOduLHFreqScanEntry 12}	
	
	
	
   -- 1.3.6.1.4.1.2011.2.25.4.40.4.10.44
    optixRtnRegOduLHFreqScanResultTable OBJECT-TYPE
	SYNTAX SEQUENCE OF OptixRtnRegOduLHFreqScanResulEntry
	MAX-ACCESS not-accessible
	STATUS current
	DESCRIPTION
	"Describes the information about RF unit, frequency scanning , and obtaining of interfering frequency."
	::= { optixODU 44 }  

    -- 1.3.6.1.4.1.2011.2.25.4.40.4.10.44.1
    optixRtnRegOduLHFreqScanResulEntry OBJECT-TYPE
        SYNTAX OptixRtnRegOduLHFreqScanResulEntry
        MAX-ACCESS not-accessible
        STATUS current
        DESCRIPTION
            "Indicates the parameter entry for RF unit frequency scanning."
        INDEX{ optixRtnOduIndex1,optixRtnOduIndex2,optixRtnOduIndex3,optixRtnOduIndex4}
        ::= { optixRtnRegOduLHFreqScanResultTable 1 }
	
    OptixRtnRegOduLHFreqScanResulEntry ::=
        SEQUENCE {
            optixRtnOduLHScanResultRxFreq
                INTEGER,
            optixRtnOduLHScanResultMainRsl
                INTEGER,
            optixRtnOduLHScanResultSlaveRsl
                INTEGER
        
        }
		
    -- 1.3.6.1.4.1.2011.2.25.4.40.4.10.44.1.5
    optixRtnOduLHScanResultRxFreq	OBJECT-TYPE			
  	SYNTAX INTEGER
        MAX-ACCESS read-only
        STATUS current
        DESCRIPTION
            "Indicates the Rx frequency of frequency scanning."
        ::= { optixRtnRegOduLHFreqScanResulEntry 5 }
	
    -- 1.3.6.1.4.1.2011.2.25.4.40.4.10.44.1.6
    optixRtnOduLHScanResultMainRsl	OBJECT-TYPE				
  	SYNTAX INTEGER
        MAX-ACCESS read-only
        STATUS current
        DESCRIPTION
            "Indicates the main Rsl of frequency scanning."
        ::= { optixRtnRegOduLHFreqScanResulEntry 6 }
	
    -- 1.3.6.1.4.1.2011.2.25.4.40.4.10.44.1.7
    optixRtnOduLHScanResultSlaveRsl	OBJECT-TYPE				
  	SYNTAX INTEGER
        MAX-ACCESS read-only
        STATUS current
        DESCRIPTION
            "Indicates the slave Rsl of frequency scanning."
        ::= { optixRtnRegOduLHFreqScanResulEntry 7 }
	
    -- 1.3.6.1.4.1.2011.2.25.4.40.4.10.50
    optixRtnOduFreqScanTable OBJECT-TYPE
        SYNTAX SEQUENCE OF OptixRtnOduFreqScanEntry
        MAX-ACCESS not-accessible
        STATUS current
        DESCRIPTION
            "Describes the information about RF unit start, frequency scanning stop, and obtaining of interfering frequency."
        ::= { optixODU 50 }

    -- 1.3.6.1.4.1.2011.2.25.4.40.4.10.50.1
    optixRtnOduFreqScanEntry OBJECT-TYPE
        SYNTAX OptixRtnOduFreqScanEntry
        MAX-ACCESS not-accessible
        STATUS current
        DESCRIPTION
            "Indicates the parameter entry for RF unit frequency scanning."
        INDEX{ optixRtnOduIndex1,optixRtnOduIndex2 }
        ::= { optixRtnOduFreqScanTable 1 }

    OptixRtnOduFreqScanEntry ::=
        SEQUENCE {
            optixRtnOduStartScanStartFreq
                Unsigned32,
            optixRtnOduStartScanEndFreq
                Unsigned32,
            optixRtnOduStartScanStep
                INTEGER,
            optixRtnOduStartScanBWid
                INTEGER,
            optixRtnOduStopFreqScan
                INTEGER,
            optixRtnOduInterferenceFreqBwid
                INTEGER,
            optixRtnOduInterferenceFreqLeftChannel
                INTEGER,
            optixRtnOduInterferenceFreqCfgChannel
                INTEGER,
            optixRtnOduInterferenceFreqRightChannel
                INTEGER
        }

    -- 1.3.6.1.4.1.2011.2.25.4.40.4.10.50.1.1
    optixRtnOduStartScanStartFreq OBJECT-TYPE
        SYNTAX Unsigned32
        MAX-ACCESS read-write
        STATUS current
        DESCRIPTION
            "Indicates the start frequency of frequency scanning. Unit:KHz"
        ::= { optixRtnOduFreqScanEntry 1 }

    -- 1.3.6.1.4.1.2011.2.25.4.40.4.10.50.1.2
    optixRtnOduStartScanEndFreq OBJECT-TYPE
        SYNTAX Unsigned32
        MAX-ACCESS read-write
        STATUS current
        DESCRIPTION
            "Indicates the end freqency of frequency scanning. Unit:KHz"
        ::= { optixRtnOduFreqScanEntry 2 }

    -- 1.3.6.1.4.1.2011.2.25.4.40.4.10.50.1.3
    optixRtnOduStartScanStep OBJECT-TYPE
        SYNTAX INTEGER
        {
            step15M(1),
            step31M(2),
            step62M(3),
            step1P5M(10),
            step1P75M(11),
            step3P5M(12),
            step7M(13),
            step14M(14)
        }
        MAX-ACCESS read-write
        STATUS current
        DESCRIPTION
            "Indicates the step of frequency scanning. Values for RTN300:1-15M,2-31M,3- 62M. Values for RTN900:11-1P5M,12-1P75M,13-3P5M,14-7M,15-14M"
        ::= { optixRtnOduFreqScanEntry 3 }

    -- 1.3.6.1.4.1.2011.2.25.4.40.4.10.50.1.4
    optixRtnOduStartScanBWid OBJECT-TYPE
        SYNTAX INTEGER
        {  
        	bw3P5M(1),
        	bw7M(2),
        	bw14M(3),
        	bw28M(4),
        	bw40M(5),
        	bw56M(6),
        	bwFCC30M(7),
        	bwFCC40M(8),
        	bwFCC50M(9),
        	bw112M(23),
        	bwFCC10M(24),
        	bwFCC20M(25),
        	bsFCC60M(28)
        }
        MAX-ACCESS read-write
        STATUS current
        DESCRIPTION
            "Indicates the bandwidth of frequency scanning,for calculating available frequencies."
        ::= { optixRtnOduFreqScanEntry 4 }

    -- 1.3.6.1.4.1.2011.2.25.4.40.4.10.50.1.5
    optixRtnOduStopFreqScan OBJECT-TYPE
        SYNTAX INTEGER
        {
            stop(0)
        }
        MAX-ACCESS read-write
        STATUS current
        DESCRIPTION
            "Indicates the stop of frequency scanning."
        DEFVAL{ stop }
        ::= { optixRtnOduFreqScanEntry 5 }

    -- 1.3.6.1.4.1.2011.2.25.4.40.4.10.50.1.6
    optixRtnOduInterferenceFreqBwid OBJECT-TYPE
        SYNTAX INTEGER
        {
       		bw3P5M(1),
        	bw7M(2),
        	bw14M(3),
        	bw28M(4),
        	bw40M(5),
        	bw56M(6),
        	bwFCC30M(7),
        	bwFCC40M(8),
        	bwFCC50M(9),
        	bw112M(23),
        	bwFCC10M(24),
        	bwFCC20M(25),
        	bwFCC60M(28)
        }
        MAX-ACCESS read-only
        STATUS current
        DESCRIPTION
            "Indicates the configuration bandwidth."
        ::= { optixRtnOduFreqScanEntry 6 }

    -- 1.3.6.1.4.1.2011.2.25.4.40.4.10.50.1.7
    optixRtnOduInterferenceFreqLeftChannel OBJECT-TYPE
        SYNTAX INTEGER
        {
            stateUnknown(-1),
            stateNoInterference(0),
            stateInterference(1)
        }
        MAX-ACCESS read-only
        STATUS current
        DESCRIPTION
            "Indicates the left channel state of configuration frequency"
        ::= { optixRtnOduFreqScanEntry 7 }

    -- 1.3.6.1.4.1.2011.2.25.4.40.4.10.50.1.8
    optixRtnOduInterferenceFreqCfgChannel OBJECT-TYPE
        SYNTAX INTEGER
        {
            stateUnknown(-1),
            stateNoInterference(0),
            stateInterference(1)
        }
        MAX-ACCESS read-only
        STATUS current
        DESCRIPTION
            "Indicates the current channel state of configuration frequency."
        ::= { optixRtnOduFreqScanEntry 8 }

    -- 1.3.6.1.4.1.2011.2.25.4.40.4.10.50.1.9
    optixRtnOduInterferenceFreqRightChannel OBJECT-TYPE
        SYNTAX INTEGER
        {
            stateUnknown(-1),
            stateNoInterference(0),
            stateInterference(1)
        }
        MAX-ACCESS read-only
        STATUS current
        DESCRIPTION
            "Indicates the right channel state of configuration frequency."
        ::= { optixRtnOduFreqScanEntry 9 }

    -- 1.3.6.1.4.1.2011.2.25.4.40.4.10.60
    optixRtnOduFreqScanAvailFreqTable OBJECT-TYPE
        SYNTAX SEQUENCE OF OptixRtnOduFreqScanAvailFreqEntry
        MAX-ACCESS not-accessible
        STATUS current
        DESCRIPTION
            "Describes Available frequencies of the RF unit frequency scanning."
        ::= { optixODU 60 }

    -- 1.3.6.1.4.1.2011.2.25.4.40.4.10.60.1
    optixRtnOduFreqScanAvailFreqEntry OBJECT-TYPE
        SYNTAX OptixRtnOduFreqScanAvailFreqEntry
        MAX-ACCESS not-accessible
        STATUS current
        DESCRIPTION
            "Indicates the parameter entry for the RF unit frequency scanning."
        INDEX{ optixRtnOduIndex1,optixRtnOduIndex2,optixRtnOduAvailFreqList }
        ::= { optixRtnOduFreqScanAvailFreqTable 1 }

    OptixRtnOduFreqScanAvailFreqEntry ::=
        SEQUENCE {
            optixRtnOduAvailFreqList
                Unsigned32,
            optixRtnOduGetAvailableBwid
                INTEGER,
            optixRtnOduGetAvailableTxfreqs
                Unsigned32
        }

    -- 1.3.6.1.4.1.2011.2.25.4.40.4.10.60.1.1
    optixRtnOduAvailFreqList OBJECT-TYPE
        SYNTAX Unsigned32
        MAX-ACCESS not-accessible
        STATUS current
        DESCRIPTION
            "Indicates the list number of available frequencies."
        ::= { optixRtnOduFreqScanAvailFreqEntry 1 }

    -- 1.3.6.1.4.1.2011.2.25.4.40.4.10.60.1.2
    optixRtnOduGetAvailableBwid OBJECT-TYPE
        SYNTAX INTEGER
        {
            bw62P5M(16),
            bw125M(17),
            bw250M(10),
            bw500M(11),
            bw750M(12),
            bw3P5M(1),
            bw7M(2),
            bw14M(3),
            bw28M(4),
            bw40M(5),
            bw56M(6),
            bwFCC30M(7),
            bwFCC40M(8),
            bwFCC50M(9),
            bw112M(23),
            bwFCC10M(24),
            bwFCC20M(25),
            bwFCC60M(28)
        }
        MAX-ACCESS read-only
        STATUS current
        DESCRIPTION
            "Indicates the bandwidth that inputted when starting the frequency scanning."
        ::= { optixRtnOduFreqScanAvailFreqEntry 2 }

    -- 1.3.6.1.4.1.2011.2.25.4.40.4.10.60.1.3
    optixRtnOduGetAvailableTxfreqs OBJECT-TYPE
        SYNTAX Unsigned32
        MAX-ACCESS read-only
        STATUS current
        DESCRIPTION
            "Indicates the available freqencies of frequency scanning. Unit:KHz"
        ::= { optixRtnOduFreqScanAvailFreqEntry 3 }

    -- 1.3.6.1.4.1.2011.2.25.4.40.4.10.70
    optixRtnOduFreqScanResultTable OBJECT-TYPE
        SYNTAX SEQUENCE OF OptixRtnOduFreqScanResultEntry
        MAX-ACCESS not-accessible
        STATUS current
        DESCRIPTION
            "Describes result of the RF unit frequency scanning"
        ::= { optixODU 70 }

    -- 1.3.6.1.4.1.2011.2.25.4.40.4.10.70.1
    optixRtnOduFreqScanResultEntry OBJECT-TYPE
        SYNTAX OptixRtnOduFreqScanResultEntry
        MAX-ACCESS not-accessible
        STATUS current
        DESCRIPTION
            "Indicates the parameter entry for the RF unit frequency scanning."
        INDEX{ optixRtnOduIndex1,optixRtnOduIndex2,optixRtnOduScanResultList }
        ::= { optixRtnOduFreqScanResultTable 1 }

    OptixRtnOduFreqScanResultEntry ::=
        SEQUENCE {
            optixRtnOduScanResultList
                Unsigned32,
            optixRtnOduScanResultRxFreq
                Unsigned32,
            optixRtnOduScanResultRxRsl
                Integer32
        }

    -- 1.3.6.1.4.1.2011.2.25.4.40.4.10.70.1.1
    optixRtnOduScanResultList OBJECT-TYPE
        SYNTAX Unsigned32
        MAX-ACCESS not-accessible
        STATUS current
        DESCRIPTION
            "Indicates the list of RF scanning results."
        ::= { optixRtnOduFreqScanResultEntry 1 }

    -- 1.3.6.1.4.1.2011.2.25.4.40.4.10.70.1.2
    optixRtnOduScanResultRxFreq OBJECT-TYPE
        SYNTAX Unsigned32
        MAX-ACCESS read-only
        STATUS current
        DESCRIPTION
            "Indicates the receive freqencies of frequency scanning. Unit:KHz"
        ::= { optixRtnOduFreqScanResultEntry 2 }

    -- 1.3.6.1.4.1.2011.2.25.4.40.4.10.70.1.3
    optixRtnOduScanResultRxRsl OBJECT-TYPE
        SYNTAX Integer32
        MAX-ACCESS read-only
        STATUS current
        DESCRIPTION
            "Indicates the receive power of frequency scanning. Unit:0.1 dBm"
        ::= { optixRtnOduFreqScanResultEntry 3 }

    -- 1.3.6.1.4.1.2011.2.25.4.40.4.10.80
    optixRtnScanFreqTrapCommon OBJECT IDENTIFIER ::= { optixODU 80 }

    -- 1.3.6.1.4.1.2011.2.25.4.40.4.10.80.1
    optixRptRtnScanFreqEvent OBJECT IDENTIFIER ::= { optixRtnScanFreqTrapCommon 1 }

    -- 1.3.6.1.4.1.2011.2.25.4.40.4.10.80.1.1
    optixRtnOduIndexBid OBJECT-TYPE
        SYNTAX Unsigned32
        MAX-ACCESS accessible-for-notify
        STATUS current
        DESCRIPTION
            "Indicates the RF unit board ID."
        ::= { optixRptRtnScanFreqEvent 1 }

    -- 1.3.6.1.4.1.2011.2.25.4.40.4.10.80.1.2
    optixRtnOduIndexSubID OBJECT-TYPE
        SYNTAX Unsigned32
        MAX-ACCESS accessible-for-notify
        STATUS current
        DESCRIPTION
            "Indicates the subboard ID."
        ::= { optixRptRtnScanFreqEvent 2 }

    -- 1.3.6.1.4.1.2011.2.25.4.40.4.10.80.1.3
    optixRptRtnFreqScanState OBJECT-TYPE
        SYNTAX INTEGER
        {
            stopScanFreqStateNormal(0),
            stopScanFreqStateManual(1)
        }
        MAX-ACCESS accessible-for-notify
        STATUS current
        DESCRIPTION
            "Indicates the stop type of frequency scanning."
        ::= { optixRptRtnScanFreqEvent 3 }

    -- 1.3.6.1.4.1.2011.2.25.4.40.4.10.90
    optixRtnScanTrap OBJECT IDENTIFIER ::= { optixODU 90 }

    -- 1.3.6.1.4.1.2011.2.25.4.40.4.10.90.1
    optixRtnScanFreqTrap NOTIFICATION-TYPE
        OBJECTS{ optixRtnOduIndexBid,optixRtnOduIndexSubID,optixRptRtnFreqScanState }
        STATUS current
        DESCRIPTION
            "Indicates the finish event of frequency scanning."
        ::= { optixRtnScanTrap 1 }

    -- 1.3.6.1.4.1.2011.2.25.4.40.4.10.100
    optixRtnOduTemplateTable OBJECT-TYPE
        SYNTAX SEQUENCE OF OptixRtnOduTemplateEntry
        MAX-ACCESS not-accessible
        STATUS current
        DESCRIPTION
            "Describes parameters of the ODU template."
        ::= { optixODU 100 }

    -- 1.3.6.1.4.1.2011.2.25.4.40.4.10.100.1
    optixRtnOduTemplateEntry OBJECT-TYPE
        SYNTAX OptixRtnOduTemplateEntry
        MAX-ACCESS not-accessible
        STATUS current
        DESCRIPTION
            "Indicates the parameter entry for the ODU template"
        INDEX{ optixRtnOduIndex1,optixRtnOduIndex2,optixRtnOduIndex3 }
        ::= { optixRtnOduTemplateTable 1 }

    OptixRtnOduTemplateEntry ::=
        SEQUENCE {
            optixRtnOduTemplate
                INTEGER
        }

    -- 1.3.6.1.4.1.2011.2.25.4.40.4.10.100.1.1
    optixRtnOduTemplate OBJECT-TYPE
        SYNTAX INTEGER
        {
            relative(0),
            absolute(1)
        }
        MAX-ACCESS read-write
        STATUS current
        DESCRIPTION
            "Indicates the template of an RF port."
        DEFVAL{ relative }
        ::= { optixRtnOduTemplateEntry 1 }

	-- 1.3.6.1.4.1.2011.2.25.4.40.4.10.105
	optixRtnOduTypeInfoTable OBJECT-TYPE
		SYNTAX SEQUENCE OF OptixRtnOduTypeInfoEntry
		MAX-ACCESS not-accessible
		STATUS current
		DESCRIPTION
		"Indicates the type of ODU."
		::= { optixODU 105 }

	-- 1.3.6.1.4.1.2011.2.25.4.40.4.10.105.1
	optixRtnOduTypeInfoEntry OBJECT-TYPE
		SYNTAX OptixRtnOduTypeInfoEntry
		MAX-ACCESS not-accessible
		STATUS current
		DESCRIPTION
		"Indicates the type of ODU."
		INDEX{ optixRtnOduIndex1,optixRtnOduIndex2,optixRtnOduIndex3 }
		::= { optixRtnOduTypeInfoTable 1 }

	OptixRtnOduTypeInfoEntry ::=
		SEQUENCE {
		optixRtnLinkReportOduType
		OCTET STRING,
		optixRtnEquipOduType
		OCTET STRING
		}

	-- 1.3.6.1.4.1.2011.2.25.4.40.4.10.105.1.1
	optixRtnLinkReportOduType OBJECT-TYPE
		SYNTAX OCTET STRING
		MAX-ACCESS read-only
		STATUS current
		DESCRIPTION
		"Indicates the type of LinkReportODU."
		::= { optixRtnOduTypeInfoEntry 1 }

	-- 1.3.6.1.4.1.2011.2.25.4.40.4.10.105.1.2
	optixRtnEquipOduType OBJECT-TYPE
		SYNTAX OCTET STRING
		MAX-ACCESS read-only
		STATUS current
		DESCRIPTION
		"Indicates the type of EquipODU."
		::= { optixRtnOduTypeInfoEntry 2 }

		-- 1.3.6.1.4.1.2011.2.25.4.40.4.10.106
	optixRtnOduDuplexInfoTable OBJECT-TYPE
	SYNTAX SEQUENCE OF OptixRtnOduDuplexInfoEntry
	MAX-ACCESS not-accessible
	STATUS current
	DESCRIPTION
		"Query the device information of ODU duplex."
	::= { optixODU 106 }

	-- 1.3.6.1.4.1.2011.2.25.4.40.4.10.106.1
	optixRtnOduDuplexInfoEntry OBJECT-TYPE
	SYNTAX OptixRtnOduDuplexInfoEntry
	MAX-ACCESS not-accessible
	STATUS current
	DESCRIPTION
		"Indicates the device information of ODU duplex."
	INDEX{ optixRtnOduIndex1,optixRtnOduIndex2,optixRtnOduIndex3 }
	::= { optixRtnOduDuplexInfoTable 1 }

	OptixRtnOduDuplexInfoEntry ::=
	SEQUENCE {
	optixRtnSubFreq
	INTEGER,
	optixRtnTRSpacing
	Unsigned32,
	optixRtnFreqMin
	Unsigned32,
	optixRtnFreqMax
	Unsigned32
	}

	-- 1.3.6.1.4.1.2011.2.25.4.40.4.10.106.1.1
	optixRtnSubFreq OBJECT-TYPE
	SYNTAX INTEGER
	{
		a(1),
		b(2),
		c(3),
		d(4),
		e(5),
		f(6),
		g(7),
		h(8),
		i(9),
		j(10),
		k(11),
		l(12),
		m(13),
		n(14),
		o(15),
		p(16),
		q(17),
		r(18),
		s(19),
		t(20),
		u(21),
		v(22),
		w(23),
		x(24),
		y(25),
		z(26)
	}
	MAX-ACCESS read-only
	STATUS current
	DESCRIPTION
	"Indicates the subfrequency of ODU duplex."
	::= { optixRtnOduDuplexInfoEntry 1 }

	-- 1.3.6.1.4.1.2011.2.25.4.40.4.10.106.1.2
	optixRtnTRSpacing OBJECT-TYPE
	SYNTAX Unsigned32
	MAX-ACCESS read-only
	STATUS current
	DESCRIPTION
	"Indicates the TRSpacing of ODU duplex."
	::= { optixRtnOduDuplexInfoEntry 2 }
	
	-- 1.3.6.1.4.1.2011.2.25.4.40.4.10.106.1.3
	optixRtnFreqMin OBJECT-TYPE
	SYNTAX Unsigned32
	MAX-ACCESS read-only
	STATUS current
	DESCRIPTION
	"Indicates the minimum frequency of ODU duplex."
	::= { optixRtnOduDuplexInfoEntry 3 }
	
	-- 1.3.6.1.4.1.2011.2.25.4.40.4.10.106.1.4
	optixRtnFreqMax OBJECT-TYPE
	SYNTAX Unsigned32
	MAX-ACCESS read-only
	STATUS current
	DESCRIPTION
	"Indicates the maximum frequency of ODU duplex."
	::= { optixRtnOduDuplexInfoEntry 4 }


    -- 1.3.6.1.4.1.2011.2.25.4.40.4.10.110
    optixRtnCombineTable OBJECT-TYPE
        SYNTAX SEQUENCE OF OptixRtnCombineEntry
        MAX-ACCESS not-accessible
        STATUS current
        DESCRIPTION
            "Indicates the parameters of the RFU-SD combination mode."
        ::= { optixODU 110 }

    -- 1.3.6.1.4.1.2011.2.25.4.40.4.10.110.1
    optixRtnCombineEntry OBJECT-TYPE
        SYNTAX OptixRtnCombineEntry
        MAX-ACCESS not-accessible
        STATUS current
        DESCRIPTION
            "Indicates the parameter entry for the RFU-SD combine mode."
        INDEX{ optixRtnRFUBid,optixRtnRFUSubCardId }
        ::= { optixRtnCombineTable 1 }

    OptixRtnCombineEntry ::=
        SEQUENCE {
            optixRtnCombineMode
                OPTIXRtnCombineMode,
            optixRtnCombineActualMode
                OPTIXRtnCombineMode
        }

    -- 1.3.6.1.4.1.2011.2.25.4.40.4.10.110.1.1
    optixRtnCombineMode OBJECT-TYPE
        SYNTAX OPTIXRtnCombineMode
        MAX-ACCESS read-write
        STATUS current
        DESCRIPTION
            "Indicates the RFU-SD combination mode."
        DEFVAL{ 2 }
        ::= { optixRtnCombineEntry 1 }

    -- 1.3.6.1.4.1.2011.2.25.4.40.4.10.110.1.2
    optixRtnCombineActualMode OBJECT-TYPE
        SYNTAX OPTIXRtnCombineMode
        MAX-ACCESS read-only
        STATUS current
        DESCRIPTION
            "Indicates the RFU-SD actual combination mode."
        ::= { optixRtnCombineEntry 2 }

    -- 1.3.6.1.4.1.2011.2.25.4.40.4.10.120
    optixRtnSlavePowerTable OBJECT-TYPE
        SYNTAX SEQUENCE OF OptixRtnSlavePowerEntry
        MAX-ACCESS not-accessible
        STATUS current
        DESCRIPTION
            "Indicates the parameters related to the receive power of the RFU-SD slave port."
        ::= { optixODU 120 }

    -- 1.3.6.1.4.1.2011.2.25.4.40.4.10.120.1
    optixRtnSlavePowerEntry OBJECT-TYPE
        SYNTAX OptixRtnSlavePowerEntry
        MAX-ACCESS not-accessible
        STATUS current
        DESCRIPTION
            "Indicates the entry of the power parameters of the RFU-SD slave port."
        INDEX{ optixRtnRFUBid,optixRtnRFUSubCardId }
        ::= { optixRtnSlavePowerTable 1 }

    OptixRtnSlavePowerEntry ::=
        SEQUENCE {
            optixRtnSlaveCfgToBeRxPower
                Integer32,
            optixRtnSlaveRxPowerHighTh
                Integer32,
            optixRtnSlaveRxPowerLowTh
                Integer32,
            optixRtnSlaveActualRxPower
                Integer32,
            optixRtnMainActualRxPower
                Integer32,
	    optixRtnRealRxPower
                Integer32
        }

    -- 1.3.6.1.4.1.2011.2.25.4.40.4.10.120.1.1
    optixRtnSlaveCfgToBeRxPower OBJECT-TYPE
        SYNTAX Integer32
        MAX-ACCESS read-write
        STATUS current
        DESCRIPTION
            "Indicates the power expected to be received of the RFU-SD slave port. The unit is 0.1 dBm."
        ::= { optixRtnSlavePowerEntry 1 }

    -- 1.3.6.1.4.1.2011.2.25.4.40.4.10.120.1.2
    optixRtnSlaveRxPowerHighTh OBJECT-TYPE
        SYNTAX Integer32
        MAX-ACCESS read-write
        STATUS current
        DESCRIPTION
            "Indicates the upper threshold of the receive power of the RFU-SD slave port.The unit is 0.1 dBm (signed number)."
        ::= { optixRtnSlavePowerEntry 2 }

    -- 1.3.6.1.4.1.2011.2.25.4.40.4.10.120.1.3
    optixRtnSlaveRxPowerLowTh OBJECT-TYPE
        SYNTAX Integer32
        MAX-ACCESS read-write
        STATUS current
        DESCRIPTION
            "Indicates the lower threshold of the receive power of the RFU-SD slave port.The unit is 0.1 dBm (signed number)."
        ::= { optixRtnSlavePowerEntry 3 }

    -- 1.3.6.1.4.1.2011.2.25.4.40.4.10.120.1.4
    optixRtnSlaveActualRxPower OBJECT-TYPE
        SYNTAX Integer32
        MAX-ACCESS read-only
        STATUS current
        DESCRIPTION
            "Indicates the actual receive power of the RFU-SD slave port.The unit is 0.1 dBm (signed number)."
        ::= { optixRtnSlavePowerEntry 4 }
	
	
    -- 1.3.6.1.4.1.2011.2.25.4.40.4.10.120.1.5
    optixRtnMainActualRxPower OBJECT-TYPE
        SYNTAX Integer32
        MAX-ACCESS read-only
        STATUS current
        DESCRIPTION
            "Indicates the actual receive power of the RFU-SD main port.The unit is 0.1 dBm (signed number)."
        ::= { optixRtnSlavePowerEntry 5 }
	
    -- 1.3.6.1.4.1.2011.2.25.4.40.4.10.120.1.6
    optixRtnRealRxPower OBJECT-TYPE
        SYNTAX Integer32
        MAX-ACCESS read-only
        STATUS current
        DESCRIPTION
            "Indicates the real receive power of the RFU-SD slave port.The unit is 0.1 dBm (signed number)."
        ::= { optixRtnSlavePowerEntry 6 }

    -- 1.3.6.1.4.1.2011.2.25.4.40.4.10.130
    optixRtnFiberEqualTable OBJECT-TYPE
        SYNTAX SEQUENCE OF OptixRtnFiberEqualEntry
        MAX-ACCESS not-accessible
        STATUS current
        DESCRIPTION
            "Indicates the parameters of the RFU-SD delay compensation."
        ::= { optixODU 130 }

    -- 1.3.6.1.4.1.2011.2.25.4.40.4.10.130.1
    optixRtnFiberEqualEntry OBJECT-TYPE
        SYNTAX OptixRtnFiberEqualEntry
        MAX-ACCESS not-accessible
        STATUS current
        DESCRIPTION
            "Indicates the entry of the RFU-SD delay compensation parameter."
        INDEX{ optixRtnRFUBid,optixRtnRFUSubCardId }
        ::= { optixRtnFiberEqualTable 1 }

    OptixRtnFiberEqualEntry ::=
        SEQUENCE {
            optixRtnFiberEqualState
                OPTIXRtnFiberEqualState,
            optixRtnFiberEqualValue
                Integer32
        }

    -- 1.3.6.1.4.1.2011.2.25.4.40.4.10.130.1.1
    optixRtnFiberEqualState OBJECT-TYPE
        SYNTAX OPTIXRtnFiberEqualState
        MAX-ACCESS read-write
        STATUS current
        DESCRIPTION
            "Indicates the status of the RFU-SD delay compensation."
        DEFVAL{ start }
        ::= { optixRtnFiberEqualEntry 1 }

    -- 1.3.6.1.4.1.2011.2.25.4.40.4.10.130.1.2
    optixRtnFiberEqualValue OBJECT-TYPE
        SYNTAX Integer32
        MAX-ACCESS read-only
        STATUS current
        DESCRIPTION
            "Indicates the value of the RFU-SD delay compensation."
        ::= { optixRtnFiberEqualEntry 2 }

    -- 1.3.6.1.4.1.2011.2.25.4.40.4.10.140
    optixRtnRFUFrequencyTable OBJECT-TYPE
        SYNTAX SEQUENCE OF OptixRtnRFUFrequencyEntry
        MAX-ACCESS not-accessible
        STATUS current
        DESCRIPTION
            "Indicates the parameters related to the RFU receive frequency."
        ::= { optixODU 140 }

    -- 1.3.6.1.4.1.2011.2.25.4.40.4.10.140.1
    optixRtnRFUFrequencyEntry OBJECT-TYPE
        SYNTAX OptixRtnRFUFrequencyEntry
        MAX-ACCESS not-accessible
        STATUS current
        DESCRIPTION
            "Indicates the entry of the RFU receive frequency parameter."
        INDEX{ optixRtnRFUBid,optixRtnRFUSubCardId }
        ::= { optixRtnRFUFrequencyTable 1 }

    OptixRtnRFUFrequencyEntry ::=
        SEQUENCE {
            optixRtnRFURxFreq
                Unsigned32,
            optixRtnRFUMinRxFreq
                Unsigned32,
            optixRtnRFUMaxRxFreq
                Unsigned32
        }

    -- 1.3.6.1.4.1.2011.2.25.4.40.4.10.140.1.1
    optixRtnRFURxFreq OBJECT-TYPE
        SYNTAX Unsigned32
        MAX-ACCESS read-write
        STATUS current
        DESCRIPTION
            "Indicates the receive frequency of the RFU. The unit is KHz."
        ::= { optixRtnRFUFrequencyEntry 1 }

    -- 1.3.6.1.4.1.2011.2.25.4.40.4.10.140.1.2
    optixRtnRFUMinRxFreq OBJECT-TYPE
        SYNTAX Unsigned32
        MAX-ACCESS read-only
        STATUS current
        DESCRIPTION
            "Indicates the minimum value of the working range of the RFU receive frequencies. The unit is KHz."
        ::= { optixRtnRFUFrequencyEntry 2 }

    -- 1.3.6.1.4.1.2011.2.25.4.40.4.10.140.1.3
    optixRtnRFUMaxRxFreq OBJECT-TYPE
        SYNTAX Unsigned32
        MAX-ACCESS read-only
        STATUS current
        DESCRIPTION
            "Indicates the maximum value of the working range of the RFU receive frequencies. The unit is KHz."
        ::= { optixRtnRFUFrequencyEntry 3 }

    -- 1.3.6.1.4.1.2011.2.25.4.40.4.10.150
    optixRFUTrapCommon OBJECT IDENTIFIER ::= { optixODU 150 }

    -- 1.3.6.1.4.1.2011.2.25.4.40.4.10.150.1
    optixRFUTrapEvent OBJECT IDENTIFIER ::= { optixRFUTrapCommon 1 }

    -- 1.3.6.1.4.1.2011.2.25.4.40.4.10.150.1.1
    optixRptRtnRFUBid OBJECT-TYPE
        SYNTAX Unsigned32
        MAX-ACCESS accessible-for-notify
        STATUS current
        DESCRIPTION
            "Indicates the slot ID of the RFU board."
        ::= { optixRFUTrapEvent 1 }

    -- 1.3.6.1.4.1.2011.2.25.4.40.4.10.150.1.2
    optixRptRtnRFUSubCardId OBJECT-TYPE
        SYNTAX Unsigned32
        MAX-ACCESS accessible-for-notify
        STATUS current
        DESCRIPTION
            "Indicates the slot ID of the RFU subboard."
        ::= { optixRFUTrapEvent 2 }

    -- 1.3.6.1.4.1.2011.2.25.4.40.4.10.150.1.3
    optixRptRtnFiberEqualResult OBJECT-TYPE
        SYNTAX INTEGER
        {
            success(0),
            fail(1)
        }
        MAX-ACCESS accessible-for-notify
        STATUS current
        DESCRIPTION
            "Indicates the result of the delay compensation."
        ::= { optixRFUTrapEvent 3 }

    -- 1.3.6.1.4.1.2011.2.25.4.40.4.10.150.1.4
    optixRptRtnFiberEqualValue OBJECT-TYPE
        SYNTAX Integer32
        MAX-ACCESS accessible-for-notify
        STATUS current
        DESCRIPTION
            "Indicates the value of the delay compensation."
        ::= { optixRFUTrapEvent 4 }

    -- 1.3.6.1.4.1.2011.2.25.4.40.4.10.160
    optixRtnFiberEqualTrap OBJECT IDENTIFIER ::= { optixODU 160 }

    -- 1.3.6.1.4.1.2011.2.25.4.40.4.10.160.1
    optixRtnFiberEqualResultTrap NOTIFICATION-TYPE
        OBJECTS{ optixRptRtnRFUBid,optixRptRtnRFUSubCardId,optixRptRtnFiberEqualResult,optixRptRtnFiberEqualValue }
        STATUS current
        DESCRIPTION
            "Indicates the result of the delay compensation."
        ::= { optixRtnFiberEqualTrap 1 }

    -- 1.3.6.1.4.1.2011.2.25.4.40.4.10.170
    optixRtnRfuIndexTable OBJECT-TYPE
        SYNTAX SEQUENCE OF OptixRtnRfuIndexEntry
        MAX-ACCESS not-accessible
        STATUS current
        DESCRIPTION
            "Serves as the public index table for attribute tables related to an RFU."
        ::= { optixODU 170 }

    -- 1.3.6.1.4.1.2011.2.25.4.40.4.10.170.1
    optixRtnRfuIndexEntry OBJECT-TYPE
        SYNTAX OptixRtnRfuIndexEntry
        MAX-ACCESS not-accessible
        STATUS current
        DESCRIPTION
            "Indicates the index entry for an RFU."
        INDEX{ optixRtnRFUBid,optixRtnRFUSubCardId }
        ::= { optixRtnRfuIndexTable 1 }

    OptixRtnRfuIndexEntry ::=
        SEQUENCE {
            optixRtnRFUBid
                Unsigned32,
            optixRtnRFUSubCardId
                Unsigned32
        }

    -- 1.3.6.1.4.1.2011.2.25.4.40.4.10.170.1.1
    optixRtnRFUBid OBJECT-TYPE
        SYNTAX Unsigned32
        MAX-ACCESS not-accessible
        STATUS current
        DESCRIPTION
            "Indicates the RFU board ID."
        ::= { optixRtnRfuIndexEntry 1 }

    -- 1.3.6.1.4.1.2011.2.25.4.40.4.10.170.1.2
    optixRtnRFUSubCardId OBJECT-TYPE
        SYNTAX Unsigned32
        MAX-ACCESS not-accessible
        STATUS current
        DESCRIPTION
            "Indicates the subboard ID."
        ::= { optixRtnRfuIndexEntry 2 }

    -- 1.3.6.1.4.1.2011.2.25.4.40.4.10.190
 	optixRtnFlapLinkDownTable OBJECT-TYPE
		SYNTAX SEQUENCE OF OptixRtnFlapLinkDownEntry
	MAX-ACCESS not-accessible
        STATUS current
        DESCRIPTION
            "Indicates the flapping-linkdown state."
        ::= { optixODU 190}
		
	-- 1.3.6.1.4.1.2011.2.25.4.40.4.10.190.1
    optixRtnFlapLinkDownEntry OBJECT-TYPE
        SYNTAX OptixRtnFlapLinkDownEntry
        MAX-ACCESS not-accessible
        STATUS current
        DESCRIPTION
            "Indicates the flapping-linkdown state."
        INDEX{ optixRtnOduIndex1,optixRtnOduIndex2,optixRtnOduIndex3 }
        ::= { optixRtnFlapLinkDownTable 1 }
		
	OptixRtnFlapLinkDownEntry ::=
		SEQUENCE {
		optixRtnOduFlapLinkDownStatus
			Unsigned32,
		optixRtnOduFlapLinkDownChecktime
			Unsigned32,
		optixRtnOduFlapLinkDownFrequency
			Unsigned32,
		optixRtnOduFlapLinkRecoveryTime	
			Unsigned32
		}
		
	-- 1.3.6.1.4.1.2011.2.25.4.40.4.10.190.1.1
    optixRtnOduFlapLinkDownStatus OBJECT-TYPE
        SYNTAX Unsigned32
        {
            disable(0),
	    enable(1)
        }
        MAX-ACCESS read-write
        STATUS current
        DESCRIPTION
            "Indicates the flapping-linkdown status,it has two mode type:disable(0),enable(1)."
        ::= { optixRtnFlapLinkDownEntry 1 }
		
    -- 1.3.6.1.4.1.2011.2.25.4.40.4.10.190.1.2
    optixRtnOduFlapLinkDownChecktime OBJECT-TYPE
        SYNTAX Unsigned32
        MAX-ACCESS read-write
        STATUS current
        DESCRIPTION
            "Indicates the check time of flapping-linkdown,enable:30~180,disable:0.Unit:second."
        ::= { optixRtnFlapLinkDownEntry 2 }	
	
    -- 1.3.6.1.4.1.2011.2.25.4.40.4.10.190.1.3
    optixRtnOduFlapLinkDownFrequency OBJECT-TYPE
        SYNTAX Unsigned32
        MAX-ACCESS read-write
        STATUS current
        DESCRIPTION
            "Indicates the freqency of turnning off threshold, enable:3~30,disable:0."
        ::= { optixRtnFlapLinkDownEntry 3 }		

    -- 1.3.6.1.4.1.2011.2.25.4.40.4.10.190.1.4
    optixRtnOduFlapLinkRecoveryTime OBJECT-TYPE
        SYNTAX Unsigned32
        MAX-ACCESS read-write
        STATUS current
        DESCRIPTION
            "Indicates the recoveryTime of flapping-linkdown, enable:0~30,0 represents not automatically recovery,disable:0.Unit:minute."
        ::= { optixRtnFlapLinkDownEntry 4 }		
	
	
    -- 1.3.6.1.4.1.2011.2.25.4.40.4.10.101
    optixRtnOduInfoTable OBJECT-TYPE
        SYNTAX SEQUENCE OF OptixRtnOduInfoEntry
        MAX-ACCESS not-accessible
        STATUS current
        DESCRIPTION
            "Describes ODU information."
        ::= { optixODU 101}

    -- 1.3.6.1.4.1.2011.2.25.4.40.4.10.101.1
    optixRtnOduInfoEntry OBJECT-TYPE
        SYNTAX OptixRtnOduInfoEntry
        MAX-ACCESS not-accessible
        STATUS current
        DESCRIPTION
            "Indicates an ODU information entry."
        INDEX{ optixRtnOduIndex1,optixRtnOduIndex2 }
        ::= { optixRtnOduInfoTable 1 }

    OptixRtnOduInfoEntry ::=
        SEQUENCE {
            optixRtnOduFreqBand
                Unsigned32,
            optixRtnOduDeviceType
                INTEGER,
            optixRtnOduTRSpacing
                Unsigned32,
            optixRtnOduIFBandWidth
                Unsigned32,
            optixRtnOduIFBandWidthType
                INTEGER,
            optixRtnOduHighorLowStation
                INTEGER,
            optixRtnOduPowerType
                INTEGER,
            optixRtnOduFactoryCode
                Unsigned32,
            optixRtnOduProducedYear
                Unsigned32,
            optixRtnOduProducedMonth
                Unsigned32,
            optixRtnOduSNCode
                Unsigned32
        }

    -- 1.3.6.1.4.1.2011.2.25.4.40.4.10.101.1.1
    optixRtnOduFreqBand OBJECT-TYPE
        SYNTAX Unsigned32
        MAX-ACCESS read-only
        STATUS current
        DESCRIPTION
            "Indicates the frequency band, expressed in GHz."
        ::= { optixRtnOduInfoEntry 1 }

    -- 1.3.6.1.4.1.2011.2.25.4.40.4.10.101.1.2
    optixRtnOduDeviceType OBJECT-TYPE
        SYNTAX INTEGER
        {
            highcapacity(5),
            lowcapacity(10),
            rfu(11),
            rfuSd(12),
            xmc3(13),
            xmc3w(14)
        }
        MAX-ACCESS read-only
        STATUS current
        DESCRIPTION
            "Indicates the ODU device type:
				10-Low Capacity
				5-High Capacity
				11-RFU
				12-RFU-SD
				13-XMC-3
				14-XMC-3W"
        ::= { optixRtnOduInfoEntry 2 }

    -- 1.3.6.1.4.1.2011.2.25.4.40.4.10.101.1.3
    optixRtnOduTRSpacing OBJECT-TYPE
        SYNTAX Unsigned32
        MAX-ACCESS read-only
        STATUS current
        DESCRIPTION
            "Indicates the T/R spacing, expressed in kHz."
        ::= { optixRtnOduInfoEntry 3 }

    -- 1.3.6.1.4.1.2011.2.25.4.40.4.10.101.1.4
    optixRtnOduIFBandWidth OBJECT-TYPE
        SYNTAX Unsigned32
	{
		bw7(7),
		bw14(14),
		bw28(28),
		bw40(40),
		bw56(56),
		bw112(112),           
		bw250(150),
		bw500(151),
		bw750(152),
		bw125(153),
		bw62p5(154),
		bw200(155)
	}
        MAX-ACCESS read-only
        STATUS current
        DESCRIPTION
            "Indicates the supported IF bandwidth. 
If the value is between 0 and 149, it indicates the actual bandwidth in the unit of MHz.
If the value is between 150 and 255, it indicates a mapping index. You need calculate the actual bandwidth using the mapping index. For details about the mapping index, see the remarks."
        ::= { optixRtnOduInfoEntry 4 }

    -- 1.3.6.1.4.1.2011.2.25.4.40.4.10.101.1.5
    optixRtnOduIFBandWidthType OBJECT-TYPE
        SYNTAX INTEGER
        {
            fixed(0),
            max(1),
            zero(-1)
        }
        MAX-ACCESS read-only
        STATUS current
        DESCRIPTION
            "Indicates whether the supported IF bandwidth is variable. The values are as follows: 
				0: fixed
				1: variable"
        ::= { optixRtnOduInfoEntry 5 }

    -- 1.3.6.1.4.1.2011.2.25.4.40.4.10.101.1.6
    optixRtnOduHighorLowStation OBJECT-TYPE
        SYNTAX INTEGER
        {
            txLow(5),
            txHigh(10),
	    zero(0)
        }
        MAX-ACCESS read-only
        STATUS current
        DESCRIPTION
            "Indicates whether a station is high or low station.
				5: Tx-Low (low station)
				10: Tx-High (high station)
				0: undifferentiated"
        ::= { optixRtnOduInfoEntry 6 }

    -- 1.3.6.1.4.1.2011.2.25.4.40.4.10.101.1.7
    optixRtnOduPowerType OBJECT-TYPE
        SYNTAX INTEGER
        {
            standard(5),
            high(10)
        }
        MAX-ACCESS read-only
        STATUS current
        DESCRIPTION
            "Indicates the transmit power type of an ODU.
5: standard output power
10: high output power"
        ::= { optixRtnOduInfoEntry 7 }

    -- 1.3.6.1.4.1.2011.2.25.4.40.4.10.101.1.8
    optixRtnOduFactoryCode OBJECT-TYPE
        SYNTAX Unsigned32
        MAX-ACCESS read-only
        STATUS current
        DESCRIPTION
            "Indicates the vendor code."
        ::= { optixRtnOduInfoEntry 8 }

    -- 1.3.6.1.4.1.2011.2.25.4.40.4.10.101.1.9
    optixRtnOduProducedYear OBJECT-TYPE
        SYNTAX Unsigned32
        MAX-ACCESS read-only
        STATUS current
        DESCRIPTION
            "Indicates the manufacture year."
        ::= { optixRtnOduInfoEntry 9 }

    -- 1.3.6.1.4.1.2011.2.25.4.40.4.10.101.1.10
    optixRtnOduProducedMonth OBJECT-TYPE
        SYNTAX Unsigned32
        MAX-ACCESS read-only
        STATUS current
        DESCRIPTION
            "Indicates the manufacture month."
        ::= { optixRtnOduInfoEntry 10 }

    -- 1.3.6.1.4.1.2011.2.25.4.40.4.10.101.1.11
    optixRtnOduSNCode OBJECT-TYPE
        SYNTAX Unsigned32
        MAX-ACCESS read-only
        STATUS current
        DESCRIPTION
            "Indicates the production sequence number."
        ::= { optixRtnOduInfoEntry 11 }
END
