-- ===================================================================
-- Copyright (C) 2024 by HUAWEI TECHNOLOGIES. All rights reserved.
-- Description: 
-- Reference:
-- Version: V1.00
-- ===================================================================


    HUAWEI-RMON-EXT-MIB DEFINITIONS ::= BEGIN
 
        IMPORTS                                            
            OBJECT-GROUP, MODULE-COMPLIANCE, NOTIFICATION-GROUP            
                FROM SNMPv2-CONF            
            DisplayString, RowStatus                        
                FROM SNMPv2-TC
            TimeTicks, Integer32, Unsigned32, IpAddress, Counter32, OBJECT-TYPE, 
            MODULE-IDENTITY, NOTIFICATION-TYPE            
                FROM SNMPv2-SMI
            hwDatacomm            
                FROM HUAWEI-MIB
            OwnerString, EntryStatus
                FROM RMON-MIB;
    
    
        hwRmonExt MODULE-IDENTITY 
            LAST-UPDATED "202404261600Z"        
            ORGANIZATION 
                  "Huawei Technologies Co.,Ltd."
            CONTACT-INFO 
                  "Huawei Industrial Base
  Bantian, Longgang
   Shenzhen 518129
   People's Republic of China
   Website: http://www.huawei.com
   Email: support@huawei.com
 "
            DESCRIPTION 
                "Please provide the descritpion."
            REVISION    "202404261600Z"   
            DESCRIPTION "V1.00, initial version."
    
            ::= { hwDatacomm 377 }

-- 1.3.6.1.4.1.2011.5.25.377.1
     hwRmonEventsV2 OBJECT IDENTIFIER ::= { hwRmonExt 1 }

-- 1.3.6.1.4.1.2011.5.25.377.1.1
     hwRisingAlarm NOTIFICATION-TYPE
       OBJECTS { hwRmonAlarmIndex, hwRmonAlarmVariable, hwRmonAlarmSampleType, hwRmonAlarmValue, hwRmonAlarmRisingThreshold }
       STATUS current
       DESCRIPTION
         "The SNMP trap that is generated when an alarm entry
          crosses its rising threshold extended 64bit value and
          generates an event that is configured for sending SNMP
          traps."
       ::= { hwRmonEventsV2 1 }

-- 1.3.6.1.4.1.2011.5.25.377.1.2
     hwFallingAlarm NOTIFICATION-TYPE
       OBJECTS { hwRmonAlarmIndex, hwRmonAlarmVariable, hwRmonAlarmSampleType, hwRmonAlarmValue, hwRmonAlarmFallingThreshold }
       STATUS current
       DESCRIPTION
         "The SNMP trap that is generated when an alarm entry
          crosses its falling threshold extended 64 bits value and
          generates an event that is configured for sending SNMP
          traps."
       ::= { hwRmonEventsV2 2 }

-- 1.3.6.1.4.1.2011.5.25.377.2
     hwRmonAlarmTable     OBJECT-TYPE
        SYNTAX        SEQUENCE OF HwRmonAlarmEntry
        MAX-ACCESS    not-accessible
        STATUS        current
        DESCRIPTION
            "A list of rmon alarm entries with 64 bits value."
        ::= { hwRmonExt 2 }

-- 1.3.6.1.4.1.2011.5.25.377.2.1
     hwRmonAlarmEntry     OBJECT-TYPE
        SYNTAX        HwRmonAlarmEntry
        MAX-ACCESS    not-accessible
        STATUS        current
        DESCRIPTION   
            "A list of parameters that set up a periodic checking
             for rmon alarm conditions. For example, an instance of the
             hwRmonAlarmValue object might be named hwRmonAlarmValue.8"
        INDEX         {
                        hwRmonAlarmIndex
                      }
        ::= { hwRmonAlarmTable 1 }

     HwRmonAlarmEntry ::= SEQUENCE
        {
          hwRmonAlarmIndex                    Integer32,
          hwRmonAlarmInterval                 Integer32,
          hwRmonAlarmVariable                 OBJECT IDENTIFIER,
          hwRmonAlarmSampleType               INTEGER,
          hwRmonAlarmValue                    Counter64,
          hwRmonAlarmStartupAlarm             INTEGER,
          hwRmonAlarmRisingThreshold          Counter64,
          hwRmonAlarmFallingThreshold         Counter64,
          hwRmonAlarmRisingEventIndex         Integer32,
          hwRmonAlarmFallingEventIndex        Integer32,
          hwRmonAlarmOwner                    OwnerString,
          hwRmonAlarmStatus                   EntryStatus
        }

-- 1.3.6.1.4.1.2011.5.25.377.2.1.1
     hwRmonAlarmIndex     OBJECT-TYPE
        SYNTAX        Integer32 (1..65535)
        MAX-ACCESS    read-only
        STATUS        current
        DESCRIPTION
            "An index that uniquely identifies an entry in the
            alarm table.  Each such entry defines a
            diagnostic sample at a particular interval
            for an object on the device."
        ::= { hwRmonAlarmEntry 1 }

-- 1.3.6.1.4.1.2011.5.25.377.2.1.2
     hwRmonAlarmInterval    OBJECT-TYPE
        SYNTAX          Integer32
        UNITS           "Seconds"
        MAX-ACCESS      read-create
        STATUS          current
        DESCRIPTION
            "The interval in seconds over which the data is
            sampled and compared with the rising and falling
            thresholds.  When setting this variable, care
            should be taken in the case of deltaValue
            sampling - the interval should be set short enough
            that the sampled variable is very unlikely to
            increase or decrease by more than 2^31 - 1 during
            a single sampling interval.
            
            This object may not be modified if the associated
            alarmStatus object is equal to valid(1)."
        ::= { hwRmonAlarmEntry 2 }

-- 1.3.6.1.4.1.2011.5.25.377.2.1.3
     hwRmonAlarmVariable    OBJECT-TYPE
        SYNTAX          OBJECT IDENTIFIER
        MAX-ACCESS      read-create
        STATUS          current
        DESCRIPTION
            "The object identifier of the particular variable to be
            sampled.  Only variables that resolve to an ASN.1 primitive
            type of INTEGER (INTEGER, Integer32, Counter32, Counter64,
            Gauge, or TimeTicks) may be sampled.
            
            Because SNMP access control is articulated entirely
            in terms of the contents of MIB views, no access
            control mechanism exists that can restrict the value of
            this object to identify only those objects that exist
            in a particular MIB view.  Because there is thus no
            acceptable means of restricting the read access that
            could be obtained through the alarm mechanism, the
            probe must only grant write access to this object in
            those views that have read access to all objects on
            the probe.
            
            During a set operation, if the supplied variable name is
            not available in the selected MIB view, a badValue error
            must be returned.  If at any time the variable name of
            an established alarmEntry is no longer available in the
            selected MIB view, the probe must change the status of
            this alarmEntry to invalid(4).
            
            This object may not be modified if the associated
            alarmStatus object is equal to valid(1)."
        ::= { hwRmonAlarmEntry 3 }

-- 1.3.6.1.4.1.2011.5.25.377.2.1.4
     hwRmonAlarmSampleType  OBJECT-TYPE
        SYNTAX          INTEGER {
                                  absoluteValue(1),
                                  deltaValue(2)
                                }
        MAX-ACCESS      read-create
        STATUS          current
        DESCRIPTION
            "The method of sampling the selected variable and
            calculating the value to be compared against the
            thresholds.  If the value of this object is
            absoluteValue(1), the value of the selected variable
            will be compared directly with the thresholds at the
            end of the sampling interval.  If the value of this
            object is deltaValue(2), the value of the selected
            variable at the last sample will be subtracted from
            the current value, and the difference compared with
            the thresholds.
            
            This object may not be modified if the associated
            alarmStatus object is equal to valid(1)."
        ::= { hwRmonAlarmEntry 4 }

-- 1.3.6.1.4.1.2011.5.25.377.2.1.5
     hwRmonAlarmValue       OBJECT-TYPE
        SYNTAX          Counter64
        MAX-ACCESS      read-only
        STATUS          current
        DESCRIPTION
            "The value of the statistic during the last sampling
            period.  For example, if the sample type is deltaValue,
            this value will be the difference between the samples
            at the beginning and end of the period.  If the sample
            type is absoluteValue, this value will be the sampled
            value at the end of the period.
            This is the value that is compared with the rising and
            falling thresholds.
            
            The value during the current sampling period is not
            made available until the period is completed and will
            remain available until the next period completes."
        ::= { hwRmonAlarmEntry 5 }

-- 1.3.6.1.4.1.2011.5.25.377.2.1.6
     hwRmonAlarmStartupAlarm    OBJECT-TYPE
        SYNTAX              INTEGER {
                                      risingAlarm(1),
                                      fallingAlarm(2),
                                      risingOrFallingAlarm(3)
                                    }
        MAX-ACCESS          read-create
        STATUS              current
        DESCRIPTION
            "The alarm that may be sent when this entry is first
            set to valid.  If the first sample after this entry
            becomes valid is greater than or equal to the
            risingThreshold and alarmStartupAlarm is equal to
            risingAlarm(1) or risingOrFallingAlarm(3), then a single
            rising alarm will be generated.  If the first sample
            after this entry becomes valid is less than or equal
            to the fallingThreshold and alarmStartupAlarm is equal
            to fallingAlarm(2) or risingOrFallingAlarm(3), then a
            single falling alarm will be generated.
            
            This object may not be modified if the associated
            alarmStatus object is equal to valid(1)."
        ::= { hwRmonAlarmEntry 6 }

-- 1.3.6.1.4.1.2011.5.25.377.2.1.7
     hwRmonAlarmRisingThreshold    OBJECT-TYPE
        SYNTAX                 Counter64
        MAX-ACCESS             read-create
        STATUS                 current
        DESCRIPTION
            "A threshold for the sampled statistic.  When the current
            sampled value is greater than or equal to this threshold,
            and the value at the last sampling interval was less than
            this threshold, a single event will be generated.
            A single event will also be generated if the first
            sample after this entry becomes valid is greater than or
            equal to this threshold and the associated
            alarmStartupAlarm is equal to risingAlarm(1) or
            risingOrFallingAlarm(3).
            
            After a rising event is generated, another such event
            will not be generated until the sampled value
            falls below this threshold and reaches the
            alarmFallingThreshold.
            
            This object may not be modified if the associated
            alarmStatus object is equal to valid(1)."
        ::= { hwRmonAlarmEntry 7 }

-- 1.3.6.1.4.1.2011.5.25.377.2.1.8
     hwRmonAlarmFallingThreshold   OBJECT-TYPE
        SYNTAX                 Counter64
        MAX-ACCESS             read-create
        STATUS                 current
        DESCRIPTION
            "A threshold for the sampled statistic.  When the current
            sampled value is less than or equal to this threshold,
            and the value at the last sampling interval was greater than
            this threshold, a single event will be generated.
            A single event will also be generated if the first
            sample after this entry becomes valid is less than or
            equal to this threshold and the associated
            alarmStartupAlarm is equal to fallingAlarm(2) or
            risingOrFallingAlarm(3).
            
            After a falling event is generated, another such event
            will not be generated until the sampled value
            rises above this threshold and reaches the
            alarmRisingThreshold.
            
            This object may not be modified if the associated
            alarmStatus object is equal to valid(1)."
        ::= { hwRmonAlarmEntry 8 }

-- 1.3.6.1.4.1.2011.5.25.377.2.1.9
     hwRmonAlarmRisingEventIndex   OBJECT-TYPE
        SYNTAX                 Integer32 (0..65535)
        MAX-ACCESS             read-create
        STATUS                 current
        DESCRIPTION
            "The index of the eventEntry that is
            used when a rising threshold is crossed.  The
            eventEntry identified by a particular value of
            this index is the same as identified by the same value
            of the eventIndex object.  If there is no
            corresponding entry in the eventTable, then
            no association exists.  In particular, if this value
            is zero, no associated event will be generated, as
            zero is not a valid event index.
            
            This object may not be modified if the associated
            alarmStatus object is equal to valid(1)."
        ::= { hwRmonAlarmEntry 9 }

-- 1.3.6.1.4.1.2011.5.25.377.2.1.10
     hwRmonAlarmFallingEventIndex  OBJECT-TYPE
        SYNTAX                 Integer32 (0..65535)
        MAX-ACCESS             read-create
        STATUS                 current
        DESCRIPTION
            "The index of the eventEntry that is
            used when a falling threshold is crossed.  The
            eventEntry identified by a particular value of
            this index is the same as identified by the same value
            of the eventIndex object.  If there is no
            corresponding entry in the eventTable, then
            no association exists.  In particular, if this value
            is zero, no associated event will be generated, as
            zero is not a valid event index.
            
            This object may not be modified if the associated
            alarmStatus object is equal to valid(1)."
        ::= { hwRmonAlarmEntry 10 }

-- 1.3.6.1.4.1.2011.5.25.377.2.1.11
     hwRmonAlarmOwner         OBJECT-TYPE
        SYNTAX            OwnerString
        MAX-ACCESS        read-create
        STATUS            current
        DESCRIPTION
            "The entity that configured this entry and is therefore
            using the resources assigned to it."
        ::= { hwRmonAlarmEntry 11 }

-- 1.3.6.1.4.1.2011.5.25.377.2.1.12
     hwRmonAlarmStatus        OBJECT-TYPE
        SYNTAX            EntryStatus
        MAX-ACCESS        read-create
        STATUS            current
        DESCRIPTION
            "The status of this alarm entry."
        ::= { hwRmonAlarmEntry 12 }

     END
--
-- HUAWEI-RMON-EXT-MIB.mib
--
