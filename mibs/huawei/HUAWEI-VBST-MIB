-- =================================================================
-- Copyright (C) 2015 by HUAWEI TECHNOLOGIES. All rights reserved
-- 
-- Description: VBST huawei mib define
-- Reference: VBST 
-- Version: V1.01
-- History:
--    <zongchao 00240494>,<2013.09.29>,<create>
-- =================================================================
         
HUAWEI-VBST-MIB DEFINITIONS ::= BEGIN

    IMPORTS
        hwDatacomm            
            FROM HUAWEI-MIB
        OBJECT-GROUP, NOTIFICATION-GROUP, MODULE-COMPLIANCE
            FROM SNMPv2-CONF            
        OBJECT-TYPE, MODULE-IDENTITY, OBJECT-IDENTITY, NOTIFICATION-TYPE, Integer32
            FROM SNMPv2-SMI                
        entPhysicalName
      	    FROM ENTITY-MIB;
 
    hwVbstMIB MODULE-IDENTITY 
            LAST-UPDATED "201511181410Z"        
            ORGANIZATION 
                  "Huawei Technologies Co.,Ltd."
            CONTACT-INFO 
                  "Huawei Industrial Base
				   Bantian, Longgang
				   Shenzhen 518129
				   People's Republic of China
				   Website: http://www.huawei.com
				   Email: support@huawei.com
				  "
            DESCRIPTION 
                "Please provide the descritpion."

            REVISION    "201511181410Z"   
            DESCRIPTION "V1.01, Updated to include support for VBST."

            REVISION    "201008111600Z"   
            DESCRIPTION "V1.00, initial version."
    
            ::= { hwDatacomm 323 }

    
-- Top-level structure of the MIB

hwVbstObjects        OBJECT IDENTIFIER ::= { hwVbstMIB 1 }
hwVbstNotifications  OBJECT IDENTIFIER ::= { hwVbstMIB 2 }
hwVbstConformance    OBJECT IDENTIFIER ::= { hwVbstMIB 3 }

--MIB Objects
   
   hwVbstMaxTrunkNum OBJECT-TYPE
       SYNTAX      Integer32 (0..65535)
       MAX-ACCESS  accessible-for-notify
       STATUS      current
       DESCRIPTION
           "The max number of the Eth-Trunk port."
       ::= { hwVbstObjects 1 }
       
   hwVbstMaxPVNum OBJECT-TYPE
       SYNTAX      Integer32 (0..65535)
       MAX-ACCESS  accessible-for-notify
       STATUS      current
       DESCRIPTION
           "The max number of the Port-Vlan."
       ::= { hwVbstObjects 2 }

   hwVbstMaxVlanNum  OBJECT-TYPE
       SYNTAX      Integer32 (0..65535)
       MAX-ACCESS  accessible-for-notify
       STATUS      current
       DESCRIPTION
           "The max number of VLANs running VBST."
       ::= { hwVbstObjects 3 }

               
-- Notifications

    hwVbstTrunkNumExceeded NOTIFICATION-TYPE
    	OBJECTS { hwVbstMaxTrunkNum }
        STATUS current
        DESCRIPTION 
            "Trap message is generated by VBST node when 
            it detects that number of trunk ports has exceeded the specification limit."
        ::= { hwVbstNotifications 1 }
    
     hwVbstTrunkNumResumed NOTIFICATION-TYPE
    	OBJECTS { hwVbstMaxTrunkNum }
        STATUS current
        DESCRIPTION 
            "Trap message is generated by VBST node when 
            it detects that the number of trunk ports has resumed below 95% of the specification limit."
        ::= { hwVbstNotifications 2 }
        
    hwVbstPVNumExceeded NOTIFICATION-TYPE
        OBJECTS { entPhysicalName, hwVbstMaxPVNum }
        STATUS current
        DESCRIPTION 
            "Trap message is generated by VBST node when 
            it detects that the number of PortVlan has exceeded the specification limit."
        ::= { hwVbstNotifications 3 }        

    hwVbstPVNumResumed NOTIFICATION-TYPE
        OBJECTS { entPhysicalName, hwVbstMaxPVNum }
        STATUS current
        DESCRIPTION 
            "Trap message is generated by VBST node when 
            it detects that the number of PortVlan has resumed below 95% of the specification limit."
        ::= { hwVbstNotifications 4 }

    hwVbstVlanNumExceeded NOTIFICATION-TYPE
        OBJECTS { hwVbstMaxVlanNum  }
        STATUS current
        DESCRIPTION 
            "Trap message is generated by VBST node when 
            it detects that the number of VLANs running VBST has exceeded the specification limit."
        ::= { hwVbstNotifications 5 }        

    hwVbstVlanNumResumed NOTIFICATION-TYPE
        OBJECTS { hwVbstMaxVlanNum  }
        STATUS current
        DESCRIPTION 
            "Trap message is generated by VBST node when 
            it detects that the number of VLANs running VBST has resumed below 95% of the specification limit."
        ::= { hwVbstNotifications 6 }


-- Conformance

    hwVbstGroups OBJECT IDENTIFIER ::= { hwVbstConformance 1 }
    
    hwVbstObjectGroup OBJECT-GROUP
        OBJECTS { hwVbstMaxTrunkNum, hwVbstMaxPVNum, hwVbstMaxVlanNum }
        STATUS current
        DESCRIPTION 
            "The object group."
        ::= { hwVbstGroups 1 }
        
    hwVbstNotificationGroup NOTIFICATION-GROUP
        NOTIFICATIONS { hwVbstTrunkNumExceeded, hwVbstTrunkNumResumed, hwVbstPVNumExceeded, hwVbstPVNumResumed, 
                                         hwVbstVlanNumExceeded, hwVbstVlanNumResumed }
        STATUS current
        DESCRIPTION 
            "The notification group."
        ::= { hwVbstGroups 2 }        
        
    hwVbstCompliances OBJECT IDENTIFIER ::= { hwVbstConformance 2 }
                    
    hwVbstCompliance MODULE-COMPLIANCE
	STATUS current
	DESCRIPTION
            "The core compliance statement for all implementations."
	MODULE -- this module
	MANDATORY-GROUPS  {
		hwVbstObjectGroup, hwVbstNotificationGroup  		            		            		            
	    }
	    ::= { hwVbstCompliances 1 }

END
