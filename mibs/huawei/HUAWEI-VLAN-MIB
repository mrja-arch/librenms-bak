-- ============================================================================
-- Copyright (C) 2025 by  HUAWEI TECHNOLOGIES. All rights reserved.
-- Description:  The mib is used for configuring the information of the VLAN, including
--               VLAN management, VLAN interface, VLAN aggregation and so on.
-- Reference:
-- Version: V4.05
--
-- ============================================================================

  HUAWEI-VLAN-MIB DEFINITIONS ::= BEGIN

       IMPORTS
           hwFrameIndex, hwSlotIndex, hwConfigChangeIP
               FROM HUAWEI-DEVICE-MIB
           huaweiMgmt
               FROM HUAWEI-MIB
           ifIndex
               FROM IF-MIB
           Ipv6Address
               FROM IPV6-TC
           TimeTicks, IpAddress, Integer32, Unsigned32, Counter64,OBJECT-TYPE,
           MODULE-IDENTITY, OBJECT-IDENTITY, NOTIFICATION-TYPE
               FROM SNMPv2-SMI
           TruthValue, RowStatus, TEXTUAL-CONVENTION, MacAddress
               FROM SNMPv2-TC;

       hwVlan MODULE-IDENTITY
           LAST-UPDATED "202502100000Z"
           ORGANIZATION
               "Huawei Technologies Co.,Ltd."
           CONTACT-INFO
               "Huawei Industrial Base
                Bantian, Longgang
                Shenzhen 518129
                People's Republic of China
                Website: http://www.huawei.com
                Email: support@huawei.com
               "
           DESCRIPTION
               "The mib is used for configuring the information of the VLAN, including
                VLAN management, VLAN interface, VLAN aggregation and so on."

           -- Revision history
           REVISION    "202502100000Z"
           DESCRIPTION "V4.05, modify the description of table node hwVlanInterfaceTable and hwVlanInterfaceSubIpAddrTable."

           REVISION    "202406200000Z"
           DESCRIPTION "V4.04, add table node hwVlanTlsTable."

           REVISION    "202306190000Z"
           DESCRIPTION "V4.03, modified the value range of leaf node hwVlanIfDhcpsStaBindDesc in
                        HwVlanIfDhcpsStaBindEntry."

           REVISION    "202212240000Z"
           DESCRIPTION "V4.02, fix index nodes read-only properties."

           REVISION    "202209220000Z"
           DESCRIPTION "V4.01, added table node hwVlanIfDhcp6sCfgTable, hwVlanIfDhcp6sPrefixTable,
                        hwVlanIfDhcp6sDnsTable, hwVlanIfDhcp6sDomainTable, hwVlanIfDhcp6sExcIPTable,
                        hwVlanIfDhcp6sPDTable, hwVlanIfDhcp6sOptionTable, hwVlanIfDhcp6sIpInUseTable,
                        hwVlanIfDhcp6sPdInUseTable, hwVlanIfDhcpsOption121Table."

           REVISION    "202204280000Z"
           DESCRIPTION "V4.00, added table node hwVlanIfDhcpsDomainTable, hwVlanIfDhcpsExclIpTable,
                        hwVlanIfDhcpsStaBindTable, hwVlanIfDhcpsIpInUseTable.
                        Added leaf nodes hwVlanIfDhcpsDns, hwVlanIfDhcpsDnsUndo."

           REVISION    "202203010000Z"
           DESCRIPTION "V3.99, added table node hwVlanIfDhcpsOptionTable."

           REVISION    "202202240000Z"
           DESCRIPTION "V3.98, add hwDedicatedNetwork to traps hwVlanNameChangeInfoTrap, hwVlanForwardingModeInfoTrap,
                        hwVlanAndVlanSrvProfOperInfoTrap, hwVlanAddInfoTrap, hwVlanDelInfoTrap,
                        hwVlanAttrChangedInfoTrap, hwPortVlanChangedInfoTrap."

           REVISION    "202201121000Z"
           DESCRIPTION "V3.97, modified the description of leaf node hwVlanIfDhcpsSubOptCode in HwVlanInterfaceEntry."

           REVISION    "202112031000Z"
           DESCRIPTION "V3.96, modified the value range of leaf nodes hwVlanIfDhcpsLeaseDay, hwVlanIfDhcpsLeaseHour,
                        hwVlanIfDhcpsLeaseMinute in HwVlanInterfaceEntry."

           REVISION    "202111011000Z"
           DESCRIPTION "V3.95, modified the value range of hwVlanIndex, hwVlanAggregationSuperVlanId, hwVlanAggregationSubVlanId, hwVlanConnectOuterVlanID."	   

           REVISION    "202110281000Z"
           DESCRIPTION "V3.94, A leaf node name was changed from hwVlanIfDHCPSStatus to hwVlanIfDhcpsStatus.
                        Added leaf nodes hwVlanIfDhcpsLeaseMode, hwVlanIfDhcpsLeaseDay, hwVlanIfDhcpsLeaseHour,
                        hwVlanIfDhcpsLeaseMinute, hwVlanIfDhcpsStartIpAddr, hwVlanIfDhcpsEndIpAddr, hwVlanIfDhcpsMask,
                        hwVlanIfDhcpsGateway, hwVlanIfDhcpsGatewayUndo, hwVlanIfDhcpsOption, hwVlanIfDhcpsOptCode,
                        hwVlanIfDhcpsSubOptCode, hwVlanIfDhcpsOptType and hwVlanIfDhcpsOptStr in HwVlanInterfaceEntry."

           REVISION    "202109101000Z"
           DESCRIPTION "V3.93, added table node hwPacketVlanSwitchPortTable and hwPacketVlanSwitchRuleTable."

           REVISION    "202108091000Z"
           DESCRIPTION "V3.92, Modify the node type of hwVlanConnectSrcPara."

           REVISION    "202106181000Z"
           DESCRIPTION "V3.91, added leaf node hwVlanPortsExtendFrame."

           REVISION    "202001211000Z"
           DESCRIPTION "V3.90, Added hwDhcpOption82CaptureArpSwitch, hwDhcpv6OptionCaptureNaSwitch."

           REVISION    "201901161000Z"
           DESCRIPTION "V3.89, modified the value range of hwVOIPAddressIndex."
	   
           REVISION    "201803211000Z"
           DESCRIPTION "V3.88, modified the description of hwPortVlanOuterEthernetTypeTable and hwPortVlanOuterEthernetTypeEntry."

           REVISION    "201711101000Z"
           DESCRIPTION "V3.87, Added hwArpDetectMaxUserCountSwitch in hwVlanSrvProfTable."
		   
           REVISION    "201608301000Z"
           DESCRIPTION "V3.86, modified the value range and description of hwIPv6MTU and hwIPv4MTU."

           REVISION    "201605281000Z"
           DESCRIPTION "V3.85, Added hwAntiMacDuplicateSwitch in hwVlanSrvProfTable."

           REVISION    "201511101000Z"
           DESCRIPTION "V3.84, Added hwPortVlanOuterEthernetTypeTable in hwVlanMngObject."

           REVISION    "201508071000Z"
           DESCRIPTION "V3.83, modified the value range and description of hwIPv6MTU."

           REVISION    "201504130000Z"
           DESCRIPTION "V3.82, modify the description of hwUpFlowAccountByte, hwDownFlowAccountByte, hwUpFlowAccountPacket, hwDownFlowAccountPacket,
                        hwUpStreamPacket, hwDownStreamPacket, hwUpFlowAccountDiscardPacket, hwDownFlowAccountDiscardPacket."

           REVISION    "201501221000Z"
           DESCRIPTION "V3.81, Added hwCableIPv6SourceVerify in hwVlanSrvProfTable."
           
           REVISION    "201412241000Z"
           DESCRIPTION "V3.80, Added hwMethNativeVlan in hwVlanMngObject."
	   
           REVISION    "201412231000Z"
           DESCRIPTION "V3.79, modified the description of hwRegionPVCRowStatus, hwProfileRowStatus, hwVlanConnectRowStatus and hwDocsSrvVlanRowStatus."
       
           REVISION    "201411241000Z"
           DESCRIPTION "V3.78, modified the description of hwVlanMethL2Forward."
                      
           REVISION    "201411131000Z"
           DESCRIPTION "V3.77, Added hwVlanMethL2Forward in hwVlanSrvProfTable."
		                
           REVISION    "201409261000Z"
           DESCRIPTION "V3.76, Added hwRouterRedirectReverse in hwVlanSrvProfTable and.
		                modified the description of hwVlanInterfaceLinkStatus."

           REVISION    "201408301000Z"
           DESCRIPTION "V3.75, modified the value range and description of hwVlanIndex."

           REVISION    "201408151000Z"
           DESCRIPTION "V3.74, modified the description of hwVlanifUpTrap and hwVlanifDownTrap."
           
	   REVISION    "201407201000Z"
           DESCRIPTION "V3.73, added hwIPv4MTU."
	   
           REVISION    "201406231000Z"
           DESCRIPTION "V3.72, modified the option of hwUserBridging, hwDhcpMode and hwDhcpv6Mode.
                        added hwIpv4ArpUnicastSwitch, hwIpv4ArpUnicastunkonwnpolicy, 
                        hwIpv6NsUnicastSwitch and hwIpv6NsUnicastunkonwnpolicy in hwVlanSrvProfTable."
   
           REVISION    "201405081000Z"
           DESCRIPTION "V3.71, Added hwIgmpUserMaxVlanTag in hwVlanSrvProfTable."           
           
           REVISION    "201404221000Z"
           DESCRIPTION "V3.70, modified the value range of hwStackingVlanInnerEthernetType."

           REVISION    "201401151000Z"
           DESCRIPTION "V3.69, modified the description of leaves."
           
           REVISION    "201312131000Z"
           DESCRIPTION "V3.68, Added hwVlanAggregationSubVlanNdProxyStatus in hwVlanAggregationTable."
           
           REVISION    "201310291000Z"
           DESCRIPTION "V3.67, added layer3option16 option to hwDhcpv6Mode.
                        Added hwRipngTunnelSwitch in hwVlanSrvProfTable."

           REVISION    "201310021000Z"    
           DESCRIPTION "V3.66, added hwVOIPDhcpQosTable.
                        Added hwVOIPIPAddressSrc in hwVOIPAddressTable.
                        Added hwVOIPQosIPAddressSrc in hwVOIPQosTable."

           REVISION    "201309141000Z"
           DESCRIPTION "V3.65, modified hwVlanDescription to hwVlanName.
                       modified hwVlanDescriptionChangeInfoTrap to hwVlanNameChangeInfoTrap.
                       added hwCableSourceVerify."
                               
           REVISION    "201302011000Z"
           DESCRIPTION "V3.64, added hwDocsSrvVlanIDTable."

           REVISION    "201301181000Z"
           DESCRIPTION "V3.63, modified the description of hwVOIPAddressIndex in hwVOIPAddressTable."

           REVISION    "201211131000Z"
           DESCRIPTION "V3.62, added hwDocsDefaultSrvVlanID."

           REVISION    "201210291000Z"
           DESCRIPTION "V3.61, modified hwVlanName to hwVlanDescription.
                       modified hwVlanNameChangeInfoTrap to hwVlanDescriptionChangeInfoTrap."

           REVISION    "201208131000Z"
           DESCRIPTION "V3.60, modified the description of some leaves in hwVlanSrvProfTable."

           REVISION    "201206151000Z"
           DESCRIPTION "V3.59, added hwPolicyMulticastFabric.
                       modified the description of hwVlanAndVlanSrvProfOperInfoTrap."

           REVISION     "201203070000Z"
           DESCRIPTION  "V3.58, added hwIPv6MTU."

           REVISION    "201201301000Z"
           DESCRIPTION "V3.57, added hwVlanAddInfoTrap, hwVlanDelInfoTrap, hwVlanAttrChangedInfoTrap and hwPortVlanChangedInfoTrap."

           REVISION    "201109210000Z"
           DESCRIPTION "V3.56, added hwDoubleTagTunnelConfig.
                        added hwDoubleTagTunnelIgmp, hwDoubleTagTunnelRip and hwDoubleTagTunnelDhcp in hwDoubleTagTunnelConfig."

           REVISION    "201107151000Z"
           DESCRIPTION "V3.55, added hwVlanConnectTable.
                        added hwVlanTrafficSuppressUnknowncastNetwork in hwVlanMIBTable.
                        added hwDhcpRelayInterfaceRelayAgentSwitch in hwVlanSrvProfTable."

           REVISION    "201104011000Z"
           DESCRIPTION " V3.54, Add hwVOIPAddressObtainMode and hwVOIPPPPOEClientName based on V3.52"

           REVISION    "201103251000Z"
           DESCRIPTION " V3.53, Add hwVOIPAddressObtainMode, hwVOIPPPPOEClientName."

           REVISION    "201102111000Z"
           DESCRIPTION "V3.52, modified the description of hwVlanNameChangeInfoTrap, hwVlanSrvProfOperType, hwVlanForwardingModeInfoTrap."

           REVISION    "201101241000Z"
           DESCRIPTION "V3.51, added hwVmacIPoESubStatus, hwVmacPPPoESubStatus, hwVmacPPPoASubStatus, hwPPPoAMacMode,
                        hwAntiIpv6SpoofingSwitch, hwIpv6DadProxySwitch, hwIpv6BindRouteAndNdSwitch,
                        hwIpv6NsReplySwitch, hwIpv4ArpReplySwitch.
                       "

           REVISION    "201012130000Z"
           DESCRIPTION "V3.50, added hwVlanBindRaioProfileName."

           REVISION    "201011241000Z"
           DESCRIPTION "V3.49, added hwDhcpv6Mode, hwDhcpv6OptionSwitch, and modify the description of leaves.
                        Modified the description of hwVlanType, hwVlanMacFilter, hwifSVLANVlanListTable, hwRegionVLanTable,
                        hwSmartVLanTable, hwMuxVlanEnable, hwMuxVlanPortConfTable, hwMuxVlanSlotConfTable, hwMultiVLanTable, hwVlanUpCarTable,
                        hwVlanDownCarTable, hwVlanParaTable, hwLocalVlanTable, hwVlanIpAwareTable, hwMplsVlanTable.
                       "

           REVISION    "201011191000Z"
           DESCRIPTION "V3.48, modified the description of hwifSVLANVlanListTable, hwifPVLANMappingTable, hwRegionVLanTable,
                        hwSmartVLanTable, hwMuxVlanPortConfTable, hwMuxVlanSlotConfTable, hwMultiVLanTable, hwVlanUpCarTable,
                        hwVlanDownCarTable, hwVlanParaTable, hwLocalVlanTable, hwVlanIpAwareTable, hwMplsVlanTable, hwVlanType,
                        hwVlanStatus, hwVlanAttrib.
                       "

           REVISION    "201007031000Z"
           DESCRIPTION "V3.47, added hwMplsVlanTable in hwVlanMngObject.
                        Modified the description of hwVlanList,hwVlanSrvProfOperType,hwVlanNameChangeInfoTrap,
                        hwVlanForwardingModeInfoTrap,hwVlanSrvProfChageInfoTrap and hwVlanAndVlanSrvProfOperInfoTrap.
                       "

           REVISION    "201006211000Z"
           DESCRIPTION "V3.46, added OBJECT-TYPE node for notification including hwVlanList and hwVlanSrvProfOperType.
                        Added NOTIFICATION-TYPE node including hwVlanNameChangeInfoTrap,hwVlanForwardingModeInfoTrap,
                        hwVlanSrvProfChageInfoTrap and hwVlanAndVlanSrvProfOperInfoTrap."

           REVISION    "201006201000Z"
           DESCRIPTION "V3.45, modified the index of hwVlanTrafficOccupiedTable from hwVlanIndex to hwVlanIndex and hwInnerVlanID."

           REVISION    "201006101000Z"
           DESCRIPTION "V3.44, deleted the Chinese characters in this file."

           REVISION    "201006071000Z"
           DESCRIPTION "V3.43, added hwVlanIfDhcpsStatus in hwVlanInterfaceEntry"

           REVISION    "201005181000Z"
           DESCRIPTION "V3.42, added notConfig option to hwPPPoEMacMode, hwVmacStatus, hwRipTunnelSwitch, hwVtpCdpTunnelSwitch,
                        hwBpduTunnelSwitch, hwForwardingMode, hwPolicyBroadcast, hwPolicyMulticast, hwPolicyUnknowncast, hwAntiMacSpoofingSwitch."

           REVISION    "201004261000Z"
           DESCRIPTION "V3.41, modified the description of leaves."

           REVISION    "201003221000Z"
           DESCRIPTION "V3.40, added hwOspfTunnelSwitch, hwL3ProtocolTunnelSwitch, and modify the description of leaves."

           REVISION    "201003181000Z"
           DESCRIPTION "V3.39, added hwFabricMacLearningSwitch"

           REVISION    "201002111000Z"
           DESCRIPTION "V3.38, modified format of this file"

           REVISION    "201001251000Z"
           DESCRIPTION "V3.37, added hwVmacAgingMode"

           REVISION    "201001111000Z"
           DESCRIPTION "V3.36, modified the datatype definition,description of objects.
                        Integrated the huawei-VlanFluxStatistic-mib.mib and HUAWEI-VLAN-MIB.mib into HUAWEI-VLAN-MIB.mib"

           REVISION    "201001081000Z"
           DESCRIPTION "V3.35, added hwVlanIpAwareSrcIPMode, and hwVlanIpAwareArpSendPeriod"

           REVISION    "200912030000Z"
           DESCRIPTION "V3.34, added hwVlanIfDhcpClientOption60"

           REVISION    "200911160000Z"
           DESCRIPTION "V3.33, added hwVlanIpAwareTable, hwIpAwareVirtualIPTable, and hwIpAwareRouteTable"

           REVISION    "200902200000Z"
           DESCRIPTION "V3.23, added hwDot1adTpid, and hwPortOuterEthernetTypeTable"

           REVISION    "200712200000Z"
           DESCRIPTION "V3.13, added hwVlanForwarding, hwVlanPolicyBroadcast, and hwVlanPolicyUnknowncast in hwVlanMIBTable."

           REVISION    "200704230000Z"
           DESCRIPTION "V1.02, integrated HUAWEI-PACKET-TUNNEL-MIB.mib,
                        HUAWEI-VLAN-IF-MIB.mib,HUAWEI-VMIF-MIB.mib and HUAWEI-VLAN-MIB.mib into HUAWEI-VLAN-MIB.mib"

           REVISION    "200512130000Z"
           DESCRIPTION "V1.00, first draft."

           ::= { huaweiMgmt 6 }

       VlanIndex ::= TEXTUAL-CONVENTION
           STATUS current
           DESCRIPTION
               "A value used to index per-VLAN tables: values of 0 and
               4095 are not permitted; if the value is between 1 and
               4094 inclusive, it represents an IEEE 802.1Q VLAN-ID with
               global scope within a given bridged domain (see VlanId
               textual convention).  If the value is greater than 4095
               then it represents a VLAN with scope local to the
               particular agent, i.e. one without a global VLAN-ID
               assigned to it. Such VLANs are outside the scope of
               IEEE 802.1Q but it is convenient to be able to manage them
               in the same way using this MIB."
           SYNTAX Unsigned32

       SnmpAdminString ::= TEXTUAL-CONVENTION
           DISPLAY-HINT
               "255a"
           STATUS current
           DESCRIPTION
               "An octet string containing administrative
               information, preferably in human-readable form.

               To facilitate internationalization, this
               information is represented using the ISO/IEC
               IS 10646-1 character set, encoded as an octet
               string using the UTF-8 transformation format
               described in [RFC2279].

               Since additional code points are added by
               amendments to the 10646 standard from time
               to time, implementations must be prepared to
               encounter any code point from 0x00000000 to
               0x7fffffff.  Byte sequences that do not
               correspond to the valid UTF-8 encoding of a
               code point or are outside this range are
               prohibited.

               The use of control codes should be avoided.

               When it is necessary to represent a newline,
               the control code sequence CR LF should be used.

               The use of leading or trailing white space should
               be avoided.

               For code points not directly supported by user
               interface hardware or software, an alternative
               means of entry and display, such as hexadecimal,
               may be provided.

               For information encoded in 7-bit US-ASCII,
               the UTF-8 encoding is identical to the
               US-ASCII encoding.

               UTF-8 may require multiple bytes to represent a
               single character / code point; thus the length
               of this object in octets may be different from
               the number of characters encoded.  Similarly,
               size constraints refer to the number of encoded
               octets, not the number of characters represented
               by an encoding.

               Note that when this TC is used for an object that
               is used or envisioned to be used as an index, then
               a SIZE restriction MUST be specified so that the
               number of sub-identifiers for any object instance
               does not exceed the limit of 128, as defined by
               [RFC1905].

               Note that the size of an SnmpAdminString object is
               measured in octets, not characters.
               "
           SYNTAX OCTET STRING (SIZE (0..255))

       PortList ::= TEXTUAL-CONVENTION
           STATUS current
           DESCRIPTION
               "Each octet within this value specifies a set of eight
               ports, with the first octet specifying ports 1 through
               8, the second octet specifying ports 9 through 16, etc.
               Within each octet, the most significant bit represents
               the lowest numbered port, and the least significant bit
               represents the highest numbered port.  Thus, each port
               of the bridge is represented by a single bit within the
               value of this object.  If that bit has a value of '1'
               then that port is included in the set of ports; the port
               is not included if its bit has a value of '0'."
           SYNTAX OCTET STRING

       hwVlanMngObject OBJECT-IDENTITY
           STATUS current
           DESCRIPTION
               "Vlan Object
               "
           ::= { hwVlan 1 }

       hwVlanMIBTable OBJECT-TYPE
           SYNTAX SEQUENCE OF HwVlanMIBEntry
           MAX-ACCESS not-accessible
           STATUS current
           DESCRIPTION
               "Describes the VLAN basic attributes, used for managing a VLAN, including creating,
                modifying, querying, and deleting a VLAN, and configuring standard ports of a VLAN.
                The index of this table is hwVlanIndex.
               "
           ::= { hwVlanMngObject 1 }

       hwVlanMIBEntry OBJECT-TYPE
           SYNTAX HwVlanMIBEntry
           MAX-ACCESS not-accessible
           STATUS current
           DESCRIPTION
               "Describes the VLAN basic attributes, used for managing a VLAN, including creating,
                modifying, querying, and deleting a VLAN, and configuring standard ports of a VLAN.
                The index of this entry is hwVlanIndex.
               "

           INDEX { hwVlanIndex }
           ::= { hwVlanMIBTable 1 }

       HwVlanMIBEntry ::=
           SEQUENCE {
             hwVlanIndex
               VlanIndex,
             hwVlanName
               OCTET STRING,
             hwVlanPorts
               PortList,
             hwVlanType
               INTEGER,
             hwVlanMacFilter
               TruthValue,
             hwVlanMcastUnknownProtos
               TruthValue,
             hwExistInterface
               TruthValue,
             hwVlanInterfaceIndex
               Integer32,
             hwVlanMacLearn
               TruthValue,
             hwVlanStatus
               INTEGER,
             hwVlanCreationTime
               TimeTicks,
             hwVlanPriority
               Integer32,
             hwVlanRowStatus
               RowStatus,
             hwVlanAttrib
               INTEGER,
             hwVlanSuperID
               Integer32,
             hwVlanForwarding
               INTEGER,
             hwVlanPolicyBroadcast
               INTEGER,
             hwVlanPolicyMulticast
               INTEGER,
             hwVlanPolicyUnknowncast
               INTEGER,
             hwVlanOuterTpid
               Unsigned32,
             hwVlanBindSrvProfName
               OCTET STRING,
             hwVlanChangeEnable
               INTEGER,
             hwVlanBindRaioProfileName
               OCTET STRING,
             hwVlanTrafficSuppressUnknowncastNetwork
               Integer32,
             hwVlanMethL2Forward
               INTEGER,
             hwVlanPortsExtendFrame
	           OCTET STRING
            }

       hwVlanIndex OBJECT-TYPE
           SYNTAX VlanIndex
           MAX-ACCESS read-only
           STATUS current
           DESCRIPTION
               "Indicates the VLAN ID.
                Range: 1-36863.
                VLAN 1 is the native VLAN.
                It cannot be deleted, but its attributes can be modified.
               "
           ::= { hwVlanMIBEntry 1 }

       hwVlanName OBJECT-TYPE
           SYNTAX OCTET STRING (SIZE (0..32))
           MAX-ACCESS read-write
           STATUS current
           DESCRIPTION
               "Indicates the VLAN tag. Identifying the VLAN is like naming the VLAN, which facilitates management.
                Range: a string of 0-32 characters
                Default: null character string
               "
           ::= { hwVlanMIBEntry 2 }

       hwVlanPorts OBJECT-TYPE
           SYNTAX PortList
           MAX-ACCESS read-write
           STATUS current
           DESCRIPTION
               "Indicates the list of the standard ports in the VLAN.
                If the VLAN contains a port, the corresponding bit of the port is set to 1.
                The value of hwVlanPorts is an octet string.
                One bit in each octet indicates one port,
                so the octet string can indicate eight ports.
                When a bit is set to 0, it indicates that the
                corresponding port does not belong to this VLAN.
                When a bit is set to 1, it indicates that the corresponding
                port belongs to this VLAN. The order is as follows: The maximum number
                of ports in a slot is 64, so the ports need to occupy eight octets.
                The order, from left to right, is presented as eight groups, 0-7, 8-15,
                16-23, 24-31, 32-39, 40-47, 48-55, and 56-63. In each octet,
                the port IDs in ascending order are presented from low bit to high bit.
                For example, ports 0/11/2 and 0/11/3 need to added to VLAN 2.
                The values of hwVlanPorts of the upstream ports
                (ports 0/11/2 and 0/11/3) to be added is calculated as follows:
                For ports 0-7 in slot 11, their corresponding character string
                positions are 76543210, and after ports 0/11/2 and 0/11/3 are added,
                the bitmap is 00001100 00000000 00000000 00000000,
                and the string is 0c 00 00 00 00 00 00 00.
                Assuming that the other slots do not have any port that is added to the VLAN,
                the character string of each of these slots is 0x0000000000000000.
                According to the ascending order of slot from left to right,
                the character strings of ports 0/11/2 and 0/11/3 are as follows:
                0000000000000000
                0000000000000000
                0000000000000000
                0000000000000000
                0000000000000000
                0000000000000000
                0000000000000000
                0000000000000000
                0000000000000000
                0000000000000000
                0000000000000000
                0c00000000000000
                0000000000000000
                0000000000000000
                0000000000000000
                0000000000000000
               "
           ::= { hwVlanMIBEntry 3 }

       hwVlanType OBJECT-TYPE
           SYNTAX INTEGER
             {
               superVlan(1),
               commonVlan(2),
               subVlan(3),
               primaryVlan(4),
               secondaryVlan(5),
               regionVlan(6),
               smartVlan(7),
               muxVlan(8),
               multiVlan(9)
             }
           MAX-ACCESS read-write
           STATUS current
           DESCRIPTION
               "Indicates the VLAN type.
                Options:
                1. superVlan(1)      -indicates super VLAN.
                2. commonVlan(2)     -indicates common VLAN.
                3. subVlan(3)        -indicates sub VLAN, the value is not supported.
                4. primaryVlan(4)    -indicates primary VLAN, the value is not supported.
                5. secondaryVlan(5)  -indicates secondary VLAN, the value is not supported.
                6. regionVlan(6)     -indicates region VLAN, the value is not supported.
                7. smartVlan(7)      -indicates smart VLAN.
                8. muxVlan(8)        -indicates MUX VLAN.
                9. multiVlan(9)      -indicates multi VLAN.
                VLAN 1 supports the modify operation on hwVlanType.
                For other VLANs, during the creation of a VLAN, hwVlanType must be specified.
               "
           ::= { hwVlanMIBEntry 4 }

       hwVlanMacFilter OBJECT-TYPE
           SYNTAX TruthValue
           MAX-ACCESS read-write
           STATUS current
           DESCRIPTION
               "The flag indicates whether to use mac filter.
                1. true(1): use mac filter
                2. false(2): not use mac filter
               "
           ::= { hwVlanMIBEntry 5 }

       hwVlanMcastUnknownProtos OBJECT-TYPE
           SYNTAX TruthValue
           MAX-ACCESS read-write
           STATUS current
           DESCRIPTION
               "multicast unknown protocals flag in the VLAN field
               "
           ::= { hwVlanMIBEntry 6 }

       hwExistInterface OBJECT-TYPE
           SYNTAX TruthValue
           MAX-ACCESS read-only
           STATUS current
           DESCRIPTION
               "The virtual interface used by VLAN
               "
           ::= { hwVlanMIBEntry 7 }

       hwVlanInterfaceIndex OBJECT-TYPE
           SYNTAX Integer32
           MAX-ACCESS read-only
           STATUS current
           DESCRIPTION
               "The index of the VLAN interface.
               "
           ::= { hwVlanMIBEntry 8 }

       hwVlanMacLearn OBJECT-TYPE
           SYNTAX TruthValue
           MAX-ACCESS read-write
           STATUS current
           DESCRIPTION
               "The flag indicates whether to open mac learning.
               "
           ::= { hwVlanMIBEntry 9 }

       hwVlanStatus OBJECT-TYPE
           SYNTAX INTEGER
             {
               other(1),
               permanent(2),
               dynamicGvrp(3)
             }
           MAX-ACCESS read-only
           STATUS current
           DESCRIPTION
               "Status of VLAN.
                Options:
                1. other(1)       -The following enumerated values is not supported.
                2. permanent(2)   -The following enumerated values is not supported.
                3. dynamicGvrp(3) -The following enumerated values is not supported.
               "
           ::= { hwVlanMIBEntry 10 }

       hwVlanCreationTime OBJECT-TYPE
           SYNTAX TimeTicks
           MAX-ACCESS read-only
           STATUS current
           DESCRIPTION
               "The time of creating VLAN.
               "
           ::= { hwVlanMIBEntry 11 }

       hwVlanPriority OBJECT-TYPE
           SYNTAX Integer32 (0..7 | 255)
           MAX-ACCESS read-write
           STATUS current
           DESCRIPTION
               "Indicates the 802.1p priority of a VLAN.
                Range: 0-7, 255
                The larger the value, the higher the priority.
                If the query operation is performed before hwVlanPriority is configured,
                the query result is 255, which is invalid.
                The meaning of each value is as follows:
                best-effort: Best-effort priority(0)
                background: Background priority(1)
                spare: Spare priority(2)
                excellent-effort: Excellent-effort priority(3)
                controlled-load: Controlled-load priority(4)
                video: Video priority(5)
                voice: Voice priority(6)
                network-management: Network-management priority(7)
               "
           DEFVAL { 255 }
           ::= { hwVlanMIBEntry 12 }

       hwVlanRowStatus OBJECT-TYPE
           SYNTAX RowStatus
           MAX-ACCESS read-create
           STATUS current
           DESCRIPTION
               "Indicates the row status, used for creating or deleting a VLAN.
                Options:
                1. active(1)
                2. createAndGo(4)
                3. destroy(6)
                To create a VLAN, you must specify hwVlanType and set
                hwVlanRowStatus to createAndGo(4) to perform the set operation.
                Other attributes of the VLAN are optional. However,
                hwVlanPorts cannot be configured at the same time.
                To delete a VLAN, set hwVlanRowStatus to destroy(6) to perform the set operation.
                During query, the value of this leaf is the fixed active(1).
               "
           ::= { hwVlanMIBEntry 13 }

       hwVlanAttrib OBJECT-TYPE
           SYNTAX INTEGER
             {
               common(1),
               qinq(2),
               stacking(3),
               subVlan(4)
             }
           MAX-ACCESS read-write
           STATUS current
           DESCRIPTION
               "Indicates the VLAN attribute. The following enumerated values are supported:
                Options:
                1. common(1)    -indicates common VLAN.
                2. qinq(2)      -indicates QinQ VLAN.
                3. stacking(3)  -indicates stacking VLAN.
                4. subVlan(4)   -indicates sub VLAN.
                During the creation of a VLAN, if this leaf is not specified, common(1)
                is adopted by default. You can perform the set operation on this
                leaf to modify the VLAN attribute.
                The value of hwVlanAttrib must not be subvlan(4).
                The value can be subvlan(4) only in the read operation. Adding a VLAN to
                or deleting a VLAN from a super VLAN must be performed through hwVlanAggregationTable.
               "
           DEFVAL { common }
           ::= { hwVlanMIBEntry 14 }

       hwVlanSuperID OBJECT-TYPE
           SYNTAX Integer32 (-1 | 2..4093)
           MAX-ACCESS read-only
           STATUS current
           DESCRIPTION
               "Indicates the ID of the super VLAN corresponding to the sub VLAN.
                Range: -1, 2-4093
                This leaf is read-only. When the VLAN is not a sub VLAN, -1 is returned.
               "
           ::= { hwVlanMIBEntry 15 }

       hwVlanForwarding OBJECT-TYPE
           SYNTAX INTEGER
             {
               vlanMac(1),
               vlanConnect(2)
             }
           MAX-ACCESS read-write
           STATUS current
           DESCRIPTION
               "Indicates the VLAN forwarding policy.
                Options:
                1. vlanMac(1)     -indicates forwarding based on the VLAN+MAC.
                2. vlanConnect(2) -indicates forwarding based on the SVLAN+CVLAN.

                During the creation of a VLAN, if this leaf is not specified,
                vlanMac(1) is adopted by default. You can perform the set
                operation on this leaf to modify the VLAN forwarding policy.
                The VLAN forwarding policy can also be configured in
                hwForwardingMode of hwVlanSrvProfTable. If a VLAN service profile
                is bound to the VLAN, the configuration in the VLAN service profile
                takes effect.
               "
           DEFVAL { vlanMac }
           ::= { hwVlanMIBEntry 16 }

       hwVlanPolicyBroadcast OBJECT-TYPE
           SYNTAX INTEGER
             {
               forward(1),
               discard(2)
             }
           MAX-ACCESS read-write
           STATUS current
           DESCRIPTION
               "Indicates the VLAN-based forwarding policy for the broadcast packets.
                Options:
                1. forward(1) -indicates that the broadcast packets are transparently transmitted.
                2. discard(2) -indicates that the broadcast packets are discarded.

                During the creation of a VLAN, if this leaf is not specified, forward(1)
                is adopted by default. You can perform the set operation on this leaf
                to modify the VLAN-based forwarding policy for the broadcast packets.
                The VLAN-based forwarding policy for the broadcast packets can also be
                configured in hwPolicyBroadcast of hwVlanSrvProfTable. If a VLAN service
                profile is bound to the VLAN, the configuration in the VLAN service profile takes effect.
               "
           DEFVAL { forward }
           ::= { hwVlanMIBEntry 17 }

       hwVlanPolicyMulticast OBJECT-TYPE
           SYNTAX INTEGER
             {
               forward(1),
               discard(2)
             }
           MAX-ACCESS read-write
           STATUS current
           DESCRIPTION
               "Indicates the VLAN-based forwarding policy for the unknown multicast packets.
                Options:
                1. forward(1) -indicates that the unknown multicast packets are transparently transmitted.
                2. discard(2) -indicates that the unknown multicast packets are discarded.

                During the creation of a VLAN, if this leaf is not specified, forward(1)
                is adopted by default. You can perform the set operation on this leaf to
                modify the VLAN-based forwarding policy for the unknown multicast packets.
                The VLAN-based forwarding policy for the unknown multicast packets can
                also be configured in hwPolicyMulticast of hwVlanSrvProfTable. If a VLAN service
                profile is bound to the VLAN, the configuration in the VLAN service profile takes effect.
               "
           DEFVAL { forward }
           ::= { hwVlanMIBEntry 18 }

       hwVlanPolicyUnknowncast OBJECT-TYPE
           SYNTAX INTEGER
             {
               forward(1),
               discard(2)
             }
           MAX-ACCESS read-write
           STATUS current
           DESCRIPTION
               "Indicates the VLAN-based forwarding policy for the unknown unicast packets.
                Options:
                1. forward(1) -indicates that the unknown unicast packets are transparently transmitted.
                2. discard(2) -indicates that the unknown unicast packets are discarded.

                During the creation of a VLAN, if this leaf is not specified, forward(1) is adopted by default.
                You can perform the set operation on this leaf to modify the VLAN-based
                forwarding policy for the unknown unicast packets.
                The VLAN-based forwarding policy for the unknown unicast packets can also be
                configured in hwPolicyUnknowncast of hwVlanSrvProfTable. If a VLAN service profile is bound
                to the VLAN, the configuration in the VLAN service profile takes effect.
               "
           DEFVAL { forward }
           ::= { hwVlanMIBEntry 19 }

       hwVlanOuterTpid OBJECT-TYPE
           SYNTAX Unsigned32 (1536..65535)
           MAX-ACCESS read-write
           STATUS current
           DESCRIPTION
               "Indicates the Ethernet protocol type of a VLAN.
                Range: 1536-65535 (0x0600-0xFFFF)
                Default: 0x8100
               "
           DEFVAL  { 33024 }
           ::= { hwVlanMIBEntry 20 }

       hwVlanBindSrvProfName OBJECT-TYPE
           SYNTAX OCTET STRING (SIZE (0..32))
           MAX-ACCESS read-write
           STATUS current
           DESCRIPTION
               "Indicates the name of the VLAN service profile bound to a VLAN.
                Range: a string of 0-32 characters
                This leaf identifies a VLAN service profile, which must be
                created in hwVlanSrvProfTable. The null character string indicates
                that the binding relation between a VLAN and a VLAN service profile is deleted.
               "
           ::= { hwVlanMIBEntry 21 }

       hwVlanChangeEnable OBJECT-TYPE
           SYNTAX INTEGER
             {
               idle(0),
               addPort(1),
               removePort(2)
             }
           MAX-ACCESS read-write
           STATUS current
           DESCRIPTION
               "Indicates the operation type of whether a standard port list maps a VLAN.
                Options:
                1. idle(0)       -indicates invalid mapping.
                2. addPort(1)    -indicates that a port is added to the VLAN.
                3. removePort(2) -indicates that a port is deleted from the VLAN.
                This leaf must work with hwVlanPorts.
               "
           ::= { hwVlanMIBEntry 22 }

       hwVlanBindRaioProfileName OBJECT-TYPE
           SYNTAX OCTET STRING (SIZE (0..32))
           MAX-ACCESS read-write
           STATUS current
           DESCRIPTION
               "Indicates the name of the RAIO profile bound to a VLAN.
                Range: a string of 0-32 characters
                This leaf identifies a RAIO profile, which must be
                created in hwDslamRAIOProfileTable. The null character string indicates
                that the binding relation between a VLAN and a RAIO profile is deleted.
               "
           ::= { hwVlanMIBEntry 23 }

        hwVlanTrafficSuppressUnknowncastNetwork OBJECT-TYPE
           SYNTAX Integer32 (0..13)
           MAX-ACCESS read-write
           STATUS current
           DESCRIPTION
               "Indicates the unknown unicast traffic suppression on a VLAN.
                Range: 0-13
                Default: 0
                13 indicates full-suppression of traffic, and 0 indicates no traffic suppression.
                The suppression levels and corresponding bandwidth ranges are listed as follows:
                ---------------------------------------------------------------
                NO. Min bandwidth(kbps) Max bandwidth(kbps) Package number(pps)
                ---------------------------------------------------------------
                  0      Not suppressed      Not suppressed      Not suppressed
                  1                   6                 145                  12
                  2                  12                 291                  24
                  3                  24                 582                  48
                  4                  48                1153                  95
                  5                  97                2319                 191
                  6                 195                4639                 382
                  7                 390                9265                 763
                  8                 781               18531                1526
                  9                1562               37063                3052
                 10                3125               74126                6104
                 11                6249              148241               12207
                 12               12499              296483               24414
                 13                   0                   0                   0
                ---------------------------------------------------------------
               "
           ::= { hwVlanMIBEntry 24 }

       hwVlanMethL2Forward OBJECT-TYPE
           SYNTAX INTEGER
             {
               enable(1),
               disable(2)
             }
           MAX-ACCESS read-write
           STATUS current
           DESCRIPTION
               "Indicates the switch of MEth l2 forwarding on a VLAN.
                Options:
                1. enable(1)    -Enable MEth l2 forwarding on a VLAN.
                2. disable(2)   -Disable MEth l2 forwarding on a VLAN.
                The default value is disable(2).
               "
           ::= { hwVlanMIBEntry 25 }

       hwVlanPortsExtendFrame OBJECT-TYPE
           SYNTAX OCTET STRING (SIZE (0..2048))
           MAX-ACCESS read-write
           STATUS current
           DESCRIPTION
               "Indicates the list of the extend frame standard ports in the VLAN. If 
                the VLAN contains a port, the corresponding bit of the port is set to 1. 
                The value of hwVlanPortsExtendFrame is mixed encoding of the index 
                and octet string. Encoding area, which specifies the index of the FrameId 
                and SlotId, consisting of 4 characters and 2 characters respectively. 
                Port area, which is represented in octet string format and occupies 16 characters. 
                One bit in each octet indicates one port, so 8 octet means 64 ports in a slot. 
                When a bit is set to 0, it indicates that the corresponding port does not 
		        belong to this VLAN. When a bit is set to 1, it indicates that the corresponding 
		        port belongs to this VLAN. The order is as follows:
                If a extend frame has a port that belongs to a VLAN, the port in the 
                corresponding frame and slot are represented by octet strings.  The maximum number
                of ports in a slot is 64, so the ports need to occupy eight octets.
                The order, from left to right, is presented as eight groups, 0-7, 8-15,
                16-23, 24-31, 32-39, 40-47, 48-55, and 56-63. In each octet,
                the PortId in ascending order are presented from low bit to high bit.
                For example, ports 0/11/2 and 0/11/3 need to added to the same VLAN.
                The values of hwVlanPortsExtendFrame of the upstream ports
                (ports 1/02/2 and 1/02/3 and 1/03/1) to be added is calculated as follows:
                For ports 0-7 in slot 02 in frame 1, their corresponding character string
                positions are 76543210, and after ports 1/02/2 and 1/02/3 are added, the bitmap is 
		        00001100 00000000 00000000 00000000 00000000 00000000 00000000 00000000,
                and the string is (HEX) 0C 00 00 00 00 00 00 00.
                After the FrameId (2 Octet) and SoltId (1 Octet) are added at the front, 
		        the string is 0001 02 0c 00 00 00 00 00 00 00.
                In the same way, 1 / 03 / 1 is encoded as 0001 03 02 00 00 00 00 00 00 00.
                Assuming that the other slots do not have any port that is added to the VLAN,
                The slot information is not filled in. 
                Therefore, the length of the code is variable, but usually is an integer multiple 
		        of 22 characters.finally, the string is
                00 01 02 0C 00 00 00 00 00 00 00
                00 01 03 02 00 00 00 00 00 00 00
		        Under special circumstances, none port in VLAN is described by '0',which is 
		        just one character.
               "
           ::= { hwVlanMIBEntry 26 }

       hwifSVLANVlanListTable OBJECT-TYPE
           SYNTAX SEQUENCE OF HwifSVLANVlanListEntry
           MAX-ACCESS not-accessible
           STATUS current
           DESCRIPTION
               "Indicates the super VLAN list, shows the sub VLANs in the super VLAN.
                The index of this table is hwifSvlanVlanID.
               "
           ::= { hwVlanMngObject 3 }

       hwifSVLANVlanListEntry OBJECT-TYPE
           SYNTAX HwifSVLANVlanListEntry
           MAX-ACCESS not-accessible
           STATUS current
           DESCRIPTION
               "Indicates the super VLAN list, shows the sub VLANs in the super VLAN.
                The index of this entry is hwifSvlanVlanID.
               "
           INDEX { hwifSvlanVlanID }
           ::= { hwifSVLANVlanListTable 1 }

       HwifSVLANVlanListEntry ::=
           SEQUENCE {
             hwifSvlanVlanID
               VlanIndex,
             hwifSvlanSubVlanlistLow
               OCTET STRING,
             hwifSvlanSubVlanlisHigh
               OCTET STRING,
             hwifSvlanOperStatus
               RowStatus
            }

       hwifSvlanVlanID OBJECT-TYPE
           SYNTAX VlanIndex
           MAX-ACCESS read-only
           STATUS current
           DESCRIPTION
               "The index of the table, indicates the super VLAN ID "
           ::= { hwifSVLANVlanListEntry 1 }

       hwifSvlanSubVlanlistLow OBJECT-TYPE
           SYNTAX OCTET STRING (SIZE (0..256))
           MAX-ACCESS read-write
           STATUS current
           DESCRIPTION
               "The low oct string for sub VLAN list of Primary VLANs, Each bit is one VLAN. All bits  be  2048(256 * 8) VLAN.
                Sub VLAN will be added to super VLAN.
               "
           ::= { hwifSVLANVlanListEntry 2 }

       hwifSvlanSubVlanlisHigh OBJECT-TYPE
           SYNTAX OCTET STRING (SIZE (0..256))
           MAX-ACCESS read-write
           STATUS current
           DESCRIPTION
               "The high oct string for sub VLAN list of Primary VLANs, Each bit is one VLAN. All bits  be  2048(256 * 8) VLAN
                Sub VLAN will be added to super VLAN.
               "
           ::= { hwifSVLANVlanListEntry 3 }

       hwifSvlanOperStatus OBJECT-TYPE
           SYNTAX RowStatus
           MAX-ACCESS read-create
           STATUS current
           DESCRIPTION
               "VLAN operational status, now support createAndGo(4),destroy(6)
               "
           ::= { hwifSVLANVlanListEntry 4 }

       hwifPVLANMappingTable OBJECT-TYPE
           SYNTAX SEQUENCE OF HwifPVLANMappingEntry
           MAX-ACCESS not-accessible
           STATUS current
           DESCRIPTION
               "Secondary VLAN lists of Primary VLANs.
                The index of this table is hwifPvlanPrimaryVlanID.
               "
           ::= { hwVlanMngObject 4 }

       hwifPVLANMappingEntry OBJECT-TYPE
           SYNTAX HwifPVLANMappingEntry
           MAX-ACCESS not-accessible
           STATUS current
           DESCRIPTION
               "Secondary VLAN lists of Primary VLANs.
                The index of this entry is hwifPvlanPrimaryVlanID.
               "
           INDEX { hwifPvlanPrimaryVlanID }
           ::= { hwifPVLANMappingTable 1 }

       HwifPVLANMappingEntry ::=
           SEQUENCE {
             hwifPvlanPrimaryVlanID
               VlanIndex,
             hwifPvlanSecondaryVlanlistLow
               OCTET STRING,
             hwifPvlanSecondaryVlanlistHigh
               OCTET STRING,
             hwifPvlanOperStatus
               RowStatus
            }

       hwifPvlanPrimaryVlanID OBJECT-TYPE
           SYNTAX VlanIndex
           MAX-ACCESS read-only
           STATUS current
           DESCRIPTION
               "Primary VLAN ID
               "
           ::= { hwifPVLANMappingEntry 1 }

       hwifPvlanSecondaryVlanlistLow OBJECT-TYPE
           SYNTAX OCTET STRING (SIZE (0..256))
           MAX-ACCESS read-write
           STATUS current
           DESCRIPTION
               "The second low oct string for sub VLAN list of Primary VLANs, Each bit is one VLAN. All bits  be  2048(256 * 8) VLAN
                Secondary VLAN will be added to primary VLAN.
               "
           ::= { hwifPVLANMappingEntry 2 }

       hwifPvlanSecondaryVlanlistHigh OBJECT-TYPE
           SYNTAX OCTET STRING (SIZE (0..256))
           MAX-ACCESS read-write
           STATUS current
           DESCRIPTION
               "The second low oct string for sub VLAN list of Primary VLANs, Each bit is one VLAN. All bits  be  2048(256 * 8) VLAN
                Secondary VLAN will be added to primary VLAN.
               "
           ::= { hwifPVLANMappingEntry 3 }

       hwifPvlanOperStatus OBJECT-TYPE
           SYNTAX RowStatus
           MAX-ACCESS read-create
           STATUS current
           DESCRIPTION
               "vlan operational status, now support createAndGo(4),destroy(6)
               "
           ::= { hwifPVLANMappingEntry 4 }

       hwRegionVLanTable OBJECT-TYPE
           SYNTAX SEQUENCE OF HwRegionVLanEntry
           MAX-ACCESS not-accessible
           STATUS current
           DESCRIPTION
               "Indicates the region VLAN, it is used to configure the region VLAN.
                The index of this table is hwVlanIndex.
               "
           ::= { hwVlanMngObject 5 }

       hwRegionVLanEntry OBJECT-TYPE
           SYNTAX HwRegionVLanEntry
           MAX-ACCESS not-accessible
           STATUS current
           DESCRIPTION
               "Indicates the region VLAN, it is used to configure the region VLAN.
                The index of this entry is hwVlanIndex.
               "
           INDEX { hwVlanIndex }
           ::= { hwRegionVLanTable 1 }

       HwRegionVLanEntry ::=
           SEQUENCE {
             hwRegionVpi
               Integer32,
             hwRegionVci
               Integer32,
             hwRegionPVCRowStatus
               RowStatus
            }

       hwRegionVpi OBJECT-TYPE
           SYNTAX Integer32
           MAX-ACCESS read-write
           STATUS current
           DESCRIPTION
               "THE atm vpi of the VLAN.
               "
           ::= { hwRegionVLanEntry 1 }

       hwRegionVci OBJECT-TYPE
           SYNTAX Integer32
           MAX-ACCESS read-write
           STATUS current
           DESCRIPTION
               "The atm vci of the VLAN.
               "
           ::= { hwRegionVLanEntry 2 }
       hwRegionPVCRowStatus OBJECT-TYPE
           SYNTAX RowStatus
           MAX-ACCESS read-create
           STATUS current
           DESCRIPTION
               "Row status,now support createAndGo(4),destroy(6).
                4 is used for creating group pvc for region VLAN,
                6 is used for deleting group pvc for region VLAN.
               "
           ::= { hwRegionVLanEntry 3 }


       hwSmartVLanTable OBJECT-TYPE
           SYNTAX SEQUENCE OF HwSmartVLanEntry
           MAX-ACCESS not-accessible
           STATUS current
           DESCRIPTION
               "Indicates the smart VLAN, it is used to configure the smart VLAN.
                The index of this table is hwSmartVlanID.
               "
           ::= { hwVlanMngObject 6 }

       hwSmartVLanEntry OBJECT-TYPE
           SYNTAX HwSmartVLanEntry
           MAX-ACCESS not-accessible
           STATUS current
           DESCRIPTION
               "Indicates the smart VLAN, it is used to configure the smart VLAN.
                The index of this entry is hwSmartVlanID.
               "
           INDEX { hwSmartVlanID }
           ::= { hwSmartVLanTable 1 }

       HwSmartVLanEntry ::=
           SEQUENCE {
             hwSmartVlanID
               VlanIndex,
             hwSmartVlanUplinkPort
               PortList,
             hwSmartVlanDownlinkPort
               PortList,
             hwSmartVlanRowStatus
               RowStatus
            }

       hwSmartVlanID OBJECT-TYPE
           SYNTAX VlanIndex
           MAX-ACCESS read-only
           STATUS current
           DESCRIPTION
               "The index of the table, indicates a smart VLAN ID.
               "
           ::= { hwSmartVLanEntry 1 }

       hwSmartVlanUplinkPort OBJECT-TYPE
           SYNTAX PortList
           MAX-ACCESS read-write
           STATUS current
           DESCRIPTION
               "smart VLAN uplink ports
               "
           ::= { hwSmartVLanEntry 2 }

       hwSmartVlanDownlinkPort OBJECT-TYPE
           SYNTAX PortList
           MAX-ACCESS read-write
           STATUS current
           DESCRIPTION
               "smart VLAN downlink ports
               "
           ::= { hwSmartVLanEntry 3 }

       hwSmartVlanRowStatus OBJECT-TYPE
           SYNTAX RowStatus
           MAX-ACCESS read-create
           STATUS current
           DESCRIPTION
               "Row status, now support createAndGo(4),destroy(6)
               "
           ::= { hwSmartVLanEntry 4 }

       hwMuxVlanEnable OBJECT-TYPE
           SYNTAX INTEGER
             {
               enabled(1),
               disabled(2)
             }
           MAX-ACCESS read-write
           STATUS current
           DESCRIPTION
               "Enable/disable MUX VLAN.
                Options:
                1. enabled(1)  -Enable MUX VLAN.
                2. disabled(2) -Disable MUX VLAN.
               "
           ::= { hwVlanMngObject 7 }

       hwMuxVlanPortConfTable OBJECT-TYPE
           SYNTAX SEQUENCE OF HwMuxVlanPortConfEntry
           MAX-ACCESS not-accessible
           STATUS current
           DESCRIPTION
               "Indicates the Mux VLAN port configuration, it is used to configure the Mux VLAN port.
                The index of this table is ifIndex.
               "
           ::= { hwVlanMngObject 8 }

       hwMuxVlanPortConfEntry OBJECT-TYPE
           SYNTAX HwMuxVlanPortConfEntry
           MAX-ACCESS not-accessible
           STATUS current
           DESCRIPTION
               "Indicates the Mux VLAN port configuration, it is used to configure the Mux VLAN port.
                The index of this entry is ifIndex.
               "
           INDEX { ifIndex }
           ::= { hwMuxVlanPortConfTable 1 }

       HwMuxVlanPortConfEntry ::=
           SEQUENCE {
             hwMuxVlanPortType
               INTEGER,
             hwMuxVlanStartVlanId
               Integer32,
             hwMuxVlanGroupNum
               Integer32,
             hwMuxVlanPortConfRowStatus
               RowStatus,
             hwMuxVlanUplinkPort
               Integer32,
             hwMuxVlanDownlinkPort
               Integer32
            }

       hwMuxVlanPortType OBJECT-TYPE
           SYNTAX INTEGER
             {
               uplinkPort(1),
               cascadingPort(2)
             }
           MAX-ACCESS read-create
           STATUS current
           DESCRIPTION
               "Configure the uplink-port or cascading-port for the MUX VLAN.
                Options:
                1. uplinkPort(1)    -uplink port
                2. cascadingPort(2) -cascading port
               "
           DEFVAL { cascadingPort }
           ::= { hwMuxVlanPortConfEntry 1 }

       hwMuxVlanStartVlanId OBJECT-TYPE
           SYNTAX Integer32
           MAX-ACCESS read-create
           STATUS current
           DESCRIPTION
               "The start VLAN ID of Mux VLAN.
               "
           DEFVAL { 128 }
           ::= { hwMuxVlanPortConfEntry 2 }

       hwMuxVlanGroupNum OBJECT-TYPE
           SYNTAX Integer32
           MAX-ACCESS read-create
           STATUS current
           DESCRIPTION
               "The VLAN group number.
               "
           ::= { hwMuxVlanPortConfEntry 3 }

       hwMuxVlanPortConfRowStatus OBJECT-TYPE
           SYNTAX RowStatus
           MAX-ACCESS read-create
           STATUS current
           DESCRIPTION
               "Row status, now support createAndGo(4),destroy(6).
               "
           ::= { hwMuxVlanPortConfEntry 4 }

       hwMuxVlanUplinkPort OBJECT-TYPE
           SYNTAX Integer32
           MAX-ACCESS read-create
           STATUS current
           DESCRIPTION
               "Uplink port for mux VLAN configuration.(for UA 5000)
               "
           ::= { hwMuxVlanPortConfEntry 5 }

       hwMuxVlanDownlinkPort OBJECT-TYPE
           SYNTAX Integer32
           MAX-ACCESS read-create
           STATUS current
           DESCRIPTION
               "Downlink port for mux VLAN configuration.
                If the value is -1, use inner port instead(Only used for UA5000).
               "
           ::= { hwMuxVlanPortConfEntry 6 }

       hwMuxVlanSlotConfTable OBJECT-TYPE
           SYNTAX SEQUENCE OF HwMuxVlanSlotConfEntry
           MAX-ACCESS not-accessible
           STATUS current
           DESCRIPTION
               "Indicates the I/O board MUX VLAN configure, it is used to configure the I/O board MUX VLAN.
                The index of this table is hwSlotIndex.
               "
           ::= { hwVlanMngObject 9 }

       hwMuxVlanSlotConfEntry OBJECT-TYPE
           SYNTAX HwMuxVlanSlotConfEntry
           MAX-ACCESS not-accessible
           STATUS current
           DESCRIPTION
               "Indicates the I/O board MUX VLAN configure, it is used to configure the I/O board MUX VLAN.
                The index of this entry is hwSlotIndex.
               "
           INDEX { hwSlotIndex }
           ::= { hwMuxVlanSlotConfTable 1 }

       HwMuxVlanSlotConfEntry ::=
           SEQUENCE {
             hwMuxVlanSlotStartVlanId
               Integer32,
             hwMuxVlanSlotRowStatus
               RowStatus
            }

       hwMuxVlanSlotStartVlanId OBJECT-TYPE
           SYNTAX Integer32
           MAX-ACCESS read-create
           STATUS current
           DESCRIPTION
               "The start VLAN ID for the I/O board.
               "
           ::= { hwMuxVlanSlotConfEntry 1 }

       hwMuxVlanSlotRowStatus OBJECT-TYPE
           SYNTAX RowStatus
           MAX-ACCESS read-create
           STATUS current
           DESCRIPTION
               "Row status, now support createAndGo(4),destroy(6).
               "
           ::= { hwMuxVlanSlotConfEntry 2 }

       hwMultiVLanTable OBJECT-TYPE
           SYNTAX SEQUENCE OF HwMultiVLanEntry
           MAX-ACCESS not-accessible
           STATUS current
           DESCRIPTION
               "Indicates the Multi VLAN, it is used to configure the multi VLAN.
                The index of this table is hwMultiVlanID.
               "
           ::= { hwVlanMngObject 10 }

       hwMultiVLanEntry OBJECT-TYPE
           SYNTAX HwMultiVLanEntry
           MAX-ACCESS not-accessible
           STATUS current
           DESCRIPTION
               "Indicates the Multi VLAN, it is used to configure the multi VLAN.
                The index of this entry is hwMultiVlanID.
               "
           INDEX { hwMultiVlanID }
           ::= { hwMultiVLanTable 1 }

       HwMultiVLanEntry ::=
           SEQUENCE {
             hwMultiVlanID
               VlanIndex,
             hwMultiVlanUplinkPort
               PortList,
             hwMultiVlanDownlinkPort
               PortList,
             hwMultiVlanRowStatus
               RowStatus
            }

       hwMultiVlanID OBJECT-TYPE
           SYNTAX VlanIndex
           MAX-ACCESS read-only
           STATUS current
           DESCRIPTION
               "The index of the table, indicates a Multi VLAN ID.
               "
           ::= { hwMultiVLanEntry 1 }

       hwMultiVlanUplinkPort OBJECT-TYPE
           SYNTAX PortList
           MAX-ACCESS read-write
           STATUS current
           DESCRIPTION
               "Multi VLAN uplink ports.
               "
           ::= { hwMultiVLanEntry 2 }

       hwMultiVlanDownlinkPort OBJECT-TYPE
           SYNTAX PortList
           MAX-ACCESS read-write
           STATUS current
           DESCRIPTION
               "Multi VLAN downlink ports.
               "
           ::= { hwMultiVLanEntry 3 }

       hwMultiVlanRowStatus OBJECT-TYPE
           SYNTAX RowStatus
           MAX-ACCESS read-create
           STATUS current
           DESCRIPTION
               "Row status, now support createAndGo(4),destroy(6).
               "
           ::= { hwMultiVLanEntry 4 }

       hwVlanAggregationTable    OBJECT-TYPE
           SYNTAX SEQUENCE OF HwVlanAggregationEntry
           MAX-ACCESS      not-accessible
           STATUS      current
           DESCRIPTION
                "Describes the relation between the super VLAN and the sub VLAN in a VLAN aggregation.
                 The indexes of this table are hwVlanAggregationSuperVlanId and hwVlanAggregationSubVlanId.
                "
           ::= { hwVlanMngObject 11 }

       hwVlanAggregationEntry  OBJECT-TYPE
           SYNTAX     HwVlanAggregationEntry
           MAX-ACCESS     not-accessible
           STATUS     current
           DESCRIPTION
                "Describes the relation between the super VLAN and the sub VLAN in a VLAN aggregation.
                 The indexes of this entry are hwVlanAggregationSuperVlanId and hwVlanAggregationSubVlanId.
                "
           INDEX { hwVlanAggregationSuperVlanId, hwVlanAggregationSubVlanId}
           ::= { hwVlanAggregationTable  1 }

       HwVlanAggregationEntry    ::= SEQUENCE  {
                 hwVlanAggregationSuperVlanId
                     Integer32,
                 hwVlanAggregationSubVlanId
                     Integer32,
                 hwVlanAggregationSubVlanArpProxyStatus
                     INTEGER,
                 hwVlanAggregationSubVlanNdProxyStatus
                     INTEGER,
                 hwVlanAggregationRowStatus
                     RowStatus
                 }

       hwVlanAggregationSuperVlanId  OBJECT-TYPE
           SYNTAX  Integer32 (2..36863)
           MAX-ACCESS  read-only
           STATUS  current
           DESCRIPTION
               "Indicates the super VLAN ID in a VLAN aggregation.
                Range: 2-36863
               "
           ::= { hwVlanAggregationEntry 1 }

       hwVlanAggregationSubVlanId  OBJECT-TYPE
           SYNTAX  Integer32 (2..36863)
           MAX-ACCESS  read-only
           STATUS  current
           DESCRIPTION
               "Indicates the sub VLAN ID in a VLAN aggregation.
                Range: 2-36863
               "
           ::= { hwVlanAggregationEntry 2 }

       hwVlanAggregationSubVlanArpProxyStatus OBJECT-TYPE
           SYNTAX  INTEGER
             {
               enabled(1),
               disabled(2)
             }
           MAX-ACCESS read-write
           STATUS current
           DESCRIPTION
               "Indicates the status of ARP proxy in a sub VLAN.
                Options:
                1. enabled(1)      -Enable ARP proxy in a sub VLAN.
                2. disabled(2)     -Disable ARP proxy in a sub VLAN.
                Default: disabled(2)
               "
           ::= { hwVlanAggregationEntry 3 }

       hwVlanAggregationRowStatus  OBJECT-TYPE
           SYNTAX  RowStatus
           MAX-ACCESS  read-create
           STATUS  current
           DESCRIPTION
               "Indicates the row status, used for creating or deleting a VLAN aggregation.
                Options:
                1. active(1)
                2. createAndGo(4)
                3. destroy(6)
                To create a VLAN aggregation, specify the indexes, and set
                hwVlanAggregationRowStatus to createAndGo(4) to perform the set operation.
                To delete a VLAN aggregation, specify the indexes, and set
                hwVlanAggregationRowStatus to destroy(6) to perform the set operation.
                During query, the value of this leaf is the fixed active(1).
               "
           ::= { hwVlanAggregationEntry 4 }
       
       hwVlanAggregationSubVlanNdProxyStatus OBJECT-TYPE
           SYNTAX  INTEGER
             {
               enabled(1),
               disabled(2)
             }
           MAX-ACCESS read-write
           STATUS current
           DESCRIPTION
               "Indicates the status of ND proxy in a sub VLAN.
                Options:
                1. enabled(1)      -Enable ND proxy in a sub VLAN.
                2. disabled(2)     -Disable ND proxy in a sub VLAN.
                Default: disabled(2)
               "
           ::= { hwVlanAggregationEntry 5 }

       hwStackingVlanInnerEthernetType OBJECT-TYPE
           SYNTAX Unsigned32 (0..65535)
           MAX-ACCESS read-write
           STATUS current
           DESCRIPTION
               "Indicates the Ethernet protocol type of the inner VLAN tag supported by VLAN stacking.
                Range: 0-65535
                Default: 0x8100
               "
           ::= { hwVlanMngObject 13 }

       hwVlanUpCarTable OBJECT-TYPE
           SYNTAX SEQUENCE OF HwVlanUpCarEntry
           MAX-ACCESS not-accessible
           STATUS current
           DESCRIPTION
               "Indicates the VLAN up direct CAR.
                The index of this table is hwVlanUpCarId.
               "
           ::= { hwVlanMngObject 15 }

       hwVlanUpCarEntry OBJECT-TYPE
           SYNTAX HwVlanUpCarEntry
           MAX-ACCESS not-accessible
           STATUS current
           DESCRIPTION
               "Indicates the VLAN up direct CAR.
                The index of this entry is hwVlanUpCarId.
               "
           INDEX { hwVlanUpCarId }
           ::= { hwVlanUpCarTable 1 }

       HwVlanUpCarEntry ::=
           SEQUENCE {
             hwVlanUpCarId
               Integer32,
             hwVlanUpCarName
               OCTET STRING,
             hwVlanUpCarBandValue
               Integer32,
             hwVlanUpCarBurstValue
               Integer32,
             hwVlanUpCarIsUsed
               INTEGER,
             hwVlanUpCarRowStatus
               RowStatus
            }

       hwVlanUpCarId OBJECT-TYPE
           SYNTAX Integer32 (1..4000)
           MAX-ACCESS read-only
           STATUS current
           DESCRIPTION
               "The index of the table, indicates a up direct Carid.
               "
           ::= { hwVlanUpCarEntry  1 }

       hwVlanUpCarName OBJECT-TYPE
           SYNTAX OCTET STRING (SIZE (0..32))
           MAX-ACCESS read-write
           STATUS current
           DESCRIPTION
               "Up direct car name.
               "
           ::= { hwVlanUpCarEntry  2 }

       hwVlanUpCarBandValue OBJECT-TYPE
           SYNTAX Integer32 (64..1048512)
           MAX-ACCESS read-write
           STATUS current
           DESCRIPTION
               "Car band value,The car value is multiple of 64kbps.
                Unit :kbps
               "
           ::= { hwVlanUpCarEntry  3 }

       hwVlanUpCarBurstValue OBJECT-TYPE
           SYNTAX Integer32 (2..8192)
           MAX-ACCESS read-write
           STATUS current
           DESCRIPTION
               "Car burst value.
                Unit:kbps
               "
           ::= { hwVlanUpCarEntry  4 }

       hwVlanUpCarIsUsed OBJECT-TYPE
           SYNTAX INTEGER
             {
               used(1),
               noUsed(2)
             }
           MAX-ACCESS read-only
           STATUS current
           DESCRIPTION
               "The flag indicates whether the carid is used.
                Options:
                1. used(1)    -The carid is used.
                2. noUsed(2)  -The carid is no-used.
               "
           ::= { hwVlanUpCarEntry  5 }

       hwVlanUpCarRowStatus OBJECT-TYPE
           SYNTAX RowStatus
           MAX-ACCESS read-create
           STATUS current
           DESCRIPTION
               "Row status, now support createAndGo(4),destroy(6).
               "
           ::= { hwVlanUpCarEntry  6 }

       hwVlanDownCarTable OBJECT-TYPE
           SYNTAX SEQUENCE OF HwVlanDownCarEntry
           MAX-ACCESS not-accessible
           STATUS current
           DESCRIPTION
               "Indicates the VLAN down direct CAR.
                The index of this table is hwVlanDownCarId.
               "
           ::= { hwVlanMngObject 16 }

       hwVlanDownCarEntry OBJECT-TYPE
           SYNTAX HwVlanDownCarEntry
           MAX-ACCESS not-accessible
           STATUS current
           DESCRIPTION
               "Indicates the VLAN down direct CAR.
                The index of this entry is hwVlanDownCarId.
               "
           INDEX { hwVlanDownCarId }
           ::= { hwVlanDownCarTable 1 }

       HwVlanDownCarEntry ::=
           SEQUENCE {
             hwVlanDownCarId
               Integer32,
             hwVlanDownCarName
               OCTET STRING,
             hwVlanDownCarBandValue
               Integer32,
             hwVlanDownCarBurstValue
               Integer32,
             hwVlanDownCarIsUsed
               INTEGER,
             hwVlanDownCarRowStatus
               RowStatus
            }

       hwVlanDownCarId OBJECT-TYPE
           SYNTAX Integer32 (1..4000)
           MAX-ACCESS read-only
           STATUS current
           DESCRIPTION
               "The index of the table, indicates a down direct carid.
               "
           ::= { hwVlanDownCarEntry  1 }

       hwVlanDownCarName OBJECT-TYPE
           SYNTAX OCTET STRING (SIZE (0..32))
           MAX-ACCESS read-write
           STATUS current
           DESCRIPTION
               "Down direct car name.
               "
           ::= { hwVlanDownCarEntry  2 }

       hwVlanDownCarBandValue OBJECT-TYPE
           SYNTAX Integer32 (64..1048512)
           MAX-ACCESS read-write
           STATUS current
           DESCRIPTION
               "Car band value,The car value is multiple of 64kbps.
                Unit: kbps
               "
           ::= { hwVlanDownCarEntry  3 }

       hwVlanDownCarBurstValue OBJECT-TYPE
           SYNTAX Integer32 (2..8192)
           MAX-ACCESS read-write
           STATUS current
           DESCRIPTION
               "Car burst value.
                Unit: kbps
               "
           ::= { hwVlanDownCarEntry  4 }

       hwVlanDownCarIsUsed OBJECT-TYPE
           SYNTAX INTEGER
             {
               used(1),
               noUsed(2)
             }
           MAX-ACCESS read-only
           STATUS current
           DESCRIPTION
               "The flag indicates whether the carid is used.
                Options:
                1. used(1)   -The carid is used.
                2. noUsed(2) -The carid is no-used.
               "
           ::= { hwVlanDownCarEntry  5 }

       hwVlanDownCarRowStatus OBJECT-TYPE
           SYNTAX RowStatus
           MAX-ACCESS read-create
           STATUS current
           DESCRIPTION
               "Row status, now support createAndGo(4),destroy(6).
               "
           ::= { hwVlanDownCarEntry  6 }

       hwVlanParaTable OBJECT-TYPE
           SYNTAX SEQUENCE OF HwVlanParaEntry
           MAX-ACCESS not-accessible
           STATUS current
           DESCRIPTION
               "Indicates the VLAN parameters, include hwVlanParaIndex, hwVlanMacLearnCpability, hwVlanMaxMacLearnNum,
                hwVlanUpdirectCar, hwVlanDownDirectCar, it is used to configure the VLAN param.
                The index of this table is hwVlanParamIndex.
               "
           ::= { hwVlanMngObject 17 }

       hwVlanParaEntry OBJECT-TYPE
           SYNTAX HwVlanParaEntry
           MAX-ACCESS not-accessible
           STATUS current
           DESCRIPTION
               "Indicates the VLAN parameters, include hwVlanParaIndex, hwVlanMacLearnCpability, hwVlanMaxMacLearnNum,
                hwVlanUpdirectCar, hwVlanDownDirectCar, it is used to configure the VLAN param.
                The index of this entry is hwVlanParamIndex.
               "
           INDEX { hwVlanParaIndex }
           ::= { hwVlanParaTable 1 }

       HwVlanParaEntry ::=
           SEQUENCE {
             hwVlanParaIndex
               VlanIndex,
             hwVlanMacLearnCpability
               INTEGER,
             hwVlanMaxMacLearnNum
               Integer32,
             hwVlanUpDirectCarID
               Integer32,
             hwVlanDownDirectCarID
               Integer32
            }

       hwVlanParaIndex OBJECT-TYPE
           SYNTAX VlanIndex
           MAX-ACCESS read-only
           STATUS current
           DESCRIPTION
               "The index of the table,the VLAN index means Vlan Id.
               "
           ::= { hwVlanParaEntry 1 }

       hwVlanMacLearnCpability OBJECT-TYPE
           SYNTAX INTEGER
            {
               enabled(1),
               disabled(2)
            }
           MAX-ACCESS read-write
           STATUS current
           DESCRIPTION
               "MAC learning or not flag by VLAN.
                Options:
                1. enabled(1)    -Enable MAC learning by VLAN.
                2. disabled(2)   -Disable MAC learning by VLAN.
               "
           DEFVAL { enabled }
           ::= { hwVlanParaEntry 2 }

       hwVlanMaxMacLearnNum OBJECT-TYPE
           SYNTAX Integer32 (0..255)
           MAX-ACCESS read-write
           STATUS current
           DESCRIPTION
               "The VLAN max mac learn number.
               "
           DEFVAL { 255 }
           ::= { hwVlanParaEntry 3 }

       hwVlanUpDirectCarID OBJECT-TYPE
           SYNTAX Integer32 (1..4000)
           MAX-ACCESS read-write
           STATUS current
           DESCRIPTION
               "The VLAN up direct carID.
               "
           DEFVAL { 1 }
           ::= { hwVlanParaEntry 4 }

       hwVlanDownDirectCarID OBJECT-TYPE
           SYNTAX Integer32 (1..4000)
           MAX-ACCESS read-write
           STATUS current
           DESCRIPTION
               "The VLAN down direct carID.
               "
           DEFVAL { 1 }
           ::= { hwVlanParaEntry 5 }

       hwMethL2Vlan OBJECT-TYPE
           SYNTAX Integer32 (0..4095)
           MAX-ACCESS read-write
           STATUS current
           DESCRIPTION
               "set the Meth L2 function of the VLAN.
               "
           ::= { hwVlanMngObject 23 }

       hwDocsDefaultSrvVlanID OBJECT-TYPE
           SYNTAX Integer32 (1..4093)
           MAX-ACCESS read-write
           STATUS current
           DESCRIPTION
               "Indicates the service svlan of DOCSIS service.
                The default value is 1.
               "
           ::= { hwVlanMngObject 24 }

       hwStackingVlanOuterEthernetType OBJECT-TYPE
           SYNTAX Unsigned32 (1536..65535)
           MAX-ACCESS read-write
           STATUS current
           DESCRIPTION
               "Describes the Ethernet protocol type of the outer VLAN tag supported by VLAN stacking.
                Range: 0x600-0xffff
                Default: 0x8100
               "
           ::= { hwVlanMngObject 65000 }

       hwDot1adTpid OBJECT-TYPE
           SYNTAX Unsigned32 (1536..65535)
           MAX-ACCESS read-write
           STATUS current
           DESCRIPTION
               "Describes the value of the 802.1ad Ethernet protocol type.
                The Ethernet protocol type of the outer VLAN tag of a port can
                be configured to dot1q or dot1ad. The value of dot1q is invariably 0x8100;
                the value of dot1ad is configurable, but cannot be the values of
                other standard protocols, such as 0x0806.
                The default value of dot1ad is 0x88a8.
                Range: 0x600-0xffff
               "
           ::= { hwVlanMngObject 65001 }

       hwPortOuterEthernetTypeTable OBJECT-TYPE
           SYNTAX SEQUENCE OF HwPortOuterEthernetTypeEntry
           MAX-ACCESS not-accessible
           STATUS current
           DESCRIPTION
               "Describes the Ethernet protocol type of the outer VLAN tag of a port.
                The index of this table is ifIndex (for details about how to calculate the value of
                ifIndex, see the MA5600T ifIndex MIB Encoding Rules).
               "
           ::= { hwVlanMngObject 65002 }

       hwPortOuterEthernetTypeEntry OBJECT-TYPE
           SYNTAX HwPortOuterEthernetTypeEntry
           MAX-ACCESS not-accessible
           STATUS current
           DESCRIPTION
               "Describes the Ethernet protocol type of the outer VLAN tag of a port.
                The index of this entry is ifIndex (for details about how to calculate the value of
                ifIndex, see the MA5600T ifIndex MIB Encoding Rules).
               "
           INDEX { ifIndex }
           ::= { hwPortOuterEthernetTypeTable 1 }

       HwPortOuterEthernetTypeEntry ::=
           SEQUENCE {
             hwPortOuterEthernetType
               INTEGER
            }

       hwPortOuterEthernetType OBJECT-TYPE
           SYNTAX INTEGER
             {
               invalid(-1),
               dot1qTpid(1),
               dot1adTpid(2)
             }
           MAX-ACCESS read-write
           STATUS current
           DESCRIPTION
               "Indicates the Ethernet protocol type of the outer VLAN tag of a port.
                Options:
                1. invalid(-1)   -it indicates that the port does not support the
                                  Ethernet protocol type of the outer VLAN. During the query,
                                  the invalid value -1 is fixedly returned.
                2. dot1qTpid(1)  -it is valid for all service streams on the port.
                3. dot1adTpid(2) -it is valid for only switching-oriented and
                                  connection-oriented service streams with two VLAN tags on the port.
                Default: dot1qTpid(1)
               "
           DEFVAL { dot1qTpid }
           ::= { hwPortOuterEthernetTypeEntry 1 }

       hwVlanLocalSwitch OBJECT-TYPE
           SYNTAX INTEGER
             {
               enable(1),
               disable(2)
             }
           MAX-ACCESS read-write
           STATUS current
           DESCRIPTION
               "Set the global Local VLAN switch.
                Options:
                1. enable(1)  -the switch is enable.
                2. disable(2) -the switch is disabled.
                Default: disable(2)
               "
           ::= { hwVlanMngObject 65003 }

       hwLocalVlanTable OBJECT-TYPE
           SYNTAX SEQUENCE OF HwLocalVlanEntry
           MAX-ACCESS not-accessible
           STATUS current
           DESCRIPTION
               "Indicates the Local VLAN, it is used to configure the Local VLAN.
                The index of this table is hwVlanIndex.
               "
           ::= { hwVlanMngObject 65004 }

       hwLocalVlanEntry OBJECT-TYPE
           SYNTAX HwLocalVlanEntry
           MAX-ACCESS not-accessible
           STATUS current
           DESCRIPTION
               "Indicates the Local VLAN, it is used to configure the Local VLAN.
                The index of this entry is hwVlanIndex.
               "
           INDEX { hwVlanIndex }
           ::= { hwLocalVlanTable 1 }

       HwLocalVlanEntry ::=
           SEQUENCE {
             hwLocalVlan
                 INTEGER
            }

       hwLocalVlan OBJECT-TYPE
           SYNTAX INTEGER
             {
               enable(1),
               disable(2)
             }
           MAX-ACCESS read-write
           STATUS current
           DESCRIPTION
               "The flag indicates whether to set the Local VLAN.
                Options:
                1. enable(1)  -Enable local VLAN.
                2. disable(2) -Disable local VLAN.
               "
           DEFVAL { disable }
           ::= { hwLocalVlanEntry 1 }

        hwVlanInterfaceTable OBJECT-TYPE
           SYNTAX SEQUENCE OF HwVlanInterfaceEntry
           MAX-ACCESS not-accessible
           STATUS current
           DESCRIPTION
               "Describes VLAN interface management, including IP address
                management, enabling and disabling of the DHCP client, and
                DHCP client option 60.
               "
           ::= { hwVlanMngObject 2 }

       hwVlanInterfaceEntry OBJECT-TYPE
           SYNTAX HwVlanInterfaceEntry
           MAX-ACCESS not-accessible
           STATUS current
           DESCRIPTION
               "Describes VLAN interface management, including IP address
                management, enabling and disabling of the DHCP client, and
                DHCP client option 60.
                The index of this entry is hwVlanInterfaceID.
               "
           INDEX { hwVlanInterfaceID }
           ::= { hwVlanInterfaceTable 1 }

       HwVlanInterfaceEntry ::=
           SEQUENCE {
             hwVlanInterfaceID
               Integer32,
             hwVlanID
               Integer32,
             hwVlanIpAddress
               IpAddress,
             hwVlanIpAddressMask
               IpAddress,
             hwVlanInterfaceAdminStatus
               INTEGER,
             hwVlanInterfaceFrameType
               INTEGER,
             hwInterfaceRowStatus
               RowStatus,
             hwVlanInterfaceLinkStatus
               INTEGER,
             hwVlanIfIPMode
               INTEGER,
             hwVlanIfDhcpClientOption60
               OCTET STRING,
             hwVlanIfVlanEncapMode
               INTEGER,
             hwVlanIfVlanInnerLabel
               Integer32,
             hwVlanIfDhcpsStatus
               INTEGER,
             hwIPv6MTU
               Integer32,
	     hwIPv4MTU
               Integer32,
             hwVlanIfDhcpsLeaseMode
               INTEGER,
             hwVlanIfDhcpsLeaseDay
               Integer32,
             hwVlanIfDhcpsLeaseHour
               Integer32,
             hwVlanIfDhcpsLeaseMinute
               Integer32,
             hwVlanIfDhcpsStartIpAddr
               IpAddress,
             hwVlanIfDhcpsEndIpAddr
               IpAddress,
             hwVlanIfDhcpsMask
               IpAddress,
             hwVlanIfDhcpsGateway
               OCTET STRING,
             hwVlanIfDhcpsGatewayUndo
               OCTET STRING,
             hwVlanIfDhcpsOption
               INTEGER,
             hwVlanIfDhcpsOptCode
               Integer32,
             hwVlanIfDhcpsSubOptCode
               Integer32,
             hwVlanIfDhcpsOptType
               INTEGER,
             hwVlanIfDhcpsOptStr
               OCTET STRING,
             hwVlanIfDhcpsDns
               OCTET STRING,
             hwVlanIfDhcpsDnsUndo
               OCTET STRING
            }

       hwVlanInterfaceID OBJECT-TYPE
           SYNTAX Integer32
           MAX-ACCESS read-only
           STATUS current
           DESCRIPTION
               "Indicates the index of a VLAN interface, which maps a VLAN ID.
                For example, the index of VLAN interface 3 is 3.
               "
           ::= { hwVlanInterfaceEntry 1 }

       hwVlanID OBJECT-TYPE
           SYNTAX Integer32
           MAX-ACCESS read-only
           STATUS current
           DESCRIPTION
               "Indicates the corresponding VLAN ID of a VLAN interface.
               "
           ::= { hwVlanInterfaceEntry 2 }

       hwVlanIpAddress OBJECT-TYPE
           SYNTAX IpAddress
           MAX-ACCESS read-write
           STATUS current
           DESCRIPTION
               "Indicates the IP address of a VLAN interface.
                Default: 0.0.0.0.
               "
           ::= { hwVlanInterfaceEntry 3 }

       hwVlanIpAddressMask OBJECT-TYPE
           SYNTAX IpAddress
           MAX-ACCESS read-write
           STATUS current
           DESCRIPTION
               "Indicates the IP address subnet mask.
               "
           ::= { hwVlanInterfaceEntry 4 }

       hwVlanInterfaceAdminStatus OBJECT-TYPE
           SYNTAX INTEGER
             {
               up(1),
               down(2)
             }
           MAX-ACCESS read-write
           STATUS current
           DESCRIPTION
               "Indicates the management status of a VLAN interface.
                Options:
                1. up(1)   -indicates up status.
                2. down(2) -indicates down status.
                Default: up(1)
                "
           ::= { hwVlanInterfaceEntry 5 }

       hwVlanInterfaceFrameType OBJECT-TYPE
           SYNTAX INTEGER
             {
               ethernetii(1),
               ethernetsnap(2),
               ethernet8022(3),
               ethernet8023(4)
             }
           MAX-ACCESS read-write
           STATUS current
           DESCRIPTION
               "Indicates the type of the frame that can be received by a VLAN interface.
                Options:
                1. ethernetii(1)    -For the frame format of ethernetii(1), see RFC894.
                2. ethernetsnap(2)  -The value is not supported.
                3. ethernet8022(3)  -The value is not supported.
                4. ethernet8023(4)  -The value is not supported.
                Currently, only ethernetii(1) is supported.
                "
           ::= { hwVlanInterfaceEntry 6 }

       hwInterfaceRowStatus OBJECT-TYPE
           SYNTAX RowStatus
           MAX-ACCESS read-create
           STATUS current
           DESCRIPTION
               "Indicates the row status. It is used for create, delete and modify operations.
                Options:
                1. createAndGo(4)
                2. destroy(6)
                3. active(1)
               "
           ::= { hwVlanInterfaceEntry 7 }

       hwVlanInterfaceLinkStatus OBJECT-TYPE
           SYNTAX INTEGER
             {
               up(1),
               down(2)
             }
           MAX-ACCESS read-only
           STATUS current
           DESCRIPTION
               "Indicates the protocol status of a link that is contained in a VLAN interface.
                Options:
                1. up(1)     -The protocol status of a link that is contained in a VLAN interface is up.
                2. down(2)   -The protocol status of a link that is contained in a VLAN interface is down.
               "
           ::= { hwVlanInterfaceEntry 8 }

       hwVlanIfIPMode OBJECT-TYPE
           SYNTAX INTEGER
             {
               static(1),
               dhcp(2)
             }
           MAX-ACCESS read-write
           STATUS current
           DESCRIPTION
               "Indicates the mode of obtaining an IP address.
                Options:
                1. static(1)   -Configured statically.
                2. dhcp(2)     -Obtained through DHCP.
               "
           ::= { hwVlanInterfaceEntry 9 }

       hwVlanIfDhcpClientOption60 OBJECT-TYPE
           SYNTAX OCTET STRING (SIZE (0..32))
           MAX-ACCESS read-write
           STATUS current
           DESCRIPTION
               "Indicates the option 60 information carried in DHCP packets that are sent by a L3
                interface when obtaining an IP address in the DHCP mode.
                Range: 0-32 characters
               "
           ::= { hwVlanInterfaceEntry 10 }

       hwVlanIfVlanEncapMode OBJECT-TYPE
           SYNTAX INTEGER
             {
               singleTag(1),
               doubleTag(2)
             }
           MAX-ACCESS read-write
           STATUS current
           DESCRIPTION
               "Used to configure the VLAN encapsulation mode of a VLAN interface.
                Options:
                1. singleTag(1)     -Single tag VLAN encapsulation mode.
                2. doubleTag(2)     -Double tag VLAN encapsulation mode.
                Default: singleTag(1)
                "
           ::= { hwVlanInterfaceEntry 11 }

       hwVlanIfVlanInnerLabel OBJECT-TYPE
           SYNTAX Integer32 (1..4095)
           MAX-ACCESS read-write
           STATUS current
           DESCRIPTION
               "Used to configure the inner VLAN ID when the VLAN encapsulation mode of a VLAN interface is double-tag mode.
                Range: 1-4095
                Default: 1
               "
           ::= { hwVlanInterfaceEntry 12 }

       hwVlanIfDhcpsStatus OBJECT-TYPE
           SYNTAX INTEGER
             {
               disable(1),
               enable(2)
             }
           MAX-ACCESS read-write
           STATUS current
       DESCRIPTION
           "Describes the mode of dhcp server on this interface.
                Options:
                1. disable(1) -disable dhcp server.
                2. enable(2)  -enable dhcp server.
                Default: disable(1)
               "
            ::= { hwVlanInterfaceEntry 13 }

       hwIPv6MTU OBJECT-TYPE
           SYNTAX Integer32 (-1|1280..1499|1501..9600)
           MAX-ACCESS read-write
           STATUS current
           DESCRIPTION
               "Used to configure the maximum transmission unit of vlanif.If you set it on one vlanif,all the vlanif will
                be configured. For P300 device, the node can take effect on IPV4 and IPV6. For Saturn device, it only takes 
                effect on IPV6.
                Range: -1,1280-1499,1501-9600. For P300 device, the range is -1,1501-1560. For Saturn device, the range is
                -1,1280-1499,1501-9600. 
                Deafult:-1,this value means the MTU of vlanif is the default value(for example: 1500).
               "
           ::= { hwVlanInterfaceEntry 14 }

       hwIPv4MTU OBJECT-TYPE
           SYNTAX Integer32 (-1|1501..9600)
           MAX-ACCESS read-write
           STATUS current
           DESCRIPTION
               "Used to configure the maximum transmission unit of vlanif. The node is only supported on Saturn device. It
               only takes effect on IPV4.
                Range: -1,1501-9600
                Deafult:-1,this value means the MTU of vlanif is the default value(for example: 1500).
               "
           ::= { hwVlanInterfaceEntry 15 }

       hwVlanIfDhcpsLeaseMode OBJECT-TYPE
           SYNTAX INTEGER
             {
               delete(0),
               limited(1),
               unlimited(2)
             }
           MAX-ACCESS read-write
           STATUS current
           DESCRIPTION
               "Indicates that the lease mode.
                Options:
                1. delete(0)     -Set zero to delete the current lease configuration.
                2. limited(1)    -The lease mode is limited.
                3. unlimited(2)  -The lease mode is unlimited.
                Default: limited(1)
                If you want to set limited mode, you have to set leaseDay, leaseHour and leaseMin simultaneously.
               "
           ::= { hwVlanInterfaceEntry 16 }

       hwVlanIfDhcpsLeaseDay OBJECT-TYPE
           SYNTAX Integer32 (-1|0..999)
           MAX-ACCESS read-write
           STATUS current
           DESCRIPTION
               "Used to configure the day number of leasing dhcp server time.
                Range: -1, 0-999.
                Deafult:-1, this value means the lease mode is unlimited or dhcp server is unset.
               "
           ::= { hwVlanInterfaceEntry 17 }

       hwVlanIfDhcpsLeaseHour OBJECT-TYPE
           SYNTAX Integer32 (-1|0..23)
           MAX-ACCESS read-write
           STATUS current
           DESCRIPTION
               "Used to configure the hour number of leasing dhcp server time.
                Range: -1, 0-23.
                Deafult:-1, this value means the lease mode is unlimited or dhcp server is unset.
               "
           ::= { hwVlanInterfaceEntry 18 }

       hwVlanIfDhcpsLeaseMinute OBJECT-TYPE
           SYNTAX Integer32 (-1|0..59)
           MAX-ACCESS read-write
           STATUS current
           DESCRIPTION
               "Used to configure the minute number of leasing dhcp server time.
                Range: -1, 0-59.
                Deafult:-1, this value means the lease mode is unlimited or dhcp server is unset.
               "
           ::= { hwVlanInterfaceEntry 19 }

       hwVlanIfDhcpsStartIpAddr OBJECT-TYPE
           SYNTAX IpAddress
           MAX-ACCESS read-write
           STATUS current
           DESCRIPTION
               "Indicates the start address of the ip range.
                Default: 0.0.0.0.
                When you set 0.0.0.0, it means to delete the configuration of ip-range.
                However, you need to set 0.0.0.0 for endIpAddr simultaneously to delete ip-range.
               "
           ::= { hwVlanInterfaceEntry 20 }
           
       hwVlanIfDhcpsEndIpAddr OBJECT-TYPE
           SYNTAX IpAddress
           MAX-ACCESS read-write
           STATUS current
           DESCRIPTION
               "Indicates the end address of the ip range.
                Default: 0.0.0.0.
                When you set 0.0.0.0, it means to delete the configuration of ip-range.
                However, you need to set 0.0.0.0 for startIpAddr simultaneously to delete ip-range.
               "
           ::= { hwVlanInterfaceEntry 21 }
           
       hwVlanIfDhcpsMask OBJECT-TYPE
           SYNTAX IpAddress
           MAX-ACCESS read-write
           STATUS current
           DESCRIPTION
               "Indicates the mask of the dhcp server.
                Default: 0.0.0.0.
                Please set 0.0.0.0 to delete current mask.
               "
           ::= { hwVlanInterfaceEntry 22 }

       hwVlanIfDhcpsGateway OBJECT-TYPE
           SYNTAX OCTET STRING (SIZE (0..129))
           MAX-ACCESS read-write
           STATUS current
           DESCRIPTION
               "String of gateway ip addresses for DHCP server.
                Since mostly 8 ip addresses can be configured for a pool
                totally, a string is defined to get or configure 8 ip
                addresses at a time. Please use ',' to separate them.
               "
           ::= { hwVlanInterfaceEntry 23 }

       hwVlanIfDhcpsGatewayUndo OBJECT-TYPE
           SYNTAX OCTET STRING (SIZE (0..16))
           MAX-ACCESS read-write
           STATUS current
           DESCRIPTION
               "A gateway ip address to be deleted. This object is
                only for deleting a given ip address of gateway-list.
               "
           ::= { hwVlanInterfaceEntry 24 }

       hwVlanIfDhcpsOption OBJECT-TYPE
           SYNTAX INTEGER
             {
              config(1),
              delete(2)
             }
           MAX-ACCESS read-write
           STATUS current
           DESCRIPTION
               "Indicates the option operation of DHCP server.
                Default: config(1).
               "
           ::= { hwVlanInterfaceEntry 25 }

       hwVlanIfDhcpsOptCode OBJECT-TYPE
           SYNTAX Integer32 (0..254)
           MAX-ACCESS read-write
           STATUS current
           DESCRIPTION
               "Indicates the option code of DHCP server.
                Default: 0. This means option is unset.
               "
           ::= { hwVlanInterfaceEntry 26 }

       hwVlanIfDhcpsSubOptCode OBJECT-TYPE
           SYNTAX Integer32 (0..254)
           MAX-ACCESS read-write
           STATUS current
           DESCRIPTION
               "Indicates the sub-option code of DHCP server.
                Setting the node, this node must match with hwVlanIfDhcpsOptType. 
                When the value is 0, it means setting option.
                When the value is not 0, it means setting sub-option.
                The rules ara as follow:
                1.subOptCode == 0, optType can choose all the types.
                2.subOptCode == 1, optType must be hex.
                3.subOptCode == 2, optType must be ipAddress.
                4.subOptCode == 3, optType must be ascii.
                5.subOptCode == 4, optType must be cipher.
               "
           ::= { hwVlanInterfaceEntry 27 }
       
       hwVlanIfDhcpsOptType OBJECT-TYPE
           SYNTAX INTEGER
             {
               unset(0),
               ascii(1),
               hex(2),
               cipher(3),
               ipAddress(4)
             }
           MAX-ACCESS read-write
           STATUS current
           DESCRIPTION
               "Indicates the option type of DHCP server option.
                The type you choose must match the sub-option code.
                Types:
                1. unset(0)
                2. ascii(1)
                3. hex(2)
                4. cipher(3)
                5. ipAddress(4)
               "
           ::= { hwVlanInterfaceEntry 28 }

       hwVlanIfDhcpsOptStr OBJECT-TYPE
           SYNTAX OCTET STRING (SIZE (0..256))
           MAX-ACCESS read-write
           STATUS current
           DESCRIPTION
               "This node is an IP string of dhcp server option.
                The string you input must match the type that you choose in hwVlanIfDhcpsOptType.
               "
           ::= { hwVlanInterfaceEntry 29 }

       hwVlanIfDhcpsDns OBJECT-TYPE
           SYNTAX OCTET STRING (SIZE (0..129))
           MAX-ACCESS read-write
           STATUS current
           DESCRIPTION
               "String of dns server ip addresses for DHCP clients.
                Since mostly 8 ip can be configured for a pool
                totally, a string is defined to get or configure 8 ip
                addresses at a time. Please use ',' to separate them.
               "
           ::= { hwVlanInterfaceEntry 30 }

       hwVlanIfDhcpsDnsUndo OBJECT-TYPE
           SYNTAX OCTET STRING (SIZE (0..16))
           MAX-ACCESS read-write
           STATUS current
           DESCRIPTION
               "A dns server ip address to be deleted. This object is
                only for deleting a given ip address of dns-list.
               "
           ::= { hwVlanInterfaceEntry 31 }

       hwVlanInterfaceSubIpAddrTable OBJECT-TYPE
           SYNTAX SEQUENCE OF HwVlanInterfaceSubIpAddrEntry
           MAX-ACCESS not-accessible
           STATUS current
           DESCRIPTION
               "Describes management of the secondary IP addresses of a VLAN interface.
               "
           ::= { hwVlanMngObject 22 }

       hwVlanInterfaceSubIpAddrEntry OBJECT-TYPE
           SYNTAX HwVlanInterfaceSubIpAddrEntry
           MAX-ACCESS not-accessible
           STATUS current
           DESCRIPTION
               "Describes management of the secondary IP addresses of a VLAN interface.
                The indexes of this entry are hwVlanInterfaceIDWithSub, hwVlanSubIpAddress and hwVlanSubIpAddressMask.
               "
           INDEX { hwVlanInterfaceIDWithSub, hwVlanSubIpAddress, hwVlanSubIpAddressMask}
           ::= { hwVlanInterfaceSubIpAddrTable 1 }

       HwVlanInterfaceSubIpAddrEntry ::=
           SEQUENCE {
             hwVlanInterfaceIDWithSub
               Integer32,
             hwVlanSubIpAddress
               IpAddress,
             hwVlanSubIpAddressMask
               IpAddress,
             hwInterfaceSubIpAddrRowStatus
               RowStatus
            }

       hwVlanInterfaceIDWithSub OBJECT-TYPE
           SYNTAX Integer32
           MAX-ACCESS read-only
           STATUS current
           DESCRIPTION
               "Indicates the index of a VLAN interface, which maps a VLAN ID. For example,
                the index of VLAN interface 3 is 3.
               "
           ::= { hwVlanInterfaceSubIpAddrEntry 1 }

       hwVlanSubIpAddress OBJECT-TYPE
           SYNTAX IpAddress
           MAX-ACCESS read-only
           STATUS current
           DESCRIPTION
               "Indicates the secondary IP address of a VLAN interface.
               "
           ::= { hwVlanInterfaceSubIpAddrEntry 2 }

       hwVlanSubIpAddressMask OBJECT-TYPE
           SYNTAX IpAddress
           MAX-ACCESS read-only
           STATUS current
           DESCRIPTION
               "Indicates the subnet mask of the secondary IP address of a VLAN interface.
               "
           ::= { hwVlanInterfaceSubIpAddrEntry 3 }

       hwInterfaceSubIpAddrRowStatus OBJECT-TYPE
           SYNTAX RowStatus
           MAX-ACCESS read-create
           STATUS current
           DESCRIPTION
               "Indicates the row status. It is used for create, modify and delete operations.
                Options:
                1. createAndGo(4)
                2. destroy(6)
                3. active(1)
               "
           ::= { hwVlanInterfaceSubIpAddrEntry 4 }

       hwPacketTunnelTable    OBJECT-TYPE
           SYNTAX          SEQUENCE OF HwPacketTunnelEntry
           MAX-ACCESS      not-accessible
           STATUS          current
           DESCRIPTION
               "Used for setting and querying the status of the L2 transparent transmission of RIP packets and VTP/CDP packets in a VLAN.
                The index of this table is hwVlanIndex.
               "
           ::= { hwVlanMngObject 21 }

       hwPacketTunnelEntry    OBJECT-TYPE
           SYNTAX          HwPacketTunnelEntry
           MAX-ACCESS      not-accessible
           STATUS          current
           DESCRIPTION
               "Used for setting and querying the status of the L2 transparent transmission of RIP packets and VTP/CDP packets in a VLAN.
                The index of this entry is hwVlanIndex.
               "
           INDEX   { hwVlanIndex }
           ::= { hwPacketTunnelTable 1 }

       HwPacketTunnelEntry ::=
           SEQUENCE {
              hwPacketTunnelRip
                   INTEGER,
              hwPacketTunnelVTPCDP
                   INTEGER
             }

       hwPacketTunnelRip        OBJECT-TYPE
           SYNTAX INTEGER
            {
               enable(1),
               disable(2)
            }
           MAX-ACCESS  read-create
           STATUS      current
           DESCRIPTION
               "Indicates the transparent transmission of RIP packets in a VLAN.
                Options:
                1. enable(1)        -Enable transparent transmission of RIP packets in a VLAN.
                2. disable(2)       -Disable transparent transmission of RIP packets in a VLAN.
                Default: disable(2)
               "
           ::= { hwPacketTunnelEntry 1}

       hwPacketTunnelVTPCDP OBJECT-TYPE
           SYNTAX INTEGER
             {
               enable(1),
               disable(2)
             }
           MAX-ACCESS  read-create
           STATUS      current
           DESCRIPTION
               "Indicates the transparent transmission of VTP/CDP packets in a VLAN.
        Options:
                1. enable(1)        -Enable transparent transmission of VTP/CDP packets in a VLAN.
                2. disable(2)       -Disable transparent transmission of VTP/CDP packets in a VLAN.
        Default: disable(2)
               "
           ::= { hwPacketTunnelEntry 2}

       hwBpduTunnelTable    OBJECT-TYPE
           SYNTAX   SEQUENCE OF HwBpduTunnelEntry
           MAX-ACCESS      not-accessible
           STATUS          current
           DESCRIPTION
               "Used for setting and querying the status of the L2 transparent transmission of BPDU packets.
                The index of this table is hwVlanIndex.
               "
           ::= { hwVlanMngObject 18 }

       hwBpduTunnelEntry    OBJECT-TYPE
           SYNTAX          HwBpduTunnelEntry
           MAX-ACCESS      not-accessible
           STATUS          current
           DESCRIPTION
               "Used for setting and querying the status of the L2 transparent transmission of BPDU packets.
                The index of this entry is hwVlanIndex.
               "
           INDEX   { hwVlanIndex }
           ::= { hwBpduTunnelTable 1 }

       HwBpduTunnelEntry ::=
           SEQUENCE {
                hwBpduTunnel
                    INTEGER
              }

       hwBpduTunnel OBJECT-TYPE
           SYNTAX  INTEGER
            {
               enable(1),
               disable(2)
            }
           MAX-ACCESS  read-create
           STATUS      current
           DESCRIPTION
               "Indicates the status of the L2 transparent transmission of BDPU packets in a VLAN.
                Options:
                1. enable(1)        -Enable transparent transmission of BDPU packets in a VLAN.
                2. disable(2)       -Disable transparent transmission of BDPU packets in a VLAN.
                Default: disable(2)
               "
           ::= { hwBpduTunnelEntry 1}

       hwVOIPAddressTable OBJECT-TYPE
           SYNTAX SEQUENCE OF HwVOIPAddressEntry
           MAX-ACCESS not-accessible
           STATUS current
           DESCRIPTION
               "VOIP multiply IP table.
                The index of this table is hwVOIPAddressIndex
               "
           ::= { hwVlanMngObject 19 }

       hwVOIPAddressEntry OBJECT-TYPE
           SYNTAX HwVOIPAddressEntry
           MAX-ACCESS not-accessible
           STATUS current
           DESCRIPTION
               "VOIP multiply IP table.
                The index of this entry is hwVOIPAddressIndex
               "
           INDEX { hwVOIPAddressIndex }
           ::= { hwVOIPAddressTable 1 }

       HwVOIPAddressEntry ::=
           SEQUENCE {
             hwVOIPAddressIndex
               Unsigned32,
             hwVOIPIPType
               INTEGER,
             hwVOIPIPAddress
               IpAddress,
             hwVOIPSubMask
               IpAddress,
             hwVOIPGateway
               IpAddress,
             hwVOIPMACAddress
               OCTET STRING,
             hwVOIPVlanTagIdentifier
               Integer32,
             hwVOIPQosIPStrategy
               INTEGER,
             hwVOIPAddressRowStatus
               RowStatus,
             hwVOIPAddressObtainMode
               INTEGER,
             hwVOIPPPPOEClientName
               OCTET STRING,
             hwVOIPIPAddressSrc
               INTEGER                  
           }

       hwVOIPAddressIndex OBJECT-TYPE
           SYNTAX Unsigned32 (0..63|4294967295)
           MAX-ACCESS not-accessible
           STATUS current
           DESCRIPTION
               "the index scope is 0-63
               "
           ::= { hwVOIPAddressEntry 1 }

       hwVOIPIPType OBJECT-TYPE
           SYNTAX INTEGER
               {
               media(1),
               signaling(2)
               }
           MAX-ACCESS read-create
           STATUS current
           DESCRIPTION
               "Indicates the type of VOIP IP.
                Options:
                1. media(1)  -indicates that the type of VOIP IP is media.
                2. signaling(2) -indicates that the type of VOIP IP is signaling.
               "
           ::= { hwVOIPAddressEntry 2 }

       hwVOIPIPAddress OBJECT-TYPE
           SYNTAX IpAddress
           MAX-ACCESS read-create
           STATUS current
           DESCRIPTION
               "IP address"
           ::= { hwVOIPAddressEntry 3 }

       hwVOIPSubMask OBJECT-TYPE
           SYNTAX IpAddress
           MAX-ACCESS read-only
           STATUS current
           DESCRIPTION
               "subMask of VAG "
           ::= { hwVOIPAddressEntry 4 }

       hwVOIPGateway OBJECT-TYPE
           SYNTAX IpAddress
           MAX-ACCESS  read-create
           STATUS current
           DESCRIPTION
               "gateway of VAG"
           ::= { hwVOIPAddressEntry 5 }

       hwVOIPMACAddress OBJECT-TYPE
           SYNTAX OCTET STRING (SIZE(1..17))
           MAX-ACCESS read-only
           STATUS current
           DESCRIPTION
               "MAC address"
           ::= { hwVOIPAddressEntry  6 }

       hwVOIPVlanTagIdentifier OBJECT-TYPE
          SYNTAX Integer32 (0..4095)
          MAX-ACCESS read-only
          STATUS current
          DESCRIPTION
              "vlanid of VAG"
          ::= { hwVOIPAddressEntry 7 }

       hwVOIPQosIPStrategy OBJECT-TYPE
          SYNTAX INTEGER
              {
              tos(1),
              dscp(2)
              }
          MAX-ACCESS read-only
          STATUS current
          DESCRIPTION
              "Indicates the qos ip strategy
        Options:
        1. tos(1)  -indicates that the qos ip strategy is tos.
        2. dscp(2) -indicates that the qos ip strategy is dscp."
          ::= { hwVOIPAddressEntry 8 }

       hwVOIPAddressRowStatus OBJECT-TYPE
           SYNTAX  RowStatus
           MAX-ACCESS  read-create
           STATUS  current
           DESCRIPTION
               "Indicates the status of this conceptual row.
                Options:
                1. active(1)
                2. createAndGo(4)
                3. destroy(6)
                Until instances of all corresponding columns are appropriately configured,
                the value of the corresponding instance of the hwAddressRowStatus column is
                'notReady'.
               "
           ::= { hwVOIPAddressEntry 9 }

       hwVOIPAddressObtainMode OBJECT-TYPE
          SYNTAX INTEGER
              {
              static(1),
              pppoe(2),
              dhcp(3)
              }
          MAX-ACCESS read-only
          STATUS current
          DESCRIPTION
              "ip address obtain mode:
               Options:
               1. static(1) -static config
               2. pppoe(2)  -pppoe dynamic obtain
               3. dhcp(3)   -dhcp dynamic obtain
              "
          ::= { hwVOIPAddressEntry 10 }

       hwVOIPPPPOEClientName OBJECT-TYPE
           SYNTAX OCTET STRING (SIZE(0..65))
           MAX-ACCESS read-only
           STATUS current
           DESCRIPTION
               "ip address name of pppoe dynamic obtain, the same as pppoe client name"
           ::= { hwVOIPAddressEntry  11 }

       hwVOIPIPAddressSrc OBJECT-TYPE
           SYNTAX INTEGER
               {
               static(0),
               dhcp(1)
               }
           MAX-ACCESS read-only
           STATUS current
           DESCRIPTION
               "Indicates the source type of IP.
                Options: 
                1. static(0)  -indicates that the source type of IP is static.
                2. dhcp(1)    -indicates that the source type of IP is dhcp.
               "
           ::= { hwVOIPAddressEntry 12 }         
                 
       hwVOIPQosTable OBJECT-TYPE
           SYNTAX SEQUENCE OF HwVOIPQosEntry
           MAX-ACCESS not-accessible
           STATUS current
           DESCRIPTION
               "Describes the Qos IP tos and VLAN priority
                The index of this table is hwVOIPAddressIndex
               "
           ::= { hwVlanMngObject 20 }

       hwVOIPQosEntry OBJECT-TYPE
           SYNTAX HwVOIPQosEntry
           MAX-ACCESS not-accessible
           STATUS current
           DESCRIPTION
               "Describes the Qos IP tos and VLAN priority
                The index of this entry is hwVOIPAddressIndex
               "
           INDEX { hwVOIPAddressIndex}
           ::= { hwVOIPQosTable 1 }

       HwVOIPQosEntry ::=
           SEQUENCE {
             hwVOIPQosIPTosValue
               Integer32,
             hwVOIPQosIPDscpValue
               Integer32,    
             hwVOIPQosVlanPriority     
               Integer32,
             hwVOIPQosIPAddressSrc
               INTEGER
           }

       hwVOIPQosIPTosValue OBJECT-TYPE
           SYNTAX Integer32 (0..255)
           MAX-ACCESS read-create
           STATUS current
           DESCRIPTION
               "Qos value of tos"
           ::= { hwVOIPQosEntry 1 }

       hwVOIPQosIPDscpValue OBJECT-TYPE
           SYNTAX Integer32 (0..255)
           MAX-ACCESS read-create
           STATUS current
           DESCRIPTION
               "Qos value of dscp"
           ::= { hwVOIPQosEntry 2 }

       hwVOIPQosVlanPriority  OBJECT-TYPE
           SYNTAX Integer32 (0..7)
           MAX-ACCESS read-create
           STATUS current
           DESCRIPTION
               "Qos VLAN priority"
           ::= { hwVOIPQosEntry 3 }

       hwVOIPQosIPAddressSrc OBJECT-TYPE
           SYNTAX INTEGER
               {
               static(0),
               dhcp(1)
               }
           MAX-ACCESS read-only
           STATUS current
           DESCRIPTION
               "Indicates the source type of IP.
                Options: 
                1. static(0)  -indicates that the source type of IP is static.
                2. dhcp(1)    -indicates that the source type of IP is dhcp.
               "
           ::= { hwVOIPQosEntry 4 }     
             
       hwVlanSrvProfTable OBJECT-TYPE
           SYNTAX SEQUENCE OF HwVlanSrvProfEntry
           MAX-ACCESS not-accessible
           STATUS current
           DESCRIPTION
               "Describes the attributes of a VLAN service profile, used for adding or deleting
                a VLAN service profile, or modifying the status of the attributes in an existing
                VLAN service profile.
                The index of this table is hwVlanSrvProfName.
               "
           ::= { hwVlanMngObject 25 }

       hwVlanSrvProfEntry OBJECT-TYPE
           SYNTAX HwVlanSrvProfEntry
           MAX-ACCESS not-accessible
           STATUS current
           DESCRIPTION
               "Describes the attributes of a VLAN service profile, used for adding or deleting
                a VLAN service profile, or modifying the status of the attributes in an existing
                VLAN service profile.
                The index of this entry is hwVlanSrvProfName.
               "
           INDEX { hwVlanSrvProfName }
           ::= { hwVlanSrvProfTable 1 }

       HwVlanSrvProfEntry ::=
           SEQUENCE {
             hwVlanSrvProfName
               OCTET STRING,
             hwForwardingMode
               INTEGER,
             hwAntiIpSpoofingSwitch
               INTEGER,
             hwAntiMacSpoofingSwitch
               INTEGER,
             hwPPPoEMacMode
               INTEGER,
             hwBpduTunnelSwitch
               INTEGER,
             hwRipTunnelSwitch
               INTEGER,
             hwVtpCdpTunnelSwitch
               INTEGER,
             hwDhcpMode
               INTEGER,
             hwDhcpProxySwitch
               INTEGER,
             hwDhcpOption82Switch
               INTEGER,
             hwPitpSwitch
               INTEGER,
             hwPolicyBroadcast
               INTEGER,
             hwPolicyMulticast
               INTEGER,
             hwPolicyUnknowncast
               INTEGER,
             hwUserBridging
               INTEGER,
             hwDhcpSuppressSwitch
               INTEGER,
             hwMismatchIgmpPolicy
               INTEGER,
             hwVmacStatus
               INTEGER,
             hwIPoEMacMode
               INTEGER,
             hwVmacAgingMode
               INTEGER,
             hwFabricMacLearningSwitch
               INTEGER,
             hwOspfTunnelSwitch
               INTEGER,
             hwL3ProtocolTunnelSwitch
               INTEGER,
             hwDhcpv6Mode
               INTEGER,
             hwDhcpv6OptionSwitch
               INTEGER,
             hwVmacIPoESubStatus
               INTEGER,
             hwVmacPPPoESubStatus
               INTEGER,
             hwVmacPPPoASubStatus
               INTEGER,
             hwPPPoAMacMode
               INTEGER,
             hwAntiIpv6SpoofingSwitch
               INTEGER,
             hwIpv6DadProxySwitch
               INTEGER,
             hwIpv6BindRouteAndNdSwitch
               INTEGER,
             hwIpv6NsReplySwitch
               INTEGER,
             hwIpv4ArpReplySwitch
               INTEGER,
             hwDhcpRelayInterfaceRelayAgentSwitch
               INTEGER,
             hwPolicyMulticastFabric
               INTEGER,
             hwCableSourceVerify
               INTEGER,
             hwRipngTunnelSwitch
               INTEGER,
             hwIpv4ArpUnicastSwitch
               INTEGER,      
             hwIpv4ArpUnicastunkonwnpolicy
               INTEGER, 
             hwIpv6NsUnicastSwitch
               INTEGER,      
             hwIpv6NsUnicastunkonwnpolicy
               INTEGER,
             hwIgmpUserMaxVlanTag
               INTEGER,
             hwRouterRedirectReverse
               INTEGER,
             hwCableIPv6SourceVerify
               INTEGER,
             hwAntiMacDuplicateSwitch
               INTEGER,  
             hwArpDetectMaxUserCountSwitch
               INTEGER,	       
             hwDhcpOption82CaptureArpSwitch
               INTEGER,
             hwDhcpv6OptionCaptureNaSwitch
               INTEGER,
             hwProfileRowStatus
               RowStatus
            }

       hwVlanSrvProfName OBJECT-TYPE
           SYNTAX OCTET STRING (SIZE (1..32))
           MAX-ACCESS read-only
           STATUS current
           DESCRIPTION
               "Indicates the name of the VLAN service profile.
                Range: a string of 1-32 characters
                The input index consists of the VLAN service profile name and
                the length of the VLAN service profile name.
                The input VLAN service profile name must be ASCII codes.
                Assume that you need to create a huawei VLAN service profile.
                Because the ASCII value of huawei is 104.117.97.119.101.105 and
                the length of huawei is 6, the index is 6.104.117.97.119.101.105.
               "
           ::= { hwVlanSrvProfEntry 1 }

       hwForwardingMode OBJECT-TYPE
           SYNTAX INTEGER
             {
               vlanMac(1),
               vlanConnect(2),
               notConfig(3)
             }
           MAX-ACCESS read-write
           STATUS current
           DESCRIPTION
               "Indicates the VLAN forwarding policy.
                Options:
                1. vlanMac(1)     -indicates forwarding based on the VLAN+MAC.
                2. vlanConnect(2) -indicates forwarding based on the SVLAN+CVLAN.
                3. notConfig(3)   -indicates forwarding based on VLAN single switch.
                This leaf is optional for creating a VLAN service profile.
                The VLAN forwarding policy can also be configured in hwVlanForwarding
                of hwVlanMIBTable. If a VLAN service profile is bound to the VLAN,
                the configuration in the VLAN service profile takes effect.
               "
           ::= { hwVlanSrvProfEntry 2 }

       hwAntiIpSpoofingSwitch OBJECT-TYPE
           SYNTAX INTEGER
             {
               enable(1),
               disable(2)
             }
           MAX-ACCESS read-write
           STATUS current
           DESCRIPTION
               "Indicates the VLAN-based anti-IP-spoofing function.
                Options:
                1. enable(1) -indicates that the anti-IP-spoofing function is enabled.
                2. disable(2) -indicates that the anti-IP-spoofing function is disabled.
                This leaf is optional for creating a VLAN service profile.
                The anti-IP spoofing function in the global mode can be set in
                hwIpDslamIpAddrDynamicBindingStatus of HUAWEI-IPDSLAM-SECURITY-MIB.
                The final status of the anti-IP-spoofing function is determined by its
                global-level switch and VLAN-level switch. The anti-IP-spoofing function
                of a VLAN is enabled only when the switches at both levels are enabled.
               "
           ::= { hwVlanSrvProfEntry 3 }

       hwAntiMacSpoofingSwitch OBJECT-TYPE
           SYNTAX INTEGER
             {
               enable(1),
               disable(2),
               notConfig(3)
             }
           MAX-ACCESS read-write
           STATUS current
           DESCRIPTION
               "Indicates the VLAN-based anti-MAC-spoofing function.
                Options:
                1. enable(1) -indicates that the anti-MAC-spoofing function is enabled.
                2. disable(2)-indicates that the anti-MAC spoofing function is disabled.
                3. notConfig(3)   -indicate by VLAN single switch.
                This leaf is optional for creating a VLAN service profile.
                The anti-MAC spoofing function in the global mode can be set in
                hwIpDslamAntiMacSpoofingStatus of HUAWEI-IPDSLAM-SECURITY-MIB.
                The VLAN-based anti-MAC-spoofing function can also be configured
                in hwIpDslamL2pVlanCtrlMacSpoofing of hwIpDslamL2pVlanCtrlTable
                in HUAWEI-IPDSLAM-L2PPORTCONFIG-MIB.
                The final status of the anti-MAC-spoofing function is determined by
                its global-level switch and VLAN-level switch. The anti-MAC spoofing
                function of a VLAN is enabled only when the switches at both levels are
                enabled. If a VLAN service profile is bound to the VLAN, the configuration
                of the VLAN-based anti-MAC-spoofing function in the VLAN service profile takes effect.
               "
           ::= { hwVlanSrvProfEntry 4 }

       hwPPPoEMacMode OBJECT-TYPE
           SYNTAX INTEGER
             {
               multiMac(1),
               singleMac(2),
               notConfig(3)
             }
           MAX-ACCESS read-write
           STATUS current
           DESCRIPTION
               "Indicates the VLAN-based PPPoE single-MAC function.
                Options:
                1. multiMac(1) -indicates that the multi-MAC mode is adopted.
                2. singleMac(2) -indicates that the single-MAC mode is adopted.
                3. notConfig(3)   -indicate by VLAN single switch.
                This leaf is optional for creating a VLAN service profile.
                The PPPoE single-MAC function in the global mode can be set
                in hwIpDslamPPPoEMacMode of HUAWEI-IPDSLAM-PPPOE-MIB.
                The VLAN-based PPPoE single-MAC function can also be configured
                in hwIpDslamL2pVlanCtrlPppoeMacMode of
                hwIpDslamL2pVlanCtrlTable in HUAWEI-IPDSLAM-L2PPORTCONFIG-MIB.
                The final status of the PPPoE single-MAC function is determined
                by its global-level switch and VLAN-level switch.
                The PPPoE single-MAC function of a VLAN is enabled only
                when the switches at both levels are enabled.
                If a VLAN service profile is bound to the VLAN,
                the configuration of the VLAN-based PPPoE single-MAC
                function in the VLAN service profile takes effect.
               "
           ::= { hwVlanSrvProfEntry 5 }

       hwBpduTunnelSwitch  OBJECT-TYPE
           SYNTAX INTEGER
             {
               enable(1),
               disable(2),
               notConfig(3)
             }
           MAX-ACCESS read-write
           STATUS current
           DESCRIPTION
               "Indicates the VLAN-based BPDU transparent transmission function.
                Options:
                1. enable(1)  -indicates that the BPDU transparent transmission function is enabled.
                2. disable(2) -indicates that the BPDU transparent transmission function is disabled.
                3. notConfig(3)   -indicate by VLAN single switch.
                This leaf is optional for creating a VLAN service profile.
                The BPDU transparent transmission function can also be configured
                in hwBpduTunnel of hwBpduTunnelTable. If a VLAN service profile is bound to the VLAN,
                the configuration in the VLAN service profile takes effect.
               "
           ::= { hwVlanSrvProfEntry 6 }

       hwRipTunnelSwitch OBJECT-TYPE
           SYNTAX INTEGER
             {
               enable(1),
               disable(2),
               notConfig(3)
             }
           MAX-ACCESS read-write
           STATUS current
           DESCRIPTION
               "Indicates the VLAN-based RIP transparent transmission function.
                Options:
                1. enable(1)  -indicates that the RIP transparent transmission function is enabled.
                2. disable(2) -indicates that the RIP transparent transmission function is disabled.
                3. notConfig(3)   -indicate by VLAN single switch.
                This leaf is optional for creating a VLAN service profile.
                The RIP transparent transmission function can also be configured in
                hwPacketTunnelRip of hwPacketTunnelTable. If a VLAN service profile is bound to
                the VLAN, the configuration in the VLAN service profile takes effect.
               "
           ::= { hwVlanSrvProfEntry 7 }

       hwVtpCdpTunnelSwitch  OBJECT-TYPE
           SYNTAX INTEGER
             {
               enable(1),
               disable(2),
               notConfig(3)
             }
           MAX-ACCESS read-write
           STATUS current
           DESCRIPTION
               "Indicates the VLAN-based VTP/CDP transparent transmission function.
                Options:
                1. enable(1)  -indicates that the VTP/CDP transparent transmission function is enabled.
                2. disable(2) -indicates that the VTP/CDP transparent transmission function is disabled.
                3. notConfig(3)   -indicate by VLAN single switch.
                This leaf is optional for creating a VLAN service profile.
                The VTP/CDP transparent transmission function can also be configured
                in hwPacketTunnelVTPCDP of hwPacketTunnelTable. If a VLAN service profile
                is bound to the VLAN, the configuration in the VLAN service profile takes effect.
               "
           ::= { hwVlanSrvProfEntry 8 }

       hwDhcpMode OBJECT-TYPE
           SYNTAX INTEGER
             {
               notConfig(1),
               layer2(2),
               l3Standard(3),
               l3Option60(4),
               l3MacRange(5)
             }
           MAX-ACCESS read-write
           STATUS current
           DESCRIPTION
               "Indicates the VLAN-based DHCP L2/L3 mode switch.
                Options:
                1. notConfig(1)  -indicates that if the VLAN configuration exists, 
                                  the VLAN configuration takes effect. 
                                  Otherwise, the configuration in global mode takes effect.
                2. layer2(2)     -indicates the DHCP L2 forwarding mode.
                                  In this mode, the device only transparently transmits
                                  packets and does not process the packets.
                3. l3Standard(3) -indicates the standard mode of the DHCP L3
                                  forwarding mode. In this mode, packets select the
                                  DHCP server through the VLAN L3 interface that is
                                  used for forwarding the DHCP packets.
                4. l3Option60(4) -indicates the DHCP option 60 mode of the DHCP L3
                                  forwarding mode. In this mode, packets select the
                                  DHCP server according to the option 60 field.
                                  Option 60 is an option with code 60 in the DHCP packet.
                                  It can identify the terminal type. That is, packets can
                                  select the DHCP server according to terminal types.
                5. l3MacRange(5) -indicates the MAC address segment mode of the DHCP L3
                                  forwarding mode. In this mode, packets select the DHCP
                                  server according to the MAC address segment to which
                                  the source MAC address of the DHCP packets belong.
                This leaf is optional for creating a VLAN service profile.
                The DHCP L2/L3 mode in the global mode can also be set in hwDhcpRelayMode
                and hwDhcpServerSelectMode of HUAWEI-DHCP-Proxy-MIB. The DHCP L2/L3 mode
                at the VLAN level can also be set in hwDhcpServerSelectModeByVlanTable.
                If a VLAN service profile is bound to the VLAN, the configuration in the
                VLAN service profile takes effect. The global DHCP L2/L3 mode, however,
                is not changed.
                If no VLAN service profile is bound to the VLAN, but hwDhcpServerSelectModeByVlanTable
                is configured, the configuration of hwDhcpServerSelectModeByVlanTable takes effect;
                if hwDhcpServerSelectModeByVlanTable is not configured, the configuration
                in the global mode takes effect.
               "
           ::= { hwVlanSrvProfEntry 9 }

       hwDhcpProxySwitch  OBJECT-TYPE
           SYNTAX INTEGER
             {
               enable(1),
               disable(2)
             }
           MAX-ACCESS read-write
           STATUS current
           DESCRIPTION
               "Indicates the VLAN-based DHCP proxy function.
                Options:
                1. enable(1)  -indicates that the DHCP proxy is enabled.
                2. disable(2) -indicates that the DHCP proxy is disabled.
                This leaf is optional for creating a VLAN service profile.
                The global DHCP proxy function can be configured in
                hwDhcpProxyStatus of HUAWEI-DHCP-Proxy-MIB. The final
                status of the DHCP proxy function is determined by its
                global-level switch and VLAN-level switch. The DHCP
                proxy function of a VLAN is enabled only when the switches
                at both levels are enabled. When the DHCP mode of the VLAN
                is configured to L2 mode, the configuration data can
                be saved, but the configuration of the
                DHCP proxy function does not take effect.
               "
           ::= { hwVlanSrvProfEntry 10 }

       hwDhcpOption82Switch OBJECT-TYPE
           SYNTAX INTEGER
             {
               enable(1),
               disable(2)
             }
           MAX-ACCESS read-write
           STATUS current
           DESCRIPTION
               "Indicates the VLAN-based DHCP option 82 function.
                Options:
                1. enable(1)  -indicates that the DHCP option 82 function is enabled.
                2. disable(2) -indicates that the DHCP option 82 function is disabled.
                This leaf is optional for creating a VLAN service profile.
                The global DHCP option 82 function can be configured in hwDhcpOption82Status
                of HUAWEI-DHCP-Proxy-MIB. The final status of the DHCP option
                82 function is determined by its global-level switch and VLAN-level switch.
                The DHCP option 82 function of a VLAN is enabled only when
                the switches at both levels are enabled.
               "
           ::= { hwVlanSrvProfEntry 11 }

       hwPitpSwitch OBJECT-TYPE
           SYNTAX INTEGER
             {
               enable(1),
               disable(2)
             }
           MAX-ACCESS read-write
           STATUS current
           DESCRIPTION
               "Indicates the PITP switch based on VLAN.
                Options:
                1. enable(1)  -indicates enabling the PITP switch.
                2. disable(2) -indicates disabling the PITP switch.
                This leaf is optional for creating a VLAN service profile.
                Leaf hwDslamPITPStatus in HUAWEI-DSLAM-PITP-MIB can be used for configuring the global
                PITP switch. The final status of the PITP switch is determined by both the global-level
                PITP switch and the VLAN-level PITP switch. The PITP function is enabled on the VLAN
                only when the switches at both levels are enabled.
               "
           ::= { hwVlanSrvProfEntry 12 }

       hwPolicyBroadcast OBJECT-TYPE
           SYNTAX INTEGER
             {
               forward(1),
               discard(2),
               notConfig(3)
             }
           MAX-ACCESS read-write
           STATUS current
           DESCRIPTION
               "Indicates the VLAN-based forwarding policy for the broadcast packets.
                Options:
                1. forward(1) -indicates that the broadcast packets are transparently transmitted.
                2. discard(2) -indicates that the broadcast packets are discarded.
                3. notConfig(3)   -indicate by VLAN single switch.
                This leaf is optional for creating a VLAN service profile.
                You can perform the set operation on this leaf to modify
                the VLAN-based forwarding policy for the broadcast packets.
                The VLAN-based forwarding policy for the broadcast packets can
                also be configured in hwVlanPolicyBroadcast of hwVlanMIBTable.
                If a VLAN service profile is bound to the VLAN, the configuration
                in the VLAN service profile takes effect.
               "
           ::= { hwVlanSrvProfEntry 13 }

       hwPolicyMulticast   OBJECT-TYPE
           SYNTAX INTEGER
             {
               forward(1),
               discard(2),
               notConfig(3)
             }
           MAX-ACCESS read-write
           STATUS current
           DESCRIPTION
               "Indicates the VLAN-based forwarding policy for the unknown multicast packets.
                Options:
                1. forward(1) -indicates that the unknown multicast packets are transparently transmitted.
                2. discard(2) -indicates that the unknown multicast packets are discarded.
                3. notConfig(3)   -indicate by VLAN single switch.
                This leaf is optional for creating a VLAN service profile.
                You can perform the set operation on this leaf to modify the VLAN-based forwarding policy
                for the unknown multicast packets.
                The VLAN-based forwarding policy for the unknown multicast packets can
                also be configured in hwVlanPolicyMulticast of hwVlanMIBTable.
                If a VLAN service profile is bound to the VLAN, the configuration
                in the VLAN service profile takes effect.
               "
           ::= { hwVlanSrvProfEntry 14 }

       hwPolicyUnknowncast OBJECT-TYPE
           SYNTAX INTEGER
             {
               forward(1),
               discard(2),
               notConfig(3)
             }
           MAX-ACCESS read-write
           STATUS current
           DESCRIPTION
               "Indicates the VLAN-based forwarding policy for the unknown unicast packets.
                Options:
                1. forward(1) -indicates that the unknown unicast packets are transparently transmitted.
                2. discard(2) -indicates that the unknown unicast packets are discarded.
                3. notConfig(3)   -indicate by VLAN single switch.
                This leaf is optional for creating a VLAN service profile.
                You can perform the set operation on this leaf
                to modify the VLAN-based forwarding policy for the unknown unicast packets.
                The VLAN-based forwarding policy for the unknown unicast packets can also be
                configured in hwVlanPolicyUnknowncast of hwVlanMIBTable. If a VLAN service
                profile is bound to the VLAN, the configuration in the VLAN service profile takes effect.
               "
           ::= { hwVlanSrvProfEntry 15 }

       hwUserBridging OBJECT-TYPE
           SYNTAX INTEGER
             {
               enable(1),
               disable(2)
             }
           MAX-ACCESS read-write
           STATUS current
           DESCRIPTION
               "Indicates the VLAN-based bridging function.
                Options:
                1. enable(1)   -indicates bridging in a VLAN.
                2. disable(2)  -indicates L2 isolation in a VLAN.
                This leaf is optional for creating a VLAN service profile.
               "
           ::= { hwVlanSrvProfEntry 16 }

       hwDhcpSuppressSwitch OBJECT-TYPE
           SYNTAX INTEGER
             {
               enable(1),
               disable(2)
             }
           MAX-ACCESS read-write
           STATUS current
           DESCRIPTION
               "DHCP boardcast-suppress switch.
                Options:
                1. enable(1)   -Enable DHCP boardcast-suppress.
                2. disable(2)  -Disable DHCP boardcast-suppress.
                This leaf is optional for creating a VLAN service profile.
               "
           ::= { hwVlanSrvProfEntry 17 }

       hwMismatchIgmpPolicy OBJECT-TYPE
           SYNTAX INTEGER
             {
               transparent(1),
               discard(2)
             }
           MAX-ACCESS read-write
           STATUS current
           DESCRIPTION
               "Indicates the VLAN-based forwarding policy for the mismatched IGMP packets.
                Options:
                1. transparent(1) -indicates that the mismatched IGMP packets are transparently transmitted.
                2. discard(2) -indicates that the mismatched IGMP packets are discarded.
                This leaf is optional for creating a VLAN service profile.
               "
           ::= { hwVlanSrvProfEntry 18 }

       hwVmacStatus OBJECT-TYPE
           SYNTAX INTEGER
               {
               enable(1),
               disable(2),
               notConfig(3)
               }
           MAX-ACCESS read-write
           STATUS current
           DESCRIPTION
               "Indicates the VLAN-based VMAC function.
                Options:
                1. enable(1)  -indicates that the VMAC function is enabled.
                2. disable(2) -indicates that the VMAC function is disabled.
                3. notConfig(3)   -indicate by VLAN single switch.
                This leaf is optional for creating a VLAN service profile.
                The global VMAC function can be configured in hwIpDslamVmacStatus
                of HUAWEI-IPDSLAM-VMAC-MIB. The VLAN-based VMAC function can
                also be configured hwIpDslamL2pVlanCtrlVmacStatus
                of HUAWEI-IPDSLAM-L2PPORTCONFIG-MIB.
                The final status of the VMAC function is determined by its
                global-level switch and VLAN-level switch. The VMAC function
                of a VLAN is enabled only when the switches at both levels are
                enabled. If a VLAN service profile is bound to the VLAN,
                the configuration of the VLAN-based VMAC function
                in the VLAN service profile takes effect.
               "
           ::= { hwVlanSrvProfEntry 19 }

       hwIPoEMacMode OBJECT-TYPE
           SYNTAX INTEGER
             {
               multiMac(1),
               singleMac(2)
             }
           MAX-ACCESS read-write
           STATUS current
           DESCRIPTION
               "Indicates the mode of allocating MAC addresses to DHCP users.
                Options:
                1. multiMac(1)  -indicates the multi-MAC mode.
                2. singleMac(2) -indicates the single-MAC mode.
                This leaf is optional for creating a VLAN service profile.
                The global mode of allocating MAC addresses to DHCP users
                can be configured in hwIpDslamIPoEMacMode of HUAWEI-IPDSLAM-VMAC-MIB.
                The final status of the mode of allocating MAC addresses to DHCP
                users is determined by its global-level switch and VLAN-level switch.
                The single-MAC mode of a VLAN can be enabled only when
                the single-MAC mode is enabled at both levels.
               "
           ::= { hwVlanSrvProfEntry 20 }

       hwVmacAgingMode OBJECT-TYPE
           SYNTAX INTEGER
             {
               macLearning(1),
               dhcp(2)
             }
           MAX-ACCESS read-write
           STATUS current
           DESCRIPTION
               "Indicates the time selection mode for reallocating VMAC addresses to users.
                Options:
                1. macLearning(1) -indicates that the VMAC addresses are
                                   reallocated to users after the corresponding MAC address learning entry ages.
                2. dhcp(2)        -indicates that the VMAC addresses are reallocated to users after
                                   the corresponding IP addresses are released or the lease time of the IP address expires.
                This leaf is optional for creating a VLAN service profile.
               "
           ::= { hwVlanSrvProfEntry 21 }

       hwFabricMacLearningSwitch OBJECT-TYPE
           SYNTAX INTEGER
             {
               enable(1),
               disable(2)
             }
           MAX-ACCESS read-write
           STATUS current
           DESCRIPTION
               "Indicates the VLAN-based MAC address learning capability switch of the control board.
                Options:
                1. enable(1)  -indicates that the VLAN-based MAC address learning is enabled.
                2. disable(2) -indicates that the VLAN-based MAC address learning is disabled.
                This leaf is optional for creating a VLAN service profile.
               "
           ::= { hwVlanSrvProfEntry 22 }

       hwOspfTunnelSwitch  OBJECT-TYPE
           SYNTAX INTEGER
             {
               enable(1),
               disable(2)
             }
           MAX-ACCESS read-write
           STATUS current
           DESCRIPTION
               "Indicates the VLAN-based OSPF transparent transmission function.
                Options:
                1. enable(1)  -indicates that the OSPF transparent transmission function is enabled.
                2. disable(2) -indicates that the OSPF transparent transmission function is disabled.
                This leaf is optional for creating a VLAN service profile.
               "
           ::= { hwVlanSrvProfEntry 23 }

       hwL3ProtocolTunnelSwitch  OBJECT-TYPE
           SYNTAX INTEGER
             {
               enable(1),
               disable(2)
             }
           MAX-ACCESS read-write
           STATUS current
           DESCRIPTION
               "Indicates the VLAN-based L2 transparent transmission function
                of other L3 protocol packets except RIP and OSPF packets.
                Options:
                1. enable(1)  -indicates that the transparent transmission function is enabled.
                2. disable(2) -indicates that the transparent transmission function is disabled.
                This leaf is optional for creating a VLAN service profile.
               "
           ::= { hwVlanSrvProfEntry 24 }

       hwDhcpv6Mode OBJECT-TYPE
           SYNTAX INTEGER
             {
               notConfig(1),
               layer2(2),
               layer3(3),
               layer3option16(4)
             }
           MAX-ACCESS read-write
           STATUS current
           DESCRIPTION
               "Indicates the VLAN-based DHCPv6 L2/L3 mode switch.
                Options:
                1. notConfig(1)      -indicates that the configuration in global mode takes effect.
                2. layer2(2)         -indicates the DHCPv6 L2 forwarding mode.
                                      In this mode, the device only transparently transmits
                                      packets and does not process the packets.
                3. layer3(3)         -indicates the standard mode of the DHCPv6 L3
                                      forwarding mode. In this mode, packets select the
                                      DHCPv6 server through the VLAN L3 interface that is
                                      used for forwarding the DHCPv6 packets.
                4. layer3option16(4) -indicates the option 16 mode of the DHCPv6 L3
                                      forwarding mode. In this mode, packets select the
                                      DHCPv6 server according to the option 16 field.
                                      Option 16 is an option with code 16 in the DHCPv6 packets.
                                      It can identify the terminal type. That is, packets can
                                      select the DHCPv6 server according to terminal types.

                This leaf is optional for creating a VLAN service profile.
                The DHCPv6 L2/L3 mode in the global mode can also be set in hwDhcpv6RelayMode
                of HUAWEI-DHCPV6-RELAY-MIB.
                If a VLAN service profile is bound to the VLAN, and the hwDhcpv6Mode in VLAN service profile is not notConfig(1),
                the configuration in the VLAN service profile takes effect. The global DHCPv6 L2/L3 mode, however, is not changed.
                If no VLAN service profile is bound to the VLAN, or the hwDhcpv6Mode in VLAN service profile is notConfig(1),
                the configuration in the global mode takes effect.
               "
           ::= { hwVlanSrvProfEntry 25 }

       hwDhcpv6OptionSwitch OBJECT-TYPE
           SYNTAX INTEGER
             {
               enable(1),
               disable(2)
             }
           MAX-ACCESS read-write
           STATUS current
           DESCRIPTION
               "Indicates the VLAN-based DHCPv6 option function.
                Options:
                1. enable(1)  -indicates that the DHCPv6 option 18 and optin 37 function are enabled.
                2. disable(2) -indicates that the DHCPv6 option 18 and optin 37 function are disabled.
                This leaf is optional for creating a VLAN service profile.
                The global DHCPv6 option function can be configured in hwDhcpv6OptionStatus
                of HUAWEI-DHCPV6-RELAY-MIB. The final status of the DHCPv6 option
                function is determined by its global-level switch and VLAN-level switch.
                The DHCPv6 option function of a VLAN is enabled only when
                the switches at both levels are enabled.
               "
           ::= { hwVlanSrvProfEntry 26 }

       hwVmacIPoESubStatus OBJECT-TYPE
           SYNTAX INTEGER
             {
               enable(1),
               disable(2),
               notConfig(3)
             }
           MAX-ACCESS read-write
           STATUS current
           DESCRIPTION
               "Indicates the VLAN-based IPoE VMAC function.
                Options:
                1. enable(1)     -indicates that the IPoE VMAC function is enabled.
                2. disable(2)    -indicates that the IPoE VMAC function is disabled.
                3. notConfig(3)  -indicate by VLAN single switch.
                This leaf is optional for creating a VLAN service profile.
                The VLAN-based IPoE VMAC function can be configured in
                hwIpDslamL2pVlanCtrlVmacIPoESubStatus of HUAWEI-IPDSLAM-L2PPORTCONFIG-MIB.
                The status of the IPoE VMAC function is determined by its
                VLAN-level switch. The IPoE VMAC function of a VLAN is enabled
                only when the VLAN-level switch is enabled.
                If a VLAN service profile is bound to the VLAN,
                the configuration of the VLAN-based IPoE VMAC function
                in the VLAN service profile takes effect.
               "
           ::= { hwVlanSrvProfEntry 27 }

       hwVmacPPPoESubStatus OBJECT-TYPE
           SYNTAX INTEGER
             {
               enable(1),
               disable(2),
               notConfig(3)
             }
           MAX-ACCESS read-write
           STATUS current
           DESCRIPTION
               "Indicates the VLAN-based PPPoE VMAC function.
                Options:
                1. enable(1)     -indicates that the PPPoE VMAC function is enabled.
                2. disable(2)    -indicates that the PPPoE VMAC function is disabled.
                3. notConfig(3)  -indicate by VLAN single switch.
                This leaf is optional for creating a VLAN service profile.
                The VLAN-based PPPoE VMAC function can be configured in
                hwIpDslamL2pVlanCtrlVmacPPPoESubStatus of HUAWEI-IPDSLAM-L2PPORTCONFIG-MIB.
                The status of the PPPoE VMAC function is determined by its
                VLAN-level switch. The PPPoE VMAC function of a VLAN is enabled
                only when the VLAN-level switch is enabled.
                If a VLAN service profile is bound to the VLAN,
                the configuration of the VLAN-based PPPoE VMAC function
                in the VLAN service profile takes effect.
               "
           ::= { hwVlanSrvProfEntry 28 }

       hwVmacPPPoASubStatus OBJECT-TYPE
           SYNTAX INTEGER
             {
               enable(1),
               disable(2),
               notConfig(3)
             }
           MAX-ACCESS read-write
           STATUS current
           DESCRIPTION
               "Indicates the VLAN-based PPPoA VMAC function.
                Options:
                1. enable(1)     -indicates that the PPPoA VMAC function is enabled.
                2. disable(2)    -indicates that the PPPoA VMAC function is disabled.
                3. notConfig(3)  -indicate by VLAN single switch.
                This leaf is optional for creating a VLAN service profile.
                The VLAN-based PPPoA VMAC function can be configured in
                hwIpDslamL2pVlanCtrlVmacPPPoASubStatus of HUAWEI-IPDSLAM-L2PPORTCONFIG-MIB.
                The status of the PPPoA VMAC function is determined by its
                VLAN-level switch. The PPPoA VMAC function of a VLAN is enabled
                only when the VLAN-level switch is enabled.
                If a VLAN service profile is bound to the VLAN,
                the configuration of the VLAN-based PPPoA VMAC function
                in the VLAN service profile takes effect.
               "
           ::= { hwVlanSrvProfEntry 29 }

       hwPPPoAMacMode OBJECT-TYPE
           SYNTAX INTEGER
             {
               multiMac(1),
               singleMac(2),
               notConfig(3)
             }
           MAX-ACCESS read-write
           STATUS current
           DESCRIPTION
               "Indicates the VLAN-based PPPoA single-MAC function.
                Options:
                1. multiMac(1)    -indicates that the multi-MAC mode is adopted.
                2. singleMac(2)   -indicates that the single-MAC mode is adopted.
                3. notConfig(3)   -indicate by VLAN single switch.
                This leaf is optional for creating a VLAN service profile.
                The PPPoA single-MAC function in the global mode can be set
                in hwIpDslamPPPoAMacMode of HUAWEI-IPDSLAM-PPPOE-MIB.
                The VLAN-based PPPoA single-MAC function can also be configured
                in hwIpDslamL2pVlanCtrlPppoaMacMode of
                hwIpDslamL2pVlanCtrlTable in HUAWEI-IPDSLAM-L2PPORTCONFIG-MIB.
                The final status of the PPPoA single-MAC function is determined
                by its global-level switch and VLAN-level switch.
                The PPPoA single-MAC function of a VLAN is enabled only
                when the switches at both levels are enabled.
                If a VLAN service profile is bound to the VLAN,
                the configuration of the VLAN-based PPPoA single-MAC
                function in the VLAN service profile takes effect.
               "
           ::= { hwVlanSrvProfEntry 30 }

       hwAntiIpv6SpoofingSwitch OBJECT-TYPE
           SYNTAX INTEGER
             {
               enable(1),
               disable(2)
             }
           MAX-ACCESS read-write
           STATUS current
           DESCRIPTION
               "Indicates the VLAN-based anti-IPv6-spoofing function.
                Options:
                1. enable(1)  -indicates that the anti-IPv6-spoofing function is enabled.
                2. disable(2) -indicates that the anti-IPv6-spoofing function is disabled.
                This leaf is optional for creating a VLAN service profile.
                The anti-IPv6-spoofing function in the global mode can be set in
                hwIpDslamAntiIpv6SpoofingStatus of HUAWEI-IPDSLAM-SECURITY-MIB.
                The final status of the anti-IPv6-spoofing function is determined by its
                global-level switch and VLAN-level switch. The anti-IPv6-spoofing function
                of a VLAN is enabled only when the switches at both levels are enabled.
               "
           ::= { hwVlanSrvProfEntry 31 }

       hwIpv6DadProxySwitch OBJECT-TYPE
           SYNTAX INTEGER
             {
               enable(1),
               disable(2)
             }
           MAX-ACCESS read-write
           STATUS current
           DESCRIPTION
               "Indicates the VLAN-based IPv6 dad proxy function.
                Options:
                1. enable(1)  -indicates that the IPv6 dad proxy function is enabled.
                2. disable(2) -indicates that the IPv6 dad proxy function is disabled.
                This leaf is optional for creating a VLAN service profile.
                The IPv6 dad proxy function in the global mode can be set in
                hwIpDslamIpv6DadProxySwitch of HUAWEI-IPDSLAM-SECURITY-MIB.
                The final status of the IPv6 dad proxy function is determined by its
                global-level switch and VLAN-level switch. The IPv6 dad proxy function
                of a VLAN is enabled only when the switches at both levels are enabled.
               "
           ::= { hwVlanSrvProfEntry 32 }

       hwIpv6BindRouteAndNdSwitch OBJECT-TYPE
           SYNTAX INTEGER
             {
               enable(1),
               disable(2)
             }
           MAX-ACCESS read-write
           STATUS current
           DESCRIPTION
               "Indicates the VLAN-based bind-route-nd function.
                Options:
                1. enable(1)  -indicates that the bind-route-nd function is enabled.
                2. disable(2) -indicates that the bind-route-nd function is disabled.
                This leaf is optional for creating a VLAN service profile.
                The bind-route-nd function in the global mode can be set in
                hwIpDslamIpv6BindRouteAndNdSwitch of HUAWEI-IPDSLAM-SECURITY-MIB.
                The final status of the bind-route-nd function is determined by its
                global-level switch and VLAN-level switch. The bind-route-nd function
                of a VLAN is enabled only when the switches at both levels are enabled.
               "
           ::= { hwVlanSrvProfEntry 33 }

       hwIpv6NsReplySwitch OBJECT-TYPE
           SYNTAX INTEGER
             {
               enable(1),
               disable(2)
             }
           MAX-ACCESS read-write
           STATUS current
           DESCRIPTION
               "Indicates the VLAN-based ns reply function.
                Options:
                1. enable(1)  -indicates that the ns reply function is enabled.
                2. disable(2) -indicates that the ns reply function is disabled.
                This leaf is optional for creating a VLAN service profile.
                The ns reply function in the global mode can be set in
                hwIpDslamIpv6NsReplySwitch of HUAWEI-IPDSLAM-SECURITY-MIB.
                The final status of the ns reply function is determined by its
                global-level switch and VLAN-level switch. The ns reply function
                of a VLAN is enabled only when the switches at both levels are enabled.
               "
           ::= { hwVlanSrvProfEntry 34 }

       hwIpv4ArpReplySwitch OBJECT-TYPE
           SYNTAX INTEGER
             {
               enable(1),
               disable(2)
             }
           MAX-ACCESS read-write
           STATUS current
           DESCRIPTION
               "Indicates the VLAN-based arp reply function.
                Options:
                1. enable(1)  -indicates that the arp reply function is enabled.
                2. disable(2) -indicates that the arp reply function is disabled.
                This leaf is optional for creating a VLAN service profile.
                The arp reply function in the global mode can be set in
                hwIpDslamIpv4ArpReplySwitch of HUAWEI-IPDSLAM-SECURITY-MIB.
                The final status of the arp reply function is determined by its
                global-level switch and VLAN-level switch. The arp replyd function
                of a VLAN is enabled only when the switches at both levels are enabled.
               "
           ::= { hwVlanSrvProfEntry 35 }

       hwDhcpRelayInterfaceRelayAgentSwitch OBJECT-TYPE
           SYNTAX INTEGER
             {
               receive(1),
               send(2),
               notConfig(3)
             }
           MAX-ACCESS read-write
           STATUS current
           DESCRIPTION
               "Indicates the VLAN-based filling mode of the GIADDR field of the current DHCP-relay upstream packet.
                Options:
                1. receive(1) -indicates that in the DHCP packet sent from the DHCP relay agent to the server,
                               the gateway IP address is set to the IP address of the Rx interface (user-side interface).
                2. send(2)    -indicates that in the DHCP packet sent from the DHCP relay agent to the server,
                               the gateway IP address is set to the IP address of the Tx interface (network-side interface).
                3. notConfig(3) -indicates that the configuration in the global mode takes effect.

                This leaf is optional for creating a VLAN service profile.
                The filling mode of the GIADDR field of the current DHCP-relay upstream packet in the global mode
                can be set in hwDhcpRelayInterfaceRelayAgent of HUAWEI-DHCP-PROXY-MIB.
                The final status of the configuration is determined by its global-level switch and VLAN-level switch.
                If a VLAN service profile is bound to the VLAN, and the hwDhcpRelayInterfaceRelayAgentSwitch
                in VLAN service profile is not notConfig(3), the configuration in the VLAN service profile takes effect.
                If no VLAN service profile is bound to the VLAN, or the hwDhcpRelayInterfaceRelayAgentSwitch
                in VLAN service profile is notConfig(3), the configuration in the global mode takes effect.
               "
           ::= { hwVlanSrvProfEntry 36 }

       hwPolicyMulticastFabric OBJECT-TYPE
           SYNTAX INTEGER
             {
               forward(1),
               discard(2)
             }
           MAX-ACCESS read-write
           STATUS current
           DESCRIPTION
               "Indicates the VLAN-based forwarding policy for the control board unknown multicast packets.
                Options:
                1. forward(1) -indicates that the control board unknown multicast packets are transparently transmitted.
                2. discard(2) -indicates that the control board unknown multicast packets are discarded.

                This leaf is optional for creating a VLAN service profile.
               "
           ::= { hwVlanSrvProfEntry 37 }
           
       hwCableSourceVerify OBJECT-TYPE
           SYNTAX INTEGER
             {
               enable(1),
               disable(2)
             }
           MAX-ACCESS read-write
           STATUS current
           DESCRIPTION
               "Indicates VLAN-based Source Address Verification (SAV) function for CM configured policies. 
                Options:
                1. enable(1)  -indicates that the VLAN-based Source Address Verification for CM configured
                               policies are enabled.
                2. disable(2) -indicates that the VLAN-based Source Address Verification for CM configured
                               policies are ignored.
               "
           ::= { hwVlanSrvProfEntry 38 }

       hwRipngTunnelSwitch OBJECT-TYPE
           SYNTAX INTEGER
             {
               enable(1),
               disable(2)
             }
           MAX-ACCESS read-write
           STATUS current
           DESCRIPTION
               "Indicates the VLAN-based RIPng transparent transmission function.
                Options:
                1. enable(1)  -indicates that the RIPng transparent transmission function is enabled.
                2. disable(2) -indicates that the RIPng transparent transmission function is disabled.
                This leaf is optional for creating a VLAN service profile.
               "
           ::= { hwVlanSrvProfEntry 39 }

       hwIpv4ArpUnicastSwitch OBJECT-TYPE
           SYNTAX INTEGER
             {
               enable(1),
               disable(2)
             }
           MAX-ACCESS read-write
           STATUS current
           DESCRIPTION
               "Indicates the VLAN-based ARP unicast function.
                Options:
                1. enable(1)  -indicates that the ARP unicast function is enabled.
                2. disable(2) -indicates that the ARP unicast function is disabled.
                This leaf is optional for creating a VLAN service profile.
                Default: disable(2)                
               "
           ::= { hwVlanSrvProfEntry 40 }

    hwIpv4ArpUnicastunkonwnpolicy  OBJECT-TYPE
        SYNTAX INTEGER
        {
           forward(1),
           discard(2)
        }
        MAX-ACCESS read-write
        STATUS current
        DESCRIPTION
            "Used for setting whether to forward or discard ARP packets received from the network side when the user is offline.
             It takes effect only when the ARP unicast function is enabled.
             Options:
             1. forward(1)  -indicates that ARP packets are broadcast to ports inside the VLAN on the user, cascading, and network sides.
             2. discard(2)  -indicates that ARP packets are discarded on the user side, and only broadcast to ports inside the VLAN on the cascading and network sides.
             Default: forward(1)
            "
           ::= { hwVlanSrvProfEntry 41 }  

       hwIpv6NsUnicastSwitch OBJECT-TYPE
           SYNTAX INTEGER
             {
               enable(1),
               disable(2)
             }
           MAX-ACCESS read-write
           STATUS current
           DESCRIPTION
               "Indicates the VLAN-based NS unicast function.
                Options:
                1. enable(1)  -indicates that the NS unicast function is enabled.
                2. disable(2) -indicates that the NS unicast function is disabled.
                This leaf is optional for creating a VLAN service profile.
                Default: disable(2)                 
               "
           ::= { hwVlanSrvProfEntry 42 }

    hwIpv6NsUnicastunkonwnpolicy  OBJECT-TYPE
        SYNTAX INTEGER
        {
           forward(1),
           discard(2)
        }
        MAX-ACCESS read-write
        STATUS current
        DESCRIPTION
            "Used for setting whether to forward or discard NS packets received from the network side when the user is offline.
             It takes effect only when the NS unicast function is enabled.
             Options:
             1. forward(1)  -indicates that NS packets are broadcast to ports inside the VLAN on the user, cascading, and network sides.
             2. discard(2)  -indicates that NS packets are discarded on the user side, and only broadcast to ports inside the VLAN on the cascading and network sides.
             Default: forward(1)
            "
           ::= { hwVlanSrvProfEntry 43 }  
		   
       hwIgmpUserMaxVlanTag OBJECT-TYPE
           SYNTAX INTEGER
             {
               unaware(1),
               untag(2),
               single(3),
               double(4)
             }
           MAX-ACCESS read-write
           STATUS current
           DESCRIPTION
               "Indicates the VLAN-based IGMP user max VLAN tag mode.
                Options:
                1. unaware(1) -indicates that the maximum number of VLAN tags for the IGMP user is not concerned.  
		2. untag(2)   -indicates that the maximum number of VLAN tags for the IGMP user is untag. 
		3. single(3)  -indicates that the maximum number of VLAN tags for the IGMP user is one tag.  
		4. double(4)  -indicates that the maximum number of VLAN tags for the IGMP user is two tags. 
                Default: unaware(1)
                This leaf is optional for creating a VLAN service profile.
               "
           ::= { hwVlanSrvProfEntry 44 }

       hwRouterRedirectReverse OBJECT-TYPE
           SYNTAX INTEGER
             {
               enable(1),
               disable(2)
             }
           MAX-ACCESS read-write
           STATUS current
           DESCRIPTION
               "Indicates the Layer 2 forwarding function of reverse Router-Redirect packets.
                Options:
                1. enable(1)  -indicates that the Layer 2 forwarding function of reverse Router-Redirect packets is enabled.
                2. disable(2) -indicates that the Layer 2 forwarding function of reverse Router-Redirect packets is disabled.
                This leaf is optional for creating a VLAN service profile.
               "
           ::= { hwVlanSrvProfEntry 45 }

       hwCableIPv6SourceVerify OBJECT-TYPE
           SYNTAX INTEGER
             {
               enable(1),
               disable(2)
             }
           MAX-ACCESS read-write
           STATUS current
           DESCRIPTION
               "Indicates VLAN-based IPv6 Source Address Verification (SAV) function for CM configured policies. 
                Options:
                1. enable(1)  -indicates that the VLAN-based IPv6 Source Address Verification for CM configured
                               policies are enabled.
                2. disable(2) -indicates that the VLAN-based IPv6 Source Address Verification for CM configured
                               policies are ignored.
                This leaf is optional for creating a VLAN service profile.
                Default: enable(1) 
               "
           ::= { hwVlanSrvProfEntry 46 }

       hwAntiMacDuplicateSwitch OBJECT-TYPE
           SYNTAX INTEGER
             {
               enable(1),
               disable(2),
               notConfig(3)
             }
           MAX-ACCESS read-write
           STATUS current
           DESCRIPTION
               "Indicates the VLAN-based mac-duplicate function.
                Options:
                1. enable(1)     -indicates that the mac-duplicate function is enabled.
                2. disable(2)    -indicates that the mac-duplicate function is disabled.
                3. notConfig(3)  -indicates by VLAN single switch.
                This leaf is optional for creating a VLAN service profile.
                The VLAN-based mac-duplicate function can be configured in
                hwIpDslamL2pVlanCtrlAntiMacDuplicate of HUAWEI-IPDSLAML2PPORTCONFIG-MIB.
                The status of the mac-duplicate function is determined by its
                VLAN-level switch. The mac-duplicate function of a VLAN is enabled
                only when the VLAN-level switch is enabled.
                If a VLAN service profile is bound to the VLAN,
                the configuration of the VLAN-based mac-duplicate function
                in the VLAN service profile takes effect.
               "
           ::= { hwVlanSrvProfEntry 47 }
           
       hwArpDetectMaxUserCountSwitch OBJECT-TYPE
           SYNTAX INTEGER
             {
               enable(1),
               disable(2)
             }
           MAX-ACCESS read-write
           STATUS current
           DESCRIPTION
               "Indicates the VLAN-based arp-detect max-user-count function.
                Options:
                1. enable(1)  -indicates that the arp-detect max-user-count function is enabled.
                2. disable(2) -indicates that the arp-detect max-user-count function is disabled.
                This leaf is optional for creating a VLAN service profile.  
                The arp-detect max-user-count function in the global mode can be set in
                hwIpDslamArpDetectMaxUserCountSwitch of HUAWEI-IPDSLAM-SECURITY-MIB.
                The final status of the arp-detect max-user-count function is determined by its
                global-level switch and VLAN-level switch. The arp-detect max-user-count function
                of a VLAN is enabled only when the switches at both levels are enabled and the number 
                of users exceeds specification.
				Default: enable(1)
               "
           ::= { hwVlanSrvProfEntry 48 }

	   hwDhcpOption82CaptureArpSwitch OBJECT-TYPE
           SYNTAX INTEGER
             {
               enable(1),
               disable(2)
             }
           MAX-ACCESS read-write
           STATUS current
           DESCRIPTION
               "Indicates the VLAN-based DHCP option 82 capture ARP function.
                Options:
                1. enable(1)  -enable ARP packet capturing when DHCP option82 is enabled.
                2. disable(2) -disable ARP packet capturing when DHCP option82 is enabled.
               "
           ::= { hwVlanSrvProfEntry 49 }
		  
       hwDhcpv6OptionCaptureNaSwitch OBJECT-TYPE
           SYNTAX INTEGER
             {
               enable(1),
               disable(2)
             }
           MAX-ACCESS read-write
           STATUS current
           DESCRIPTION
               "Indicates the VLAN-based DHCPv6 option capture NA function.
                Options:
                1. enable(1)  -enable NA packet capturing when DHCPv6 option is enabled.
                2. disable(2) -disable NA packet capturing when DHCPv6 option is enabled.
               "
           ::= { hwVlanSrvProfEntry 50 }
           
       hwProfileRowStatus   OBJECT-TYPE
           SYNTAX RowStatus
           MAX-ACCESS read-create
           STATUS current
           DESCRIPTION
               "Indicates the row status, used for creating or deleting a VLAN profile.
                Options:
                1. active(1)
                2. createAndGo(4)
                3. destroy(6)
                To create a VLAN service profile, set hwProfileRowStatus to createAndGo(4)
                to perform the set operation. The other leaves are optional.
                To delete a VLAN service profile, set hwProfileRowStatus to
                destroy(6) to perform the set operation.
                To modify a VLAN service profile, you need not specify hwProfileRowStatus,
                but perform the set operation directly on the leaf of the
                corresponding attribute to be modified.
                During query, the value of this leaf is the fixed active(1).
               "
           ::= { hwVlanSrvProfEntry 255 }

       hwSmartVlanIsolateSwitch OBJECT-TYPE
           SYNTAX INTEGER
             {
             enabled(1),
             disabled(2)
             }
           MAX-ACCESS read-write
           STATUS current
           DESCRIPTION
               "Enable/Disable smart VLAN isolate-configuration.
                During the creation of a VLAN service profile, if this leaf is not specified.
                Options:
                1. enabled(1)  -indicates smart VLAN isolate-config is enabled.
                2. disabled(2) -indicates smart VLAN isolate-config is disabled.
                Default: enabled(1)
               "
           ::= { hwVlanMngObject 26 }

       hwVlanIpAwareTable OBJECT-TYPE
           SYNTAX SEQUENCE OF HwVlanIpAwareEntry
           MAX-ACCESS not-accessible
           STATUS current
           DESCRIPTION
               "Enables or disables the IP aware function of a VLAN. After the IP aware function
                is enabled, the destination IP address of the IP packets forwarded in the VLAN
                will be perceived and the packets will be forwarded to different gateways according
                to different destination IP addresses.
                The index of this table is hwVlanIpAwareVlanID.
               "
           ::= { hwVlanMngObject 27 }

       hwVlanIpAwareEntry OBJECT-TYPE
           SYNTAX HwVlanIpAwareEntry
           MAX-ACCESS not-accessible
           STATUS current
           DESCRIPTION
               "Enables or disables the IP aware function of a VLAN. After the IP aware function
                is enabled, the destination IP address of the IP packets forwarded in the VLAN
                will be perceived and the packets will be forwarded to different gateways according
                to different destination IP addresses.
                The index of this entry is hwVlanIpAwareVlanID.
               "
           INDEX { hwVlanIpAwareVlanID }
           ::= { hwVlanIpAwareTable 1 }

       HwVlanIpAwareEntry ::=
           SEQUENCE {
               hwVlanIpAwareVlanID
                   Integer32,
              hwVlanIpAwareVrfName
                   OCTET STRING,
              hwVlanIpAwareRowStatus
                   RowStatus,
              hwVlanIpAwareSrcIPMode
                   INTEGER,
              hwVlanIpAwareArpSendPeriod
                   Integer32
            }

       hwVlanIpAwareVlanID OBJECT-TYPE
           SYNTAX Integer32
           MAX-ACCESS read-only
           STATUS current
           DESCRIPTION
               "Indicates the ID of the VLAN that needs enabling the IP aware service.
                Range: 1-4093
               "
           ::= { hwVlanIpAwareEntry 1 }

       hwVlanIpAwareVrfName OBJECT-TYPE
           SYNTAX OCTET STRING (SIZE (1..31))
           MAX-ACCESS read-write
           STATUS current
           DESCRIPTION
               "Sets the name of the VPN instance bound to a VLAN. The default value is public network.
                It is a character string and the length range is 1-31.
               "
           ::= { hwVlanIpAwareEntry 2 }

       hwVlanIpAwareRowStatus OBJECT-TYPE
           SYNTAX RowStatus
           MAX-ACCESS read-create
           STATUS current
           DESCRIPTION
               "Indicates the row status. It is used to enable or disable the IP aware function.
                Options:
                1. active(1)
                2. createAndGo(4)
                3. destroy(6)
                Only options createAndGo(4) and destroy(6) support the set operation.
                During query, active(1) is always returned for this leaf.
               "
           ::= { hwVlanIpAwareEntry 3 }
       hwVlanIpAwareSrcIPMode OBJECT-TYPE
           SYNTAX INTEGER
               {
                   clientIp(1),
                   virtualIp(2)
               }
           MAX-ACCESS read-write
           STATUS current
           DESCRIPTION
               "Indicates the source IP address obtaining mode of the ARP request.
                Options:
                1. clientIp(1)             -The source IP address obtaining mode is client IP.
                2. virtualIp(2)            -The source IP address obtaining mode is virtual IP.
                Default: clientIp(1)
               "
           DEFVAL { clientIp }
           ::= { hwVlanIpAwareEntry 4 }

       hwVlanIpAwareArpSendPeriod OBJECT-TYPE
           SYNTAX Integer32(5..3600)
           MAX-ACCESS read-write
           STATUS current
           DESCRIPTION
               "Indicates the period for sending ARP requests.
                Range: 5-3600
                Unit: second
                Default: 180s
               "
           DEFVAL { 180 }
       ::= { hwVlanIpAwareEntry 5 }
       hwIpAwareVirtualIPTable OBJECT-TYPE
           SYNTAX SEQUENCE OF HwIpAwareVirtualIPEntry
           MAX-ACCESS not-accessible
           STATUS current
           DESCRIPTION
               "Configures the virtual IP address of a VLAN. After the IP aware function
                of a VLAN is enabled, the VLAN needs to obtain the gateway MAC address
                through the ARP request and use the configured virtual IP address as the
                source IP address of the ARP request.
                The indexes of this table are hwIpAwareVirtualIPVlanID,hwIpAwareVirtualIP,
                and hwIpAwareVirtualIPMask.
               "
           ::= { hwVlanMngObject 28 }

       hwIpAwareVirtualIPEntry OBJECT-TYPE
           SYNTAX HwIpAwareVirtualIPEntry
           MAX-ACCESS not-accessible
           STATUS current
           DESCRIPTION
               "Configures the virtual IP address of a VLAN. After the IP aware function
                of a VLAN is enabled, the VLAN needs to obtain the gateway MAC address
                through the ARP request and use the configured virtual IP address as the
                source IP address of the ARP request.
                The indexes of this entry are hwIpAwareVirtualIPVlanID, hwIpAwareVirtualIP,
                and hwIpAwareVirtualIPMask.
               "
           INDEX { hwIpAwareVirtualIPVlanID,hwIpAwareVirtualIP,hwIpAwareVirtualIPMask }
           ::= { hwIpAwareVirtualIPTable 1 }

       HwIpAwareVirtualIPEntry ::=
           SEQUENCE {
             hwIpAwareVirtualIPVlanID
               Integer32,
             hwIpAwareVirtualIP
               IpAddress,
             hwIpAwareVirtualIPMask
               IpAddress,
             hwIpAwareVirtualIPRowStatus
               RowStatus
            }

       hwIpAwareVirtualIPVlanID OBJECT-TYPE
           SYNTAX Integer32
           MAX-ACCESS read-only
           STATUS current
           DESCRIPTION
               "Indicates the table index. It is the ID of the VLAN that needs configuring a virtual IP address.
               "
           ::= { hwIpAwareVirtualIPEntry 1 }

       hwIpAwareVirtualIP OBJECT-TYPE
           SYNTAX IpAddress
           MAX-ACCESS read-only
           STATUS current
           DESCRIPTION
               "Indicates the virtual IP address.
               "
           ::= { hwIpAwareVirtualIPEntry 2 }

       hwIpAwareVirtualIPMask OBJECT-TYPE
           SYNTAX IpAddress
           MAX-ACCESS read-only
           STATUS current
           DESCRIPTION
               "Indicates the mask of the virtual IP address.
               "
           ::= { hwIpAwareVirtualIPEntry 3 }

       hwIpAwareVirtualIPRowStatus OBJECT-TYPE
           SYNTAX RowStatus
           MAX-ACCESS read-create
           STATUS current
           DESCRIPTION
               "Indicates the row status and is used for creating or deleting an IP address.
                Options:
                1. active(1)
                2. createAndGo(4)
                3. destroy(6)
                Only options createAndGo(4) and destroy(6) support the set operation.
                During query, active(1) is always returned for this leaf.
               "
           ::= { hwIpAwareVirtualIPEntry 4 }

       hwIpAwareRouteTable OBJECT-TYPE
           SYNTAX SEQUENCE OF HwIpAwareRouteEntry
           MAX-ACCESS not-accessible
           STATUS current
           DESCRIPTION
               "Configures the dedicated static route of the IP aware service. When a VLAN whose IP aware
                function is enabled is used to forward IP packets, a static route is required so that packets
                with different IP address segments can be forwarded to the gateway.
                The indexes of this table are hwIpAwareRouteDstIP, hwIpAwareRouteMask and hwIpAwareRouteVlanID.
               "
           ::= { hwVlanMngObject 29 }

       hwIpAwareRouteEntry OBJECT-TYPE
           SYNTAX HwIpAwareRouteEntry
           MAX-ACCESS not-accessible
           STATUS current
           DESCRIPTION
               "Configures the dedicated static route of the IP aware service. When a VLAN whose IP aware
                function is enabled is used to forward IP packets, a static route is required so that packets
                with different IP address segments can be forwarded to the gateway.
                The indexes of this entry are hwIpAwareRouteDstIP, hwIpAwareRouteMask and hwIpAwareRouteVlanID.
               "
           INDEX { hwIpAwareRouteDstIP, hwIpAwareRouteMask, hwIpAwareRouteVlanID }
           ::= { hwIpAwareRouteTable 1 }

       HwIpAwareRouteEntry ::=
           SEQUENCE {
             hwIpAwareRouteDstIP
               IpAddress,
             hwIpAwareRouteMask
               IpAddress,
             hwIpAwareRouteVlanID
               Integer32,
             hwIpAwareRouteNexthopIP
               IpAddress,
             hwIpAwareRouteRowStatus
               RowStatus
            }

       hwIpAwareRouteDstIP OBJECT-TYPE
           SYNTAX IpAddress
           MAX-ACCESS read-write
           STATUS current
           DESCRIPTION
               "Indicates the destination IP address of the static route. It is a table index.
               "
           ::= { hwIpAwareRouteEntry 1 }

       hwIpAwareRouteMask OBJECT-TYPE
           SYNTAX IpAddress
           MAX-ACCESS read-write
           STATUS current
           DESCRIPTION
               "Indicates the static route mask. It is a table index."
           ::= { hwIpAwareRouteEntry 2 }

       hwIpAwareRouteVlanID OBJECT-TYPE
           SYNTAX Integer32
           MAX-ACCESS read-write
           STATUS current
           DESCRIPTION
               "Indicates the VLAN of the static route. It is a table index.
               "
           ::= { hwIpAwareRouteEntry 3 }

       hwIpAwareRouteNexthopIP OBJECT-TYPE
           SYNTAX IpAddress
           MAX-ACCESS read-write
           STATUS current
           DESCRIPTION
               "Indicates the gateway IP address of the static route.
               "
           ::= { hwIpAwareRouteEntry 4 }

       hwIpAwareRouteRowStatus OBJECT-TYPE
           SYNTAX RowStatus
           MAX-ACCESS read-create
           STATUS current
           DESCRIPTION
               "Indicates the row status and is used for creating or deleting
                a static route.
                Options:
                1. active(1)
                2. createAndGo(4)
                3. destroy(6)
                Only options createAndGo(4) and destroy(6) are supported the set operation.
                During query, active(1) is always returned for this leaf.
               "
         ::= { hwIpAwareRouteEntry 5 }

       hwVlanFlowAccountTable OBJECT-TYPE
           SYNTAX SEQUENCE OF HwVlanFlowAccountEntry
           MAX-ACCESS not-accessible
           STATUS current
           DESCRIPTION
               "Describes the VLAN-based traffic statistics, including the numbers of the upstream bytes,
                downstream bytes, upstream packets, downstream packets, upstream and downstream packets
                in the ACL-based traffic statistics collection, discarded upstream packets, and discarded
                downstream packets.
                The indexes of this table are hwVlanIndex (outer VLAN ID) and hwInnerVlanID (inner VLAN ID).
                hwVlanIndex references the leaf in hwVlanMIBTable.
                If hwInnerVlanID is -1, that means the InnerVLAN-based traffic statistics is not supported.
                If hwVlanTrafficOccupiedTable is being used to query the traffic and bandwidth occupancy of
                a VLAN, querying hwVlanFlowAccountTable fails.
               "
           ::= { hwVlanMngObject 14 }

       hwVlanFlowAccountEntry OBJECT-TYPE
           SYNTAX HwVlanFlowAccountEntry
           MAX-ACCESS not-accessible
           STATUS current
           DESCRIPTION
               "Describes the VLAN-based traffic statistics, including the numbers of the upstream bytes,
                downstream bytes, upstream packets, downstream packets, upstream and downstream packets
                in the ACL-based traffic statistics collection, discarded upstream packets, and discarded
                downstream packets.
                The indexes of this entry are hwVlanIndex (outer VLAN ID) and hwInnerVlanID (inner VLAN ID).
                hwVlanIndex references the leaf in hwVlanMIBTable.
                If hwInnerVlanID is -1, that means the InnerVLAN-based traffic statistics is not supported.
                If hwVlanTrafficOccupiedTable is being used to query the traffic and bandwidth occupancy of
                a VLAN, querying hwVlanFlowAccountTable fails.
               "
           INDEX { hwVlanIndex, hwInnerVlanID  }
           ::= { hwVlanFlowAccountTable 1 }

       HwVlanFlowAccountEntry ::=
           SEQUENCE {
               hwInnerVlanID
                   Integer32,
               hwUpFlowAccountByte
                   Counter64,
               hwDownFlowAccountByte
                   Counter64,
               hwUpFlowAccountPacket
                   Counter64,
               hwDownFlowAccountPacket
                   Counter64,
               hwUpStreamPacket
                   Counter64,
               hwDownStreamPacket
                   Counter64,
               hwFlowAccountAdminStatus
                   INTEGER,
               hwUpFlowAccountDiscardPacket
                   Counter64,
               hwDownFlowAccountDiscardPacket
                   Counter64
                }

       hwInnerVlanID OBJECT-TYPE
           SYNTAX Integer32 (-1 | 0..4095)
           MAX-ACCESS read-only
           STATUS current
           DESCRIPTION
               "Indicates the inner VLAN tag in a stacking VLAN.
                If the VLAN is not of the stacking attribute or
                you perform the query operation only by the outer VLAN,
                this leaf must be set to -1.
                Currently, ACL-based VLAN traffic statistics of only the
                outer VLAN can be collected. Therefore, this value of
                this leaf is not useful, and you'd better set the value to -1.
                0 is not supported.
               "
           ::= { hwVlanFlowAccountEntry 1 }

       hwUpFlowAccountByte OBJECT-TYPE
           SYNTAX Counter64
           MAX-ACCESS read-only
           STATUS current
           DESCRIPTION
               "Indicates the number of upstream bytes of a VLAN.
               '18446744073709551615' means invalid value."
           ::= { hwVlanFlowAccountEntry 2 }

       hwDownFlowAccountByte OBJECT-TYPE
           SYNTAX Counter64
           MAX-ACCESS read-only
           STATUS current
           DESCRIPTION
               "Indicates the number of downstream bytes of a VLAN.
               '18446744073709551615' means invalid value."
           ::= { hwVlanFlowAccountEntry 3 }

       hwUpFlowAccountPacket OBJECT-TYPE
           SYNTAX Counter64
           MAX-ACCESS read-only
           STATUS current
           DESCRIPTION
               "Indicates the number of upstream packets of a VLAN.
               '18446744073709551615' means invalid value."
           ::= { hwVlanFlowAccountEntry 4 }

       hwDownFlowAccountPacket OBJECT-TYPE
           SYNTAX Counter64
           MAX-ACCESS read-only
           STATUS current
           DESCRIPTION
               "Indicates the number of downstream packets of a VLAN.
               '18446744073709551615' means invalid value."
           ::= { hwVlanFlowAccountEntry 5 }

       hwUpStreamPacket OBJECT-TYPE
           SYNTAX Counter64
           MAX-ACCESS read-only
           STATUS current
           DESCRIPTION
               "Indicates the number of upstream packets in the
                ACL-based VLAN traffic statistics collection.
                After the first query, 0 is fixedly returned.
                After the second query, traffic statistics of the
                VLAN between the two queries are returned. If the
                query or delete operation is not performed on the
                traffic statistics of this VLAN within 10 minutes,
                the traffic statistics collection of the VLAN is invalid.
                If a new index is specified in the second query,
                the traffic statistics of the new VLAN are collected.
                The system can collect the traffic statistics of
                a maximum of 64 VLANs concurrently.
               '18446744073709551615' means invalid value."
           ::= { hwVlanFlowAccountEntry 6 }

       hwDownStreamPacket OBJECT-TYPE
           SYNTAX Counter64
           MAX-ACCESS read-only
           STATUS current
           DESCRIPTION
               "Indicates the number of downstream packets in the
                ACL-based VLAN traffic statistics collection.
                After the first query, 0 is fixedly returned. After the second query,
                traffic statistics of the VLAN between the two queries are returned.
                If the query or delete operation is not performed on the traffic statistics
                of this VLAN within 10 minutes, the traffic statistics collection of the VLAN is invalid.
                If a new index is specified in the second query, the traffic statistics of
                the new VLAN are collected. The system can collect the traffic
                statistics of a maximum of 64 VLANs concurrently.
               '18446744073709551615' means invalid value."
           ::= { hwVlanFlowAccountEntry 7 }

       hwFlowAccountAdminStatus OBJECT-TYPE
           SYNTAX INTEGER
               {
                   invalid(-1),
                   reset(0),
                   resetAcl(1)
               }
           MAX-ACCESS read-write
           STATUS current
           DESCRIPTION
               "Used to delete the VLAN traffic statistics.
                Options:
                1. invalid(-1) -During the query, the invalid value -1 is fixedly returned.
                2. reset(0)    -indicates that the VLAN traffic statistics based on service board are deleted.
                3. resetAcl(1) -indicates that the VLAN traffic statistics based on ACL are deleted.
               "
           ::= { hwVlanFlowAccountEntry 8 }

       hwUpFlowAccountDiscardPacket OBJECT-TYPE
           SYNTAX Counter64
           MAX-ACCESS read-only
           STATUS current
           DESCRIPTION
               "Indicates the number of upstream discarded packets of a VLAN.
               '18446744073709551615' means invalid value."
           ::= { hwVlanFlowAccountEntry 9 }

       hwDownFlowAccountDiscardPacket OBJECT-TYPE
           SYNTAX Counter64
           MAX-ACCESS read-only
           STATUS current
           DESCRIPTION
               "Indicates the number of downstream discarded packets of a VLAN.
               '18446744073709551615' means invalid value."
           ::= { hwVlanFlowAccountEntry 10 }

       hwVlanTrafficOccupiedTable OBJECT-TYPE
           SYNTAX SEQUENCE OF HwVlanTrafficOccupiedEntry
           MAX-ACCESS not-accessible
           STATUS current
           DESCRIPTION
               "Describes the VLAN-based upstream/downstream rate statistics and bandwidth occupancy.
                The indexes of this table are hwVlanIndex and hwInnerVlanID.
                hwInnerVlanID must be -1, that means the InnerVLAN-based upstream/downstream rate statistics
                and bandwidth occupancy are not supported.
                If hwVlanFlowAccountTable is being used to query the network-side packet statistics of a VLAN,
                querying hwVlanTrafficOccupiedTable fails.
               "
           ::= { hwVlanMngObject 65005 }

       hwVlanTrafficOccupiedEntry OBJECT-TYPE
           SYNTAX HwVlanTrafficOccupiedEntry
           MAX-ACCESS not-accessible
           STATUS current
           DESCRIPTION
               "Describes the VLAN-based upstream/downstream rate statistics and bandwidth occupancy.
                The indexes of this entry are hwVlanIndex and hwInnerVlanID.
                hwInnerVlanID must be -1, that means the InnerVLAN-based upstream/downstream rate statistics
                and bandwidth occupancy are not supported.
                If hwVlanFlowAccountTable is being used to query the network-side packet statistics of a VLAN,
                querying hwVlanTrafficOccupiedTable fails.
               "
           INDEX { hwVlanIndex, hwInnerVlanID }
           ::= { hwVlanTrafficOccupiedTable 1 }

       HwVlanTrafficOccupiedEntry ::=
           SEQUENCE {
               hwVlanUplinkTraffic
                   Unsigned32,
               hwVlanDownTraffic
                   Unsigned32,
               hwVlanUplinkBandwidthOccupancyRate
                   Unsigned32,
               hwVlanDownBandwidthOccupancyRate
                   Unsigned32
                }

       hwVlanUplinkTraffic OBJECT-TYPE
            SYNTAX Unsigned32
            MAX-ACCESS read-only
            STATUS current
            DESCRIPTION
                "Describes the network-side upstream rate of a VLAN.
                 Unit: kbit/s
                "
            ::= { hwVlanTrafficOccupiedEntry 1 }

       hwVlanDownTraffic OBJECT-TYPE
           SYNTAX Unsigned32
           MAX-ACCESS read-only
           STATUS current
           DESCRIPTION
               "Describes the network-side downstream rate of a VLAN.
                Unit: kbit/s
               "
           ::= { hwVlanTrafficOccupiedEntry 2 }

       hwVlanUplinkBandwidthOccupancyRate OBJECT-TYPE
           SYNTAX Unsigned32
           MAX-ACCESS read-only
           STATUS current
           DESCRIPTION
               "Describes the upstream bandwidth occupancy of a VLAN, indicated in percentage.
               "
           ::= { hwVlanTrafficOccupiedEntry 3 }

       hwVlanDownBandwidthOccupancyRate OBJECT-TYPE
           SYNTAX Unsigned32
           MAX-ACCESS read-only
           STATUS current
           DESCRIPTION
               "Describes the downstream bandwidth occupancy of a VLAN, indicated in percentage.
               "
           ::= { hwVlanTrafficOccupiedEntry 4 }


        hwMplsVlanTable OBJECT-TYPE
            SYNTAX SEQUENCE OF HwMplsVlanEntry
            MAX-ACCESS not-accessible
            STATUS current
            DESCRIPTION
                "Indicates information for MPLS VLAN.
                 The index of this table is hwVlanIndex.
                "
            ::= { hwVlanMngObject 65006 }

        hwMplsVlanEntry OBJECT-TYPE
            SYNTAX HwMplsVlanEntry
            MAX-ACCESS not-accessible
            STATUS current
            DESCRIPTION
                "Indicates information for MPLS VLAN.
                 The index of this entry is hwVlanIndex.
                "
            INDEX { hwVlanIndex }
            ::= { hwMplsVlanTable 1 }

        HwMplsVlanEntry ::=
            SEQUENCE {
                hwMplsVlanEnable
                    INTEGER
             }

        hwMplsVlanEnable OBJECT-TYPE
            SYNTAX INTEGER
                {
                    enable(1),
                    disable(2)
                }
            MAX-ACCESS read-write
            STATUS current
            DESCRIPTION
                "Indicates the MPLS function of a VLAN
                Options:
                1. enable(1)   - enable the MPLS function of a VLAN.
                2. disable(2)  - disable the MPLS function of a VLAN."
            ::= { hwMplsVlanEntry 1 }

       hwVlanConnectTable OBJECT-TYPE
           SYNTAX SEQUENCE OF HwVlanConnectEntry
           MAX-ACCESS not-accessible
           STATUS current
           DESCRIPTION
               "Configures the VLAN Connect table.
                The indexes of this table are hwVlanConnectOuterVlanID and hwVlanConnectInnerVlanID.
               "
           ::= { hwVlanMngObject 65007 }

       hwVlanConnectEntry OBJECT-TYPE
           SYNTAX HwVlanConnectEntry
           MAX-ACCESS not-accessible
           STATUS current
           DESCRIPTION
               "Configures the VLAN Connect table.
                The indexes of this entry are hwVlanConnectOuterVlanID and hwVlanConnectInnerVlanID.
               "
           INDEX { hwVlanConnectOuterVlanID, hwVlanConnectInnerVlanID }
           ::= { hwVlanConnectTable 1 }

       HwVlanConnectEntry ::=
           SEQUENCE {
             hwVlanConnectOuterVlanID
               Integer32,
             hwVlanConnectInnerVlanID
               Integer32,
             hwVlanConnectSrcType
               INTEGER,
             hwVlanConnectSrcPara
               Unsigned32,
             hwVlanConnectDstType
               INTEGER,
             hwVlanConnectDstPara
               Integer32,
             hwVlanConnectRowStatus
               RowStatus
            }

        hwVlanConnectOuterVlanID OBJECT-TYPE
           SYNTAX Integer32 (-1 | 1..36863)
           MAX-ACCESS not-accessible
           STATUS current
           DESCRIPTION
               "Indicates the outer VLAN of the VLAN-connect item. It is a table index.
               "
           ::= { hwVlanConnectEntry 1 }

       hwVlanConnectInnerVlanID OBJECT-TYPE
           SYNTAX Integer32 (-1 | 1..4095)
           MAX-ACCESS not-accessible
           STATUS current
           DESCRIPTION
               "Indicates the inner VLAN of the VLAN-connect item. It is a table index.
               "
           ::= { hwVlanConnectEntry 2 }

       hwVlanConnectSrcType OBJECT-TYPE
           SYNTAX INTEGER
             {
                port(1),
                invalid(-1)
             }
           MAX-ACCESS read-write
           STATUS current
           DESCRIPTION
               "Indicates the source point type of VLAN Connect table.
                Options:
                1. port(1) -indicates that hwVlanConnectSrcPara is ifindex.
                2. invalid(-1) -indicates that hwVlanConnectSrcPara is invalid.
               "
           ::= { hwVlanConnectEntry 3 }

       hwVlanConnectSrcPara OBJECT-TYPE
           SYNTAX Unsigned32
           MAX-ACCESS read-write
           STATUS current
           DESCRIPTION
               "Indicates the source point value of VLAN Connect table.
                If hwVlanConnectSrcType is equal to invalid(-1), this leaf indicates invalid.
                If hwVlanConnectSrcType is equal to port(1), this leaf indicates ifindex.
               "
           ::= { hwVlanConnectEntry 4 }

       hwVlanConnectDstType OBJECT-TYPE
           SYNTAX INTEGER
             {
               port(1),
               flow(2),
               bundle(3),
               invalid(-1)
             }
           MAX-ACCESS read-write
           STATUS current
           DESCRIPTION
               "Indicates the source point type of VLAN-connect table.
                Options:
                1. port(1) -indicates that hwVlanConnectDstPara is ifindex.
                2. flow(2) -indicates that hwVlanConnectDstPara is flow index.
                3. bundle(3) -indicates that hwVlanConnectDstPara is bundle index.
                4. invalid(-1) -indicates that hwVlanConnectDstPara is invalid.
               "
           ::= { hwVlanConnectEntry 5 }

       hwVlanConnectDstPara OBJECT-TYPE
           SYNTAX Integer32
           MAX-ACCESS read-write
           STATUS current
           DESCRIPTION
               "Indicates the source point value of VLAN-connect table.
                If hwVlanConnectDstType is equal to invalid(-1), this leaf indicates invalid.
                If hwVlanConnectDstType is equal to port(1), this leaf indicates ifindex.
                If hwVlanConnectDstType is equal to flow(2), this leaf indicates flow index.
                If hwVlanConnectDstType is equal to bundle(3), this leaf indicates bundle index.
               "
           ::= { hwVlanConnectEntry 6 }

       hwVlanConnectRowStatus OBJECT-TYPE
           SYNTAX RowStatus
           MAX-ACCESS read-create
           STATUS current
           DESCRIPTION
               "Indicates the row status and is used for creating or deleting VLAN-connect item.
                Options:
                1. active(1)
                2. createAndGo(4)
                3. destroy(6)
                Only options createAndGo(4) and destroy(6) are supported the set operation.
                During query, active(1) is always returned for this leaf.
               "
         ::= { hwVlanConnectEntry 255 }

       hwDoubleTagTunnelConfig OBJECT IDENTIFIER ::= { hwVlanMngObject 65008 }

       hwDoubleTagTunnelIgmp OBJECT-TYPE
            SYNTAX INTEGER
              {
                enable(1),
                disable(2)
              }
            MAX-ACCESS read-write
            STATUS current
            DESCRIPTION
                "Switch the double tag tunnel function of IGMP packet.
                 Options:
                 1. enable(1)     -Enable the double-tag tunnel function of IGMP packet.
                 2. disable(2)    -Disable the double-tag tunnel function of IGMP packet.
                 The default value is disable(2).
                "
            ::= {  hwDoubleTagTunnelConfig 1 }

       hwDoubleTagTunnelRip OBJECT-TYPE
            SYNTAX INTEGER
              {
                enable(1),
                disable(2)
              }
            MAX-ACCESS read-write
            STATUS current
            DESCRIPTION
                "Switch the double tag tunnel function of RIP packet.
                 Options:
                 1. enable(1)     -Enable the double-tag tunnel function of RIP packet.
                 2. disable(2)    -Disable the double-tag tunnel function of RIP packet.
                 The default value is disable(2).
                "
            ::= {  hwDoubleTagTunnelConfig 2 }

       hwDoubleTagTunnelDhcp OBJECT-TYPE
            SYNTAX INTEGER
              {
                enable(1),
                disable(2)
              }
            MAX-ACCESS read-write
            STATUS current
            DESCRIPTION
                "Switch the double tag tunnel function of DHCP packet.
                 Options:
                 1. enable(1)     -Enable the double-tag tunnel function of DHCP packet.
                 2. disable(2)    -Disable the double-tag tunnel function of DHCP packet.
                 The default value is disable(2).
                "
            ::= {  hwDoubleTagTunnelConfig 3 }

        hwDocsSrvVlanIDTable OBJECT-TYPE
            SYNTAX SEQUENCE OF HwDocsSrvVlanIDEntry
            MAX-ACCESS not-accessible
            STATUS current
            DESCRIPTION
                "
                This is the service svlan of DOCSIS table.
                This table is used to configure the service svlan of DOCSIS service board.
                The indexes of this table are hwFrameIndex and hwSlotIndex.
                "
            ::= { hwVlanMngObject 65009 }

        hwDocsSrvVlanIDEntry OBJECT-TYPE
            SYNTAX HwDocsSrvVlanIDEntry
            MAX-ACCESS not-accessible
            STATUS current
            DESCRIPTION
                "
                This is the service svlan of DOCSIS table.
                This table is used to configure the service svlan of DOCSIS service board.
                The indexes of this entry are hwFrameIndex and hwSlotIndex.
                "
            INDEX { hwFrameIndex, hwSlotIndex }
            ::= { hwDocsSrvVlanIDTable 1 }

        HwDocsSrvVlanIDEntry ::=
            SEQUENCE {
                hwDocsSrvVlanID
                    Integer32,
                hwDocsSrvVlanRowStatus
                    RowStatus
             }

        hwDocsSrvVlanID OBJECT-TYPE
            SYNTAX Integer32 (-1 | 1..4093)
            MAX-ACCESS read-write
            STATUS current
            DESCRIPTION
                "
                Indicates the service svlan of DOCSIS service board.
                Range: 1-4093.
                -1 indicates that hwDocsSrvVlanID is invalid.
                "
            ::= { hwDocsSrvVlanIDEntry 1 }

        hwDocsSrvVlanRowStatus OBJECT-TYPE
            SYNTAX RowStatus
            MAX-ACCESS read-create
            STATUS current
            DESCRIPTION
                "
                Indicates the row status, used for creating or deleting a service VLAN of DOCSIS service board.
                Options:
                1. active(1)
                2. createAndGo(4)
                3. destroy(6)
                To create a service VLAN, you must specify hwDocsSrvVlanID and set
                hwDocsSrvVlanRowStatus to createAndGo(4) to perform the set operation.
                To delete a VLAN, set hwDocsSrvVlanRowStatus to destroy(6) to perform the set operation.
                During query, the value of this leaf is the fixed active(1).
                "
            ::= { hwDocsSrvVlanIDEntry 2 }

        hwVOIPDhcpQosTable OBJECT-TYPE
            SYNTAX SEQUENCE OF HwVOIPDhcpQosEntry
            MAX-ACCESS not-accessible
            STATUS current
            DESCRIPTION
                "
                Indicates the Qos IP tos and VLAN priority.
                The indexes of this table are hwVOIPDhcpVlanID and hwVOIPDhcpQosType.
                "
            ::= { hwVlanMngObject 35 }
        
        hwVOIPDhcpQosEntry OBJECT-TYPE
            SYNTAX HwVOIPDhcpQosEntry
            MAX-ACCESS not-accessible
            STATUS current
            DESCRIPTION
                "
                Indicates the Qos IP tos and VLAN priority.
                The indexes of this entry are hwVOIPDhcpVlanID and hwVOIPDhcpQosType.
                "
            INDEX { hwVOIPDhcpVlanID, hwVOIPDhcpQosType }
            ::= { hwVOIPDhcpQosTable 1 }
        
        HwVOIPDhcpQosEntry ::=
            SEQUENCE { 
                hwVOIPDhcpVlanID
                    Integer32,
                hwVOIPDhcpQosType
                    Integer32,
                hwVOIPDhcpQosIPTos
                    Integer32,
                hwVOIPDhcpQosIPDscp
                    Integer32,
                hwVOIPDhcpQosVlanPriority
                    Integer32,
                hwVOIPDhcpQosRowStatus
                    RowStatus
             }

        hwVOIPDhcpVlanID OBJECT-TYPE
            SYNTAX Integer32 (1..4093)
            MAX-ACCESS not-accessible
            STATUS current
            DESCRIPTION
                "
                Indicates the service VLAN.
                Range: 1-4093. 
                "
            ::= { hwVOIPDhcpQosEntry 1 }
            
        hwVOIPDhcpQosType OBJECT-TYPE
            SYNTAX Integer32 ( 0..1)
            MAX-ACCESS not-accessible
            STATUS current
            DESCRIPTION
                "
                Indicates the type of QOS.
                The value 0 indicates that the type of QOS is signaling. 
                The value 1 indicates that the type of QOS is media.
                "
            ::= { hwVOIPDhcpQosEntry 2 }
       
        hwVOIPDhcpQosIPTos OBJECT-TYPE
            SYNTAX Integer32 (-1 | 0..255)
            MAX-ACCESS read-write
            STATUS current
            DESCRIPTION
                "
                Indicates the Qos value of tos.
                Range: -1, 0-255.
                -1 indicates that the Qos value is invalid.
                "
            ::= { hwVOIPDhcpQosEntry 3 }

        hwVOIPDhcpQosIPDscp OBJECT-TYPE
            SYNTAX Integer32 (-1 | 0..255)
            MAX-ACCESS read-write
            STATUS current
            DESCRIPTION
                "
                Indicates the Qos value of dscp.
                Range: -1, 0-255.
                -1 indicates that the Qos value is invalid.
                "
            ::= { hwVOIPDhcpQosEntry 4 }

        hwVOIPDhcpQosVlanPriority OBJECT-TYPE
            SYNTAX Integer32 (0..7)
            MAX-ACCESS read-write
            STATUS current
            DESCRIPTION
                "
                Indicates the Qos VLAN priority.
                Range: 0-7.
                "
            ::= { hwVOIPDhcpQosEntry 5 }
            
        hwVOIPDhcpQosRowStatus OBJECT-TYPE
           SYNTAX  RowStatus
           MAX-ACCESS  read-create
           STATUS  current
           DESCRIPTION 
               "Indicates the status of this conceptual row.
                Options:
                1. active(1)
                2. createAndGo(4) 
                3. destroy(6)                                                                                                      
               " 
           ::= { hwVOIPDhcpQosEntry 6 }
           
       hwMethNativeVlan OBJECT-TYPE
           SYNTAX Integer32 (-1 | 2..4093)
           MAX-ACCESS read-write
           STATUS current
           DESCRIPTION
               "Indicates the MEth native VLAN.
                Range: -1, 2-4093
                In the set case, -1 indicates delete the MEth native VLAN, 2-4093 indicates set the MEth native VLAN.
                In the get case, when the MEth native VLAN is not set, -1 is returned, otherwise the MEth native VLAN is returned.
                Default: -1
               "
           ::= { hwVlanMngObject 65010 }

        --hwPortVlanOuterEthernetTypeTable 
        hwPortVlanOuterEthernetTypeTable OBJECT-TYPE
            SYNTAX SEQUENCE OF HwPortVlanOuterEthernetTypeEntry
            MAX-ACCESS not-accessible
            STATUS current
            DESCRIPTION
                "
                Indicates the Ethernet protocol type of the outer VLAN tag of a port and VLAN.
                The indexes of this table are ifIndex and hwPortVlanOuterEthernetTypeVlanid.
                "
            ::= { hwVlanMngObject 65011 }

        hwPortVlanOuterEthernetTypeEntry OBJECT-TYPE
            SYNTAX HwPortVlanOuterEthernetTypeEntry
            MAX-ACCESS not-accessible
            STATUS current
            DESCRIPTION
                "
                Indicates the Ethernet protocol type of the outer VLAN tag of a port and VLAN.
                The indexes of this entry are ifIndex and hwPortVlanOuterEthernetTypeVlanid.
                "
            INDEX { ifIndex, hwPortVlanOuterEthernetTypeVlanid }
            ::= { hwPortVlanOuterEthernetTypeTable 1 }

        HwPortVlanOuterEthernetTypeEntry ::=
            SEQUENCE {
                hwPortVlanOuterEthernetTypeVlanid
                    Integer32,
                hwPortVlanOuterEthernetType
                    INTEGER,
                hwPortVlanOuterEthernetTypeRowStatus
                    RowStatus
             }

        hwPortVlanOuterEthernetTypeVlanid OBJECT-TYPE
            SYNTAX Integer32 (1..4095)
            MAX-ACCESS not-accessible
            STATUS current
            DESCRIPTION
                "
                Indicates the VLAN ID input in TPID configuration.
                Range: 1-4095.
                "
            ::= { hwPortVlanOuterEthernetTypeEntry 1 }

        hwPortVlanOuterEthernetType OBJECT-TYPE
           SYNTAX INTEGER
             {
               dot1adTpid(2)
             }
            MAX-ACCESS read-write
            STATUS current
            DESCRIPTION
                "
                Indicates the TPID based on port and VLAN.
                Options:
                1. dot1adTpid(2) -indicates that hwPortVlanOuterEthernetType is dot1adTpid
                "
            ::= { hwPortVlanOuterEthernetTypeEntry 2 }

        hwPortVlanOuterEthernetTypeRowStatus OBJECT-TYPE
            SYNTAX RowStatus
            MAX-ACCESS read-create
            STATUS current
            DESCRIPTION
                "
                Indicates the row status, used for setting, querying or deleting a hwPortVlanOuterEthernetType.
                Options:
                1. active(1)
                2. createAndGo(4)
                3. destroy(6)
                To set a hwPortVlanOuterEthernetType, you must specify hwPortVlanOuterEthernetTypeVlanid and set
                hwPortVlanOuterEthernetTypeRowStatus to createAndGo(4) to perform the set operation.
                To delete a hwPortVlanOuterEthernetType, set hwPortVlanOuterEthernetTypeRowStatus to destroy(6) to perform the set operation.
                During query, the value of this leaf is the fixed active(1).
                "
            ::= { hwPortVlanOuterEthernetTypeEntry 3 }
        --hwPortVlanOuterEthernetTypeTable

       hwVlanInterfaceTrapsVbOids OBJECT IDENTIFIER ::= { hwVlanMngObject 30 }

       hwL3InterfaceType
           OBJECT-TYPE SYNTAX INTEGER
           {
               vlanif(1),
               meth(2)
           }
           MAX-ACCESS accessible-for-notify
           STATUS current
           DESCRIPTION
               "Describes layer 3 interface type.
                Options:
                1. vlanif(1)  -VLAN interface.
                2. meth(2)    -Meth interface.
               "
           ::= { hwVlanInterfaceTrapsVbOids 1 }

       hwVlanifTraps OBJECT IDENTIFIER ::= { hwVlanMngObject 31 }

       hwVlanifCommonTraps OBJECT IDENTIFIER ::= { hwVlanifTraps 1 }

       hwVlanifAlarmTraps OBJECT IDENTIFIER ::= { hwVlanifTraps 2 }

       hwVlanifAlarmTrapsPrefix OBJECT IDENTIFIER ::= { hwVlanifAlarmTraps 0 }

       hwVlanifUpTrap NOTIFICATION-TYPE
           OBJECTS   {
              hwL3InterfaceType,
              hwVlanID
           }
           STATUS current
           DESCRIPTION
               "This notification is generated when the Layer-3 interface 
               link is in the up state.
               "
           ::= { hwVlanifAlarmTraps 0 1 }

       hwVlanifDownTrap NOTIFICATION-TYPE
           OBJECTS   {
               hwL3InterfaceType,
                  hwVlanID
           }
           STATUS current
           DESCRIPTION
               "This notification is generated when the Layer-3 interface 
               link is in the down state.
               "
           ::= { hwVlanifAlarmTraps 0 2 }

       hwVlanCfgTrapsVbOids OBJECT IDENTIFIER ::= { hwVlanMngObject 32 }

       hwVlanList
       OBJECT-TYPE SYNTAX OCTET STRING (SIZE(1..256))
           MAX-ACCESS accessible-for-notify
           STATUS current
           DESCRIPTION
               "Related VLAN ID list information of the VLAN profile."
           ::= { hwVlanCfgTrapsVbOids  1 }

       hwVlanSrvProfOperType OBJECT-TYPE
            SYNTAX INTEGER
              {
                add(1),
                modify(2),
                delete(3)
              }
            MAX-ACCESS accessible-for-notify
            STATUS current
            DESCRIPTION
                "The operate type of the VLAN service profile.
                 Options:
                 1. add(1)     -Add a VLAN service profile.
                 2. modify(2)  -Modify a VLAN service profile.
                 3. delete(3)  -Delete a VLAN service profile.
                "
            ::= {  hwVlanCfgTrapsVbOids 2 }

       hwVlanListType OBJECT-TYPE
           SYNTAX INTEGER
             {
               superVlan(1),
               commonVlan(2),
               subVlan(3),
               primaryVlan(4),
               secondaryVlan(5),
               regionVlan(6),
               smartVlan(7),
               muxVlan(8),
               multiVlan(9)
             }
           MAX-ACCESS accessible-for-notify
           STATUS current
           DESCRIPTION
               "Indicates the type of VLAN list.
                Options:
                1. superVlan(1)      -indicates super VLAN.
                2. commonVlan(2)     -indicates common VLAN.
                3. subVlan(3)        -indicates sub VLAN, the value is not supported.
                4. primaryVlan(4)    -indicates primary VLAN, the value is not supported.
                5. secondaryVlan(5)  -indicates secondary VLAN, the value is not supported.
                6. regionVlan(6)     -indicates region VLAN, the value is not supported.
                7. smartVlan(7)      -indicates smart VLAN.
                8. muxVlan(8)        -indicates MUX VLAN.
                9. multiVlan(9)      -indicates multi VLAN.
               "
           ::= { hwVlanCfgTrapsVbOids 3 }

       hwVlanListAttrib OBJECT-TYPE
           SYNTAX INTEGER
             {
               common(1),
               qinq(2),
               stacking(3),
               subVlan(4)
             }
           MAX-ACCESS accessible-for-notify
           STATUS current
           DESCRIPTION
               "Indicates the attribute of VLAN list.
                Options:
                1. common(1)    -indicates common VLAN.
                2. qinq(2)      -indicates QinQ VLAN.
                3. stacking(3)  -indicates stacking VLAN.
                4. subVlan(4)   -indicates sub VLAN.
               "
           ::= { hwVlanCfgTrapsVbOids 4 }

        hwDedicatedNetwork OBJECT-TYPE
            SYNTAX Unsigned32
            MAX-ACCESS accessible-for-notify
            STATUS current
            DESCRIPTION
                  "Indicates the dedicated network ID."
            ::= { hwVlanCfgTrapsVbOids 5 }

       hwVlanCfgTraps OBJECT IDENTIFIER ::= { hwVlanMngObject 33 }

       hwVlanCfgCommonTraps OBJECT IDENTIFIER ::= { hwVlanCfgTraps 1 }

       hwVlanCfgCommonTrapsPrefix OBJECT IDENTIFIER ::= { hwVlanCfgCommonTraps 0 }

       hwVlanNameChangeInfoTrap NOTIFICATION-TYPE
            OBJECTS {
                    hwConfigChangeIP,
                    hwVlanIndex,
                    hwVlanName,
                    hwDedicatedNetwork
                    }
            STATUS current
            DESCRIPTION
                "The trap to be sent when the VLAN description is changed."
            ::= { hwVlanCfgCommonTraps 0 1 }

       hwVlanForwardingModeInfoTrap NOTIFICATION-TYPE
            OBJECTS {
                    hwConfigChangeIP,
                    hwVlanIndex,
                    hwVlanForwarding,
                    hwDedicatedNetwork
                    }
            STATUS current
            DESCRIPTION
                "The trap to be sent when the VLAN forwarding mode is changed."
            ::= { hwVlanCfgCommonTraps 0 2 }

        hwVlanSrvProfChageInfoTrap NOTIFICATION-TYPE
            OBJECTS {
                    hwConfigChangeIP,
                    hwVlanSrvProfName,
                    hwVlanSrvProfOperType
                    }
            STATUS current
            DESCRIPTION
                "The trap to be sent when the VLAN profile is configured."
            ::= { hwVlanCfgCommonTraps 0 3 }

        hwVlanAndVlanSrvProfOperInfoTrap NOTIFICATION-TYPE
            OBJECTS {
                    hwConfigChangeIP,
                    hwVlanList,
                    hwVlanSrvProfName,
                    hwDedicatedNetwork
                    }
            STATUS current
            DESCRIPTION
                "The trap to be sent when a VLAN profile is bound to or unbound from a VLAN."
            ::= { hwVlanCfgCommonTraps 0 4 }

    hwVlanAddInfoTrap NOTIFICATION-TYPE
            OBJECTS {
                    hwConfigChangeIP,
                    hwVlanList,
                    hwVlanListType,
                    hwVlanListAttrib,
                    hwDedicatedNetwork
                    }
            STATUS current
            DESCRIPTION
                "The trap to be sent when VLANs are added."
            ::= { hwVlanCfgCommonTraps 0 5 }

    hwVlanDelInfoTrap NOTIFICATION-TYPE
            OBJECTS {
                    hwConfigChangeIP,
                    hwVlanList,
                    hwDedicatedNetwork
                    }
            STATUS current
            DESCRIPTION
                "The trap to be sent when VLANs are deleted."
            ::= { hwVlanCfgCommonTraps 0 6 }

    hwVlanAttrChangedInfoTrap NOTIFICATION-TYPE
            OBJECTS {
                    hwConfigChangeIP,
                    hwVlanList,
                    hwVlanListAttrib,
                    hwDedicatedNetwork
                    }
            STATUS current
            DESCRIPTION
                "The trap to be sent when the attribute of VLANs are changed."
            ::= { hwVlanCfgCommonTraps 0 7 }

    hwPortVlanChangedInfoTrap NOTIFICATION-TYPE
            OBJECTS {
                    hwConfigChangeIP,
                    hwVlanList,
                    hwDedicatedNetwork
                    }
            STATUS current
            DESCRIPTION
                "The trap to be sent when the list of the standard ports in VLANs are changed."
            ::= { hwVlanCfgCommonTraps 0 8 }

    hwPacketVlanSwitchPortTable OBJECT-TYPE
            SYNTAX SEQUENCE OF HwPacketVlanSwitchPortEntry
            MAX-ACCESS not-accessible
            STATUS current
            DESCRIPTION
               "
                Configure the port that supports switching VLAN of packet, corresponding to the command line,
                packet vlan-switch port frameid/slotid port-list.
               "
            ::= { hwVlanMngObject 65012 }

    hwPacketVlanSwitchPortEntry OBJECT-TYPE
            SYNTAX HwPacketVlanSwitchPortEntry
            MAX-ACCESS not-accessible
            STATUS current
            DESCRIPTION
               "
                Configure the port that supports switching VLAN of packet, the index is ifIndex.
               "
           INDEX { ifIndex }
           ::= { hwPacketVlanSwitchPortTable 1 }

    HwPacketVlanSwitchPortEntry ::=
           SEQUENCE {
             hwVlanSwitchPortRowStatus
               RowStatus
            }

    hwVlanSwitchPortRowStatus  OBJECT-TYPE
           SYNTAX RowStatus
           MAX-ACCESS read-create
           STATUS current
           DESCRIPTION
               "
                Indicates the row status, used for setting, querying or deleting a hwVlanSwitchPortRowStatus.
                Options:
                1. active(1)
                2. createAndGo(4)
                3. destroy(6)
                To set a hwVlanSwitchPortRowStatus, you must specify ifIndex and set
                hwVlanSwitchPortRowStatus to createAndGo(4) to perform the set operation.
                To delete a ifIndex, set hwVlanSwitchPortRowStatus to destroy(6) to perform the set operation.
                During query, the value of this leaf is the fixed active(1)
               "
           ::= { hwPacketVlanSwitchPortEntry 1 }

    hwPacketVlanSwitchRuleTable OBJECT-TYPE
           SYNTAX SEQUENCE OF HwPacketVlanSwitchRuleEntry
           MAX-ACCESS not-accessible
           STATUS current
           DESCRIPTION
               "
                Configure the VLAN switching rule for the outgoing packets of the device's upstream port,
                corresponding to the command line : packet vlan-switch mac mac-addr vlan-from vlanid vlan-to vlanid.
               "
           ::= { hwVlanMngObject 65013 }

    hwPacketVlanSwitchRuleEntry OBJECT-TYPE
           SYNTAX HwPacketVlanSwitchRuleEntry
           MAX-ACCESS not-accessible
           STATUS current
           DESCRIPTION
               "
                Configure the VLAN switching rule for the outgoing packets of the device's upstream port,
                the index is hwPacketVlanSwitchMac.
               "
           INDEX { hwPacketVlanSwitchMac }
           ::= { hwPacketVlanSwitchRuleTable 1 }

    HwPacketVlanSwitchRuleEntry ::=
           SEQUENCE {
             hwPacketVlanSwitchMac
               MacAddress,
             hwPacketSwitchVlanFrom
               Unsigned32,
             hwPacketSwitchVlanTo
               Unsigned32,
             hwVlanSwitchRuleRowStatus
               RowStatus
            }

    hwPacketVlanSwitchMac OBJECT-TYPE
           SYNTAX MacAddress
           MAX-ACCESS not-accessible
           STATUS current
           DESCRIPTION
               "
                Physical address of Vlan, its index.the format of hwPacketVlanSwitchMac is 0.0.0.0.0.0.
               "
           ::= { hwPacketVlanSwitchRuleEntry 1 }

    hwPacketSwitchVlanFrom OBJECT-TYPE
           SYNTAX Unsigned32
           MAX-ACCESS read-write
           STATUS current
           DESCRIPTION
               "
                Packet switch vlan from, its type is Unsigned32.
               "
           ::= { hwPacketVlanSwitchRuleEntry 2 }

    hwPacketSwitchVlanTo OBJECT-TYPE
           SYNTAX Unsigned32
           MAX-ACCESS read-write
           STATUS current
           DESCRIPTION
               "
                Packet switch vlan to, its type is Unsigned32.
               "
           ::= { hwPacketVlanSwitchRuleEntry 3 }

    hwVlanSwitchRuleRowStatus OBJECT-TYPE
           SYNTAX RowStatus
           MAX-ACCESS read-create
           STATUS current
           DESCRIPTION
               "
                Indicates the row status, used for setting, querying or deleting a hwVlanSwitchRuleRowStatus.
                Options:
                1. active(1)
                2. createAndGo(4)
                3. destroy(6)
                To set a hwVlanSwitchRuleRowStatus, you must specify hwPacketVlanSwitchMac and set
                hwVlanSwitchRuleRowStatus to createAndGo(4) to perform the set operation.
                To delete a hwPacketVlanSwitchMac, set hwVlanSwitchRuleRowStatus to destroy(6) to perform the set operation.
                During query, the value of this leaf is the fixed active(1)
              "
           ::= { hwPacketVlanSwitchRuleEntry 4 }

    hwVlanIfDhcpsOptionTable OBJECT-TYPE
           SYNTAX SEQUENCE OF HwVlanIfDhcpsOptionEntry
           MAX-ACCESS not-accessible
           STATUS current
           DESCRIPTION
              "
               A table for configuring options to DHCP Server of vlan interface,
               include option code type and value and so on.
              "
           ::= { hwVlanMngObject 65014 }

    hwVlanIfDhcpsOptionEntry OBJECT-TYPE
           SYNTAX HwVlanIfDhcpsOptionEntry
           MAX-ACCESS not-accessible
           STATUS current
           DESCRIPTION
              "
               An entry of objects for configuring options to DHCP Server of vlan interface.
 	             The indexes of this entry is hwVlanInterfaceID, hwVlanIfDhcpsOpionCode, hwVlanIfDhcpsOptionSubCode.
              "
           INDEX { hwVlanInterfaceID, hwVlanIfDhcpsOptionCode, hwVlanIfDhcpsOptionSubCode }
           ::= { hwVlanIfDhcpsOptionTable 1 }

    HwVlanIfDhcpsOptionEntry ::=
          SEQUENCE {
              hwVlanIfDhcpsOptionCode
                  Integer32,
              hwVlanIfDhcpsOptionSubCode
                  Integer32,
              hwVlanIfDhcpsOptionType
                  INTEGER,
              hwVlanIfDhcpsOptionRowStatus
                  RowStatus,
              hwVlanIfDhcpsOptionAscii
                  OCTET STRING,
              hwVlanIfDhcpsOptionHexString
                  OCTET STRING,
              hwVlanIfDhcpsOptionCipher
                  OCTET STRING,
              hwVlanIfDhcpsOptionIPString
                  OCTET STRING
          }

    hwVlanIfDhcpsOptionCode OBJECT-TYPE
        SYNTAX Integer32 (1..254)
        MAX-ACCESS read-only
        STATUS current
        DESCRIPTION
            "
             Option code, All options begin with a tag octet, which uniquely
             identifies the option.
            "
        ::= { hwVlanIfDhcpsOptionEntry 1 }
    
    hwVlanIfDhcpsOptionSubCode OBJECT-TYPE
        SYNTAX Integer32 (0..254)
        MAX-ACCESS read-only
        STATUS current
        DESCRIPTION
            "Option sub-code, which is used for identifying the sub-option.
             Default: 0. While choosing 0, it means setting option without sub-option."
        ::= { hwVlanIfDhcpsOptionEntry 2 }

    hwVlanIfDhcpsOptionType OBJECT-TYPE
        SYNTAX INTEGER
            {
            ascii(1),
            hex(2),
            cipher(3),
            ip(4)
            }
        MAX-ACCESS read-create
        STATUS current
        DESCRIPTION
            "The object means option type in DHCP server.
            The value means :
            ascii(1)- The option type is ascii string
            hex(2)  - The option type is hex number
            cipher(3) - The option type is cipher string
            ip(4)   - The option type is ip address"
        ::= { hwVlanIfDhcpsOptionEntry 3 }

    hwVlanIfDhcpsOptionRowStatus OBJECT-TYPE
        SYNTAX RowStatus
        MAX-ACCESS read-create
        STATUS current
        DESCRIPTION
            "This object is used to configuration new rows in this
            table, modify existing rows, and to delete
            existing rows.Only three actions are used: active(1),
            createAndGo(4), destroy(6).
            while configuration new option, you must specify option type 
            and value"
        ::= { hwVlanIfDhcpsOptionEntry 4 }

    hwVlanIfDhcpsOptionAscii OBJECT-TYPE
        SYNTAX OCTET STRING (SIZE (1..255))
        MAX-ACCESS read-create
        STATUS current
        DESCRIPTION
            "Ascii string of a option"
        ::= { hwVlanIfDhcpsOptionEntry 5 }

    hwVlanIfDhcpsOptionHexString OBJECT-TYPE
        SYNTAX OCTET STRING (SIZE (1..255))
        MAX-ACCESS read-create
        STATUS current
        DESCRIPTION
            "Hex string of a option."
        ::= { hwVlanIfDhcpsOptionEntry 6 }

    hwVlanIfDhcpsOptionCipher OBJECT-TYPE
        SYNTAX OCTET STRING (SIZE (1..255))
        MAX-ACCESS read-create
        STATUS current
        DESCRIPTION
            "Cipher string of a option."
        ::= { hwVlanIfDhcpsOptionEntry 7 }

    hwVlanIfDhcpsOptionIPString OBJECT-TYPE
        SYNTAX OCTET STRING (SIZE (1..255))
        MAX-ACCESS read-create
        STATUS current
        DESCRIPTION
            "Ip string of a option."
        ::= { hwVlanIfDhcpsOptionEntry 8 }

    hwVlanIfDhcpsDomainTable OBJECT-TYPE
           SYNTAX SEQUENCE OF HwVlanIfDhcpsDomainEntry
           MAX-ACCESS not-accessible
           STATUS current
           DESCRIPTION
              "
               A table for configuring domain search list to DHCP Server of vlan interface.
              "
           ::= { hwVlanMngObject 65015 }

    hwVlanIfDhcpsDomainEntry OBJECT-TYPE
           SYNTAX HwVlanIfDhcpsDomainEntry
           MAX-ACCESS not-accessible
           STATUS current
           DESCRIPTION
              "
               An entry of objects for configuring domain search list to DHCP Server of vlan interface.
 	             The indexes of this entry is hwVlanInterfaceID, hwVlanIfDhcpsDomainIndex.
              "
           INDEX { hwVlanInterfaceID, hwVlanIfDhcpsDomainIndex }
           ::= { hwVlanIfDhcpsDomainTable 1 }

    HwVlanIfDhcpsDomainEntry ::=
          SEQUENCE {
              hwVlanIfDhcpsDomainIndex
                  Integer32,
              hwVlanIfDhcpsDomainName
                  OCTET STRING,
              hwVlanIfDhcpsDomainRowStatus
                  RowStatus
          }

    hwVlanIfDhcpsDomainIndex OBJECT-TYPE
        SYNTAX Integer32 (0..3)
        MAX-ACCESS read-only
        STATUS current
        DESCRIPTION
            "
             It is index of the DHCP Server domain search list.
            "
        ::= { hwVlanIfDhcpsDomainEntry 1 }
    
    hwVlanIfDhcpsDomainName OBJECT-TYPE
        SYNTAX OCTET STRING (SIZE (1..32))
        MAX-ACCESS read-create
        STATUS current
        DESCRIPTION
            "The domain name that client will use when resolving hostnames via the Domain Name System."
        ::= { hwVlanIfDhcpsDomainEntry 2 }

    hwVlanIfDhcpsDomainRowStatus OBJECT-TYPE
        SYNTAX RowStatus
        MAX-ACCESS read-create
        STATUS current
        DESCRIPTION
            "This object is used to configuration new rows in this
            table, modify existing rows, and to delete
            existing rows.Only three actions are used: active(1),
            createAndGo(4), destroy(6)."
        ::= { hwVlanIfDhcpsDomainEntry 3 }

    hwVlanIfDhcpsExclIpTable OBJECT-TYPE
        SYNTAX SEQUENCE OF HwVlanIfDhcpsExclIpEntry
        MAX-ACCESS not-accessible
        STATUS current
        DESCRIPTION
            "A table for configuring exclude ip to DHCP server, which don't allow to allocate to clients"
        ::= { hwVlanMngObject 65016 }

    hwVlanIfDhcpsExclIpEntry OBJECT-TYPE
        SYNTAX HwVlanIfDhcpsExclIpEntry
        MAX-ACCESS not-accessible
        STATUS current
        DESCRIPTION
            "An entry for configuring exclude ip to DHCP server"
        INDEX { hwVlanInterfaceID, hwVlanIfDhcpsExclStartIp }
        ::= { hwVlanIfDhcpsExclIpTable 1 }

    HwVlanIfDhcpsExclIpEntry ::=
        SEQUENCE {
            hwVlanIfDhcpsExclStartIp
                IpAddress,
            hwVlanIfDhcpsExclEndIp
                IpAddress,
            hwVlanIfDhcpsExclIpRowStatus
                RowStatus
        }

    hwVlanIfDhcpsExclStartIp OBJECT-TYPE
        SYNTAX IpAddress
        MAX-ACCESS read-only
        STATUS current
        DESCRIPTION
            "Start ip address of exclude ip"
        ::= { hwVlanIfDhcpsExclIpEntry 1 }

    hwVlanIfDhcpsExclEndIp OBJECT-TYPE
        SYNTAX IpAddress
        MAX-ACCESS read-create
        STATUS current
        DESCRIPTION
            "End ip address of exclude ip"
        ::= { hwVlanIfDhcpsExclIpEntry 2 }

    hwVlanIfDhcpsExclIpRowStatus OBJECT-TYPE
        SYNTAX RowStatus
        MAX-ACCESS read-create
        STATUS current
        DESCRIPTION
            "This object is used to configuration new rows in this
            table, modify existing rows, and to delete
            existing rows.Only three actions are used: active(1),
            createAndGo(4), destroy(6)
            "
        ::= { hwVlanIfDhcpsExclIpEntry 3 }

    hwVlanIfDhcpsStaBindTable OBJECT-TYPE
        SYNTAX SEQUENCE OF HwVlanIfDhcpsStaBindEntry
        MAX-ACCESS not-accessible
        STATUS current
        DESCRIPTION
            "A table for configuring static binding to DHCP server, which manual binding ip address and mac address"
        ::= { hwVlanMngObject 65017 }

    hwVlanIfDhcpsStaBindEntry OBJECT-TYPE
        SYNTAX HwVlanIfDhcpsStaBindEntry
        MAX-ACCESS not-accessible
        STATUS current
        DESCRIPTION
            "An entry of objects for configuring static binding to DHCP server."
        INDEX { hwVlanInterfaceID, hwVlanIfDhcpsStaBindIp }
        ::= { hwVlanIfDhcpsStaBindTable 1 }

    HwVlanIfDhcpsStaBindEntry ::=
        SEQUENCE {
            hwVlanIfDhcpsStaBindIp
                IpAddress,
            hwVlanIfDhcpsStaBindMac
                MacAddress,
            hwVlanIfDhcpsStaBindDesc
                OCTET STRING,
            hwVlanIfDhcpsStaBindRowStatus
                RowStatus
        }

    hwVlanIfDhcpsStaBindIp OBJECT-TYPE
        SYNTAX IpAddress
        MAX-ACCESS read-only
        STATUS current
        DESCRIPTION
            "Ip address in static binding for DHCP server"
        ::= { hwVlanIfDhcpsStaBindEntry 1 }

    hwVlanIfDhcpsStaBindMac OBJECT-TYPE
        SYNTAX MacAddress
        MAX-ACCESS read-create
        STATUS current
        DESCRIPTION
            "Mac address in static binding for DHCP server"
        ::= { hwVlanIfDhcpsStaBindEntry 2 }

    hwVlanIfDhcpsStaBindDesc OBJECT-TYPE
        SYNTAX OCTET STRING (SIZE (0..255))
        MAX-ACCESS read-create
        STATUS current
        DESCRIPTION
            "A description of the static binding for DHCP server."
        ::= { hwVlanIfDhcpsStaBindEntry 3 }

    hwVlanIfDhcpsStaBindRowStatus OBJECT-TYPE
        SYNTAX RowStatus
        MAX-ACCESS read-create
        STATUS current
        DESCRIPTION
            "This object is used to configuration new rows in this
            table, modify existing rows, and to delete
            existing rows.Only three actions are used: active(1),
            createAndGo(4), destroy(6)
            "
        ::= { hwVlanIfDhcpsStaBindEntry 4 }
    
    hwVlanIfDhcpsIpInUseTable OBJECT-TYPE
        SYNTAX SEQUENCE OF HwVlanIfDhcpsIpInUseEntry
        MAX-ACCESS not-accessible
        STATUS current
        DESCRIPTION
            "A table for displaying the information of ip allocation to clients
            for each vlanif DHCP server pools"
        ::= { hwVlanMngObject 65018 }

    hwVlanIfDhcpsIpInUseEntry OBJECT-TYPE
        SYNTAX HwVlanIfDhcpsIpInUseEntry
        MAX-ACCESS not-accessible
        STATUS current
        DESCRIPTION
            "An entry of objects for displaying information
            of ip in use for each vlanif DHCP server pools"
        INDEX { hwVlanIfDhcpsIpInUseVlan, hwVlanIfDhcpsIpInUseHAddr }
        ::= { hwVlanIfDhcpsIpInUseTable 1 }

    HwVlanIfDhcpsIpInUseEntry ::=
        SEQUENCE {
            hwVlanIfDhcpsIpInUseVlan
                Integer32,
            hwVlanIfDhcpsIpInUseHAddr
                MacAddress,
            hwVlanIfDhcpsIpInUseIP
                IpAddress,
            hwVlanIfDhcpsIpInUseEndLease
                OCTET STRING,
            hwVlanIfDhcpsIpInUseInterface
                Integer32
         }

    hwVlanIfDhcpsIpInUseVlan OBJECT-TYPE
        SYNTAX Integer32 (1..4094)
        MAX-ACCESS read-only
        STATUS current
        DESCRIPTION
            "Vlan informationg that ip address belong to"
        ::= { hwVlanIfDhcpsIpInUseEntry 1 }

    hwVlanIfDhcpsIpInUseHAddr OBJECT-TYPE
        SYNTAX MacAddress
        MAX-ACCESS read-only
        STATUS current
        DESCRIPTION
            "The MAC addreess of host use the ip address in DHCP pools"
        ::= { hwVlanIfDhcpsIpInUseEntry 2 }

    hwVlanIfDhcpsIpInUseIP OBJECT-TYPE
        SYNTAX IpAddress
        MAX-ACCESS read-only
        STATUS current
        DESCRIPTION
            "Ip address allocation to clients in DHCP pools"
        ::= { hwVlanIfDhcpsIpInUseEntry 3 }

    hwVlanIfDhcpsIpInUseEndLease OBJECT-TYPE
        SYNTAX OCTET STRING (SIZE (1..20))
        MAX-ACCESS read-only
        STATUS current
        DESCRIPTION
            "End time of ip address leasese.
            The structure of the OCTET STRING is
            year/month/day:hour:munite:second --
            YYYY/MM/DD:hh:mm:ss"
        ::= { hwVlanIfDhcpsIpInUseEntry 4 }

    hwVlanIfDhcpsIpInUseInterface OBJECT-TYPE
        SYNTAX Integer32
        MAX-ACCESS read-only
        STATUS current
        DESCRIPTION
            "Interface index information that ip address belong to"
        ::= { hwVlanIfDhcpsIpInUseEntry 5 }

    hwVlanIfDhcp6sCfgTable OBJECT-TYPE
        SYNTAX SEQUENCE OF HwVlanIfDhcp6sCfgEntry
        MAX-ACCESS not-accessible
        STATUS current
        DESCRIPTION
            "A table for configuring parameters to DHCPv6 server on this interface"
        ::= { hwVlanMngObject 65019 }

    hwVlanIfDhcp6sCfgEntry OBJECT-TYPE
        SYNTAX HwVlanIfDhcp6sCfgEntry
        MAX-ACCESS not-accessible
        STATUS current
        DESCRIPTION
            "An entry of objects for configuring parameters
 	        to DHCPv6 server on this interface.
 	        The index of this entry is the hwVlanInterfaceID"
        INDEX { hwVlanInterfaceID }
        ::= { hwVlanIfDhcp6sCfgTable 1 }

    HwVlanIfDhcp6sCfgEntry ::=
        SEQUENCE {
            hwVlanIfDhcp6sStatus
                INTEGER,
            hwVlanIfDhcp6sAllowHint
                INTEGER,
            hwVlanIfDhcp6sPreference
                Unsigned32,
            hwVlanIfDhcp6sRapidCommit
                INTEGER,
            hwVlanIfDhcp6sUnicast
                INTEGER,
            hwVlanIfDhcp6sRenewPercent
                Unsigned32,
            hwVlanIfDhcp6sRebindPercent
                Unsigned32,
            hwVlanIfDhcp6sConflictAddrExpireTime
                Unsigned32
        }

    hwVlanIfDhcp6sStatus OBJECT-TYPE
        SYNTAX INTEGER
            {
            disable(1),
            enable(2)
            }
        MAX-ACCESS read-write
        STATUS current
        DESCRIPTION
           "Describes the status of DHCPv6 server on this interface.
                Options:
                1. disable(1) -disable DHCPv6 server.
                2. enable(2)  -enable DHCPv6 server.
                Default: disable(1)
               "
            ::= { hwVlanIfDhcp6sCfgEntry 1 }

    hwVlanIfDhcp6sAllowHint OBJECT-TYPE
        SYNTAX INTEGER
            {
            disable(1),
            enable(2)
            }
        MAX-ACCESS read-write
        STATUS current
        DESCRIPTION
           "Configures the DHCPv6 server to assign prefixes based on the DHCPv6 client request.
                Options:
                1. disable(1) -disable allow hint.
                2. enable(2)  -enable allow hint.
                Default: disable(1)
               "
            ::= { hwVlanIfDhcp6sCfgEntry 2 }

    hwVlanIfDhcp6sPreference OBJECT-TYPE
        SYNTAX Unsigned32 (0..255)
        MAX-ACCESS read-write
        STATUS current
        DESCRIPTION
           "Configures the server priority to be sent by the DHCPv6 server.
                Default: 0 "
            ::= { hwVlanIfDhcp6sCfgEntry 3 }

    hwVlanIfDhcp6sRapidCommit OBJECT-TYPE
        SYNTAX INTEGER
            {
            disable(1),
            enable(2)
            }
        MAX-ACCESS read-write
        STATUS current
        DESCRIPTION
           "Enables fast address prefix assignment for the DHCPv6 server.
                Options:
                1. disable(1) -disable rapid-commit.
                2. enable(2)  -enable rapid-commit.
                Default: disable(1)
               "
            ::= { hwVlanIfDhcp6sCfgEntry 4 }

    hwVlanIfDhcp6sUnicast OBJECT-TYPE
        SYNTAX INTEGER
            {
            disable(1),
            enable(2)
            }
        MAX-ACCESS read-write
        STATUS current
        DESCRIPTION
           "Unicast communication between DHCPv6 clients and a DHCPv6 server
            during address lease renewal.
                Options:
                1. disable(1) -disable unicast.
                2. enable(2)  -enable unicast.
                Default: disable(1)
               "
            ::= { hwVlanIfDhcp6sCfgEntry 5 }

    hwVlanIfDhcp6sRenewPercent OBJECT-TYPE
        SYNTAX Unsigned32 (10..89)
        MAX-ACCESS read-write
        STATUS current
        DESCRIPTION
           "Renew time percent value, indicating the percentage of the lease renewal time
            in the preferred lifetime of an IPv6 address pool.
                Default: 50 "
            ::= { hwVlanIfDhcp6sCfgEntry 6 }

    hwVlanIfDhcp6sRebindPercent OBJECT-TYPE
        SYNTAX Unsigned32 (20..99)
        MAX-ACCESS read-write
        STATUS current
        DESCRIPTION
           "Rebind time percent value, indicating the percentage of the rebinding time
            in the preferred lifetime of an IPv6 address pool.
                Default: 80 "
            ::= { hwVlanIfDhcp6sCfgEntry 7 }

    hwVlanIfDhcp6sConflictAddrExpireTime OBJECT-TYPE
        SYNTAX Unsigned32 (60..4294967295)
        MAX-ACCESS read-write
        STATUS current
        DESCRIPTION
           "Expire time value, indicating the aging time for conflicted addresses in the IPv6 address pool.
                Default: 172800 "
            ::= { hwVlanIfDhcp6sCfgEntry 8 }

    hwVlanIfDhcp6sPrefixTable OBJECT-TYPE
        SYNTAX SEQUENCE OF HwVlanIfDhcp6sPrefixEntry
        MAX-ACCESS not-accessible
        STATUS current
        DESCRIPTION
            "A table for configuring parameters to DHCPv6 server on this interface"
        ::= { hwVlanMngObject 65020 }

    hwVlanIfDhcp6sPrefixEntry OBJECT-TYPE
        SYNTAX HwVlanIfDhcp6sPrefixEntry
        MAX-ACCESS not-accessible
        STATUS current
        DESCRIPTION
            "An entry of objects for configuring parameters
 	        to DHCPv6 server on this interface.
 	        The indexes of this entry are hwVlanInterfaceID and hwVlanIfDhcp6sPrefixAddress"
        INDEX { hwVlanInterfaceID, hwVlanIfDhcp6sPrefixAddress }
        ::= { hwVlanIfDhcp6sPrefixTable 1 }

    HwVlanIfDhcp6sPrefixEntry ::=
        SEQUENCE {
            hwVlanIfDhcp6sPrefixAddress
                Ipv6Address,
            hwVlanIfDhcp6sPrefixLen
                Unsigned32,
            hwVlanIfDhcp6sValidTime
                Unsigned32,
            hwVlanIfDhcp6sValidTimeInfinite
                INTEGER,
            hwVlanIfDhcp6sPreferTime
                Unsigned32,
            hwVlanIfDhcp6sPreferTimeInfinite
                INTEGER,
            hwVlanIfDhcp6sPrefixRowStatus
                RowStatus
        }

    hwVlanIfDhcp6sPrefixAddress OBJECT-TYPE
        SYNTAX    Ipv6Address
        MAX-ACCESS read-write
        STATUS     current
        DESCRIPTION
         "This object specifies the network prefix."
        ::= { hwVlanIfDhcp6sPrefixEntry 1 }

    hwVlanIfDhcp6sPrefixLen OBJECT-TYPE
        SYNTAX     Unsigned32 (16..128)
        MAX-ACCESS read-write
        STATUS     current
        DESCRIPTION
            "This object specifies the network prefix length."
        ::= { hwVlanIfDhcp6sPrefixEntry 2 }

    hwVlanIfDhcp6sValidTime OBJECT-TYPE
        SYNTAX Unsigned32 (60..8640000)
        MAX-ACCESS read-write
        STATUS current
        DESCRIPTION
           "This object specifies the valid lifetime of the IPv6 prefix.
                Default: 172800 "
            ::= { hwVlanIfDhcp6sPrefixEntry 3 }

    hwVlanIfDhcp6sValidTimeInfinite OBJECT-TYPE
        SYNTAX INTEGER
            {
            uninfinite(1),
            infinite(2)
            }
        MAX-ACCESS read-write
        STATUS current
        DESCRIPTION
           "This object Sets the valid lifetime to infinite.
                Options:
                1. uninfinite(1) -the valid lifetime refers to hwVlanIfDhcp6sValidTime.
                2. infinite(2)   -the valid lifetime is infinite.
                Default: uninfinite(1)
               "
            ::= { hwVlanIfDhcp6sPrefixEntry 4 }

    hwVlanIfDhcp6sPreferTime OBJECT-TYPE
        SYNTAX Unsigned32 (60..8640000)
        MAX-ACCESS read-write
        STATUS current
        DESCRIPTION
           "This object specifies the preferred lifetime of the IPv6 prefix.
                Default: 86400 "
            ::= { hwVlanIfDhcp6sPrefixEntry 5 }

    hwVlanIfDhcp6sPreferTimeInfinite OBJECT-TYPE
        SYNTAX INTEGER
            {
            uninfinite(1),
            infinite(2)
            }
        MAX-ACCESS read-write
        STATUS current
        DESCRIPTION
           "This object Sets the preferred lifetime to infinite.
                Options:
                1. uninfinite(1) -the preferred lifetime refers to hwVlanIfDhcp6sPreferTime.
                2. infinite(2)   -the preferred lifetime is infinite.
                Default: uninfinite(1)
               "
            ::= { hwVlanIfDhcp6sPrefixEntry 6 }

    hwVlanIfDhcp6sPrefixRowStatus OBJECT-TYPE
        SYNTAX RowStatus
        MAX-ACCESS read-create
        STATUS current
        DESCRIPTION
            "This object is used to configuration new rows in this table, modify existing rows, and to delete
            existing rows. Only three actions are used: active(1), createAndGo(4), destroy(6)"
        ::= { hwVlanIfDhcp6sPrefixEntry 7 }

    hwVlanIfDhcp6sDnsTable OBJECT-TYPE
        SYNTAX SEQUENCE OF HwVlanIfDhcp6sDnsEntry
        MAX-ACCESS not-accessible
        STATUS current
        DESCRIPTION
            "A table for configuring parameters to DHCPv6 Dns server on this interface"
        ::= { hwVlanMngObject 65021 }

    hwVlanIfDhcp6sDnsEntry OBJECT-TYPE
        SYNTAX HwVlanIfDhcp6sDnsEntry
        MAX-ACCESS not-accessible
        STATUS current
        DESCRIPTION
            "An entry of objects for configuring parameters
 	        to DHCPv6 Dns server on this interface.
 	        The indexes of this entry are hwVlanInterfaceID and hwVlanIfDhcp6sDnsAddress"
        INDEX { hwVlanInterfaceID, hwVlanIfDhcp6sDnsAddress }
        ::= { hwVlanIfDhcp6sDnsTable 1 }

    HwVlanIfDhcp6sDnsEntry ::=
        SEQUENCE {
            hwVlanIfDhcp6sDnsAddress
                Ipv6Address,
            hwVlanIfDhcp6sDnsRowStatus
                RowStatus
        }

    hwVlanIfDhcp6sDnsAddress OBJECT-TYPE
        SYNTAX    Ipv6Address
        MAX-ACCESS read-write
        STATUS     current
        DESCRIPTION
         "This object specifies the IPv6 Address of DNS server."
        ::= { hwVlanIfDhcp6sDnsEntry 1 }

    hwVlanIfDhcp6sDnsRowStatus OBJECT-TYPE
        SYNTAX RowStatus
        MAX-ACCESS read-create
        STATUS current
        DESCRIPTION
            "This object is used to configuration new rows in this table, modify existing rows, and to delete
            existing rows. Only three actions are used: active(1), createAndGo(4), destroy(6)"
        ::= { hwVlanIfDhcp6sDnsEntry 2 }

    hwVlanIfDhcp6sDomainTable OBJECT-TYPE
           SYNTAX SEQUENCE OF HwVlanIfDhcp6sDomainEntry
           MAX-ACCESS not-accessible
           STATUS current
           DESCRIPTION
              "A table for configuring domain search list to DHCPv6 server of vlan interface."
           ::= { hwVlanMngObject 65022 }

    hwVlanIfDhcp6sDomainEntry OBJECT-TYPE
        SYNTAX HwVlanIfDhcp6sDomainEntry
        MAX-ACCESS not-accessible
        STATUS current
        DESCRIPTION
            "An entry of objects for configuring domain search list to DHCPv6 server of vlan interface.
                The indexes of this entry are hwVlanInterfaceID and hwVlanIfDhcp6sDomainName."
        INDEX { hwVlanInterfaceID, hwVlanIfDhcp6sDomainName }
        ::= { hwVlanIfDhcp6sDomainTable 1 }

    HwVlanIfDhcp6sDomainEntry ::=
        SEQUENCE {
            hwVlanIfDhcp6sDomainName
                OCTET STRING,
            hwVlanIfDhcp6sDomainRowStatus
                RowStatus
        }
    
    hwVlanIfDhcp6sDomainName OBJECT-TYPE
        SYNTAX OCTET STRING (SIZE (1..63))
        MAX-ACCESS read-create
        STATUS current
        DESCRIPTION
            "The domain name that DHCPv6 client will use when resolving hostnames via the Domain Name System."
        ::= { hwVlanIfDhcp6sDomainEntry 1 }

    hwVlanIfDhcp6sDomainRowStatus OBJECT-TYPE
        SYNTAX RowStatus
        MAX-ACCESS read-create
        STATUS current
        DESCRIPTION
            "This object is used to configuration new rows in this table, modify existing rows, and to delete
            existing rows. Only three actions are used: active(1), createAndGo(4), destroy(6)."
        ::= { hwVlanIfDhcp6sDomainEntry 2 }

    hwVlanIfDhcp6sExcIPTable OBJECT-TYPE
        SYNTAX SEQUENCE OF HwVlanIfDhcp6sExcIPEntry
        MAX-ACCESS not-accessible
        STATUS current
        DESCRIPTION
            "A table for configuring parameters to DHCPv6 server excluded IP on this interface"
        ::= { hwVlanMngObject 65023 }
 
    hwVlanIfDhcp6sExcIPEntry OBJECT-TYPE
        SYNTAX HwVlanIfDhcp6sExcIPEntry
        MAX-ACCESS not-accessible
        STATUS current
        DESCRIPTION
            "An entry of objects for configuring parameters
 	        to DHCPv6 server excluded IP on this interface.
 	        The indexes of this entry are hwVlanInterfaceID, hwVlanIfDhcp6sStartIPv6Address"
        INDEX { hwVlanInterfaceID, hwVlanIfDhcp6sStartIPv6Address }
        ::= { hwVlanIfDhcp6sExcIPTable 1 }
 
    HwVlanIfDhcp6sExcIPEntry ::=
        SEQUENCE {
            hwVlanIfDhcp6sStartIPv6Address
                Ipv6Address,
            hwVlanIfDhcp6sEndIPv6Address
                Ipv6Address,
            hwVlanIfDhcp6sExcIPRowStatus
                RowStatus
        }
 
    hwVlanIfDhcp6sStartIPv6Address OBJECT-TYPE
        SYNTAX    Ipv6Address
        MAX-ACCESS read-write
        STATUS     current
        DESCRIPTION
         "This object specifies the start IPv6 Address of excluded IP."
        ::= { hwVlanIfDhcp6sExcIPEntry 1 }
 
    hwVlanIfDhcp6sEndIPv6Address OBJECT-TYPE
        SYNTAX    Ipv6Address
        MAX-ACCESS read-write
        STATUS     current
        DESCRIPTION
         "This object specifies the end IPv6 Address of excluded IP."
        ::= { hwVlanIfDhcp6sExcIPEntry 2 }
 
    hwVlanIfDhcp6sExcIPRowStatus OBJECT-TYPE
        SYNTAX RowStatus
        MAX-ACCESS read-create
        STATUS current
        DESCRIPTION
            "This object is used to configuration new rows in this table, modify existing rows, and to delete
            existing rows. Only three actions are used: active(1), createAndGo(4), destroy(6)"
        ::= { hwVlanIfDhcp6sExcIPEntry 3 }

    hwVlanIfDhcp6sPDTable OBJECT-TYPE
        SYNTAX SEQUENCE OF HwVlanIfDhcp6sPDEntry
        MAX-ACCESS not-accessible
        STATUS current
        DESCRIPTION
            "A table for configuring agent prefix in the address pool view"
        ::= { hwVlanMngObject 65024 }

    hwVlanIfDhcp6sPDEntry OBJECT-TYPE
        SYNTAX HwVlanIfDhcp6sPDEntry
        MAX-ACCESS not-accessible
        STATUS current
        DESCRIPTION
            "An entry of objects for configuring agent prefix in the address pool view.
 	        The indexes of this entry are hwVlanInterfaceID and hwVlanIfDhcp6sPDPrefixAddress"
        INDEX { hwVlanInterfaceID, hwVlanIfDhcp6sPDPrefixAddress }
        ::= { hwVlanIfDhcp6sPDTable 1 }

    HwVlanIfDhcp6sPDEntry ::=
        SEQUENCE {
            hwVlanIfDhcp6sPDPrefixAddress
                Ipv6Address,
            hwVlanIfDhcp6sPDPrefixLen
                Unsigned32,
            hwVlanIfDhcp6sAssignPrefixLen
                Unsigned32,
            hwVlanIfDhcp6sPDValidTime
                Unsigned32,
            hwVlanIfDhcp6sIfPDValidTimeInfinite
                INTEGER,
            hwVlanIfDhcp6sPDPreferTime
                Unsigned32,
            hwVlanIfDhcp6sIfPDPreferTimeInfinite
                INTEGER,
            hwVlanIfDhcp6sPDRowStatus
                RowStatus
        }

    hwVlanIfDhcp6sPDPrefixAddress OBJECT-TYPE
        SYNTAX Ipv6Address
        MAX-ACCESS read-write
        STATUS     current
        DESCRIPTION
         "This object specifies the delegation prefix."
        ::= { hwVlanIfDhcp6sPDEntry 1 }
                 
    hwVlanIfDhcp6sPDPrefixLen OBJECT-TYPE
        SYNTAX Unsigned32 (1..128)
        MAX-ACCESS read-write
        STATUS     current
        DESCRIPTION
            "This object specifies the delegation prefix length."
        ::= { hwVlanIfDhcp6sPDEntry 2 }

    hwVlanIfDhcp6sAssignPrefixLen OBJECT-TYPE
        SYNTAX Unsigned32 (1..128)
        MAX-ACCESS read-write
        STATUS     current
        DESCRIPTION
            "This object specifies the the assignable prefix length."
        ::= { hwVlanIfDhcp6sPDEntry 3 }

    hwVlanIfDhcp6sPDValidTime OBJECT-TYPE
        SYNTAX Unsigned32 (60..172799999)
        MAX-ACCESS read-write
        STATUS current
        DESCRIPTION
           "This object specifies the valid lifetime of the delegation prefix.
                Default: 172800 "
            ::= { hwVlanIfDhcp6sPDEntry 4 }
    
    hwVlanIfDhcp6sIfPDValidTimeInfinite OBJECT-TYPE
        SYNTAX INTEGER
            {
            uninfinite(1),
            infinite(2)
            }
        MAX-ACCESS read-write
        STATUS current
        DESCRIPTION
           "This object Sets the valid lifetime to infinite.
                Options:
                1. uninfinite(1) -the valid lifetime refers to hwVlanIfDhcp6sPDValidTime.
                2. infinite(2)   -the valid lifetime is infinite.
                Default: uninfinite(1)
               "
            ::= { hwVlanIfDhcp6sPDEntry 5}
    
    hwVlanIfDhcp6sPDPreferTime OBJECT-TYPE
        SYNTAX Unsigned32 (60..172799999)
        MAX-ACCESS read-write
        STATUS current
        DESCRIPTION
           "This object specifies the preferred lifetime of the delegation prefix.
                Default: 86400 "
            ::= { hwVlanIfDhcp6sPDEntry 6 }
    
    hwVlanIfDhcp6sIfPDPreferTimeInfinite OBJECT-TYPE
        SYNTAX INTEGER
            {
            uninfinite(1),
            infinite(2)
            }
        MAX-ACCESS read-write
        STATUS current
        DESCRIPTION
           "This object Sets the preferred lifetime to infinite.
                Options:
                1. uninfinite(1) -the preferred lifetime refers to hwVlanIfDhcp6sPDPreferTime.
                2. infinite(2)   -the preferred lifetime is infinite.
                Default: uninfinite(1)
               "
            ::= { hwVlanIfDhcp6sPDEntry 7 }

    hwVlanIfDhcp6sPDRowStatus OBJECT-TYPE
        SYNTAX RowStatus
        MAX-ACCESS read-create
        STATUS current
        DESCRIPTION
            "This object is used to configuration new rows in this table, modify existing rows, and to delete
            existing rows. Only three actions are used: active(1), createAndGo(4), destroy(6)."
        ::= { hwVlanIfDhcp6sPDEntry 8 }    

    hwVlanIfDhcp6sOptionTable OBJECT-TYPE
        SYNTAX SEQUENCE OF HwVlanIfDhcp6sOptionEntry
        MAX-ACCESS not-accessible
        STATUS current
        DESCRIPTION
            "
            A table for configuring options to DHCPv6 server of vlan interface,
            include option code type and value and so on.
            "
        ::= { hwVlanMngObject 65025 }

    hwVlanIfDhcp6sOptionEntry OBJECT-TYPE
        SYNTAX HwVlanIfDhcp6sOptionEntry
        MAX-ACCESS not-accessible
        STATUS current
        DESCRIPTION
            "
            An entry of objects for configuring options to DHCPv6 server of vlan interface.
                The indexes of this entry are hwVlanInterfaceID, hwVlanIfDhcp6sVendorId, hwVlanIfDhcp6sOptionSubCode.
            "
        INDEX { hwVlanInterfaceID, hwVlanIfDhcp6sVendorId, hwVlanIfDhcp6sOptionSubCode }
        ::= { hwVlanIfDhcp6sOptionTable 1 }

    HwVlanIfDhcp6sOptionEntry ::=
        SEQUENCE {
            hwVlanIfDhcp6sVendorId
                Unsigned32,
            hwVlanIfDhcp6sOptionSubCode
                Integer32,
            hwVlanIfDhcp6sOptionType
                INTEGER,
            hwVlanIfDhcp6sOptionRowStatus
                RowStatus,
            hwVlanIfDhcp6sOptionIpv6Addr1
                Ipv6Address,
            hwVlanIfDhcp6sOptionIpv6Addr2
                Ipv6Address,
            hwVlanIfDhcp6sOptionIpv6Addr3
                Ipv6Address,
            hwVlanIfDhcp6sOptionIpv6Addr4
                Ipv6Address,
            hwVlanIfDhcp6sOptionAscii
                OCTET STRING,
            hwVlanIfDhcp6sOptionHexString
                OCTET STRING
        }

    hwVlanIfDhcp6sVendorId OBJECT-TYPE
        SYNTAX Unsigned32 (1..4294967295)
        MAX-ACCESS read-create
        STATUS current
        DESCRIPTION
            "
             Vendor identifier, which uniquely identifies the vendor. 2011 is the identifier for Huawei.
            "
        ::= { hwVlanIfDhcp6sOptionEntry 1 }

    hwVlanIfDhcp6sOptionSubCode OBJECT-TYPE
        SYNTAX Integer32 (1..65535)
        MAX-ACCESS read-create
        STATUS current
        DESCRIPTION
            "Dhcp6s Option sub-code, which is used for identifying the sub-option."
        ::= { hwVlanIfDhcp6sOptionEntry 2 }

    hwVlanIfDhcp6sOptionType OBJECT-TYPE
        SYNTAX INTEGER
            {
            ipv6(1),
            ascii(2),
            hex(3)
            }
        MAX-ACCESS read-create
        STATUS current
        DESCRIPTION
            "The object means option type in DHCPv6 server.
            The value means :
            ipv6(1)   - The option type is ipv6 address
            ascii(2)- The option type is ascii string
            hex(3)  - The option type is hex number"
        ::= { hwVlanIfDhcp6sOptionEntry 3 }

    hwVlanIfDhcp6sOptionIpv6Addr1 OBJECT-TYPE
        SYNTAX Ipv6Address
        MAX-ACCESS read-create
        STATUS current
        DESCRIPTION
            "First ipv6 address of a option."
        ::= { hwVlanIfDhcp6sOptionEntry 4}

    hwVlanIfDhcp6sOptionIpv6Addr2 OBJECT-TYPE
        SYNTAX Ipv6Address
        MAX-ACCESS read-create
        STATUS current
        DESCRIPTION
            "Second ipv6 address of a option."
        ::= { hwVlanIfDhcp6sOptionEntry 5 }

    hwVlanIfDhcp6sOptionIpv6Addr3 OBJECT-TYPE
        SYNTAX Ipv6Address
        MAX-ACCESS read-create
        STATUS current
        DESCRIPTION
            "Third ipv6 address of a option."
        ::= { hwVlanIfDhcp6sOptionEntry 6 }

    hwVlanIfDhcp6sOptionIpv6Addr4 OBJECT-TYPE
        SYNTAX Ipv6Address
        MAX-ACCESS read-create
        STATUS current
        DESCRIPTION
            "Fourth ipv6 address of a option."
        ::= { hwVlanIfDhcp6sOptionEntry 7 }

    hwVlanIfDhcp6sOptionAscii OBJECT-TYPE
        SYNTAX OCTET STRING (SIZE (1..255))
        MAX-ACCESS read-create
        STATUS current
        DESCRIPTION
            "Ascii string of a option"
        ::= { hwVlanIfDhcp6sOptionEntry 8 }

    hwVlanIfDhcp6sOptionHexString OBJECT-TYPE
        SYNTAX OCTET STRING (SIZE (2..128))
        MAX-ACCESS read-create
        STATUS current
        DESCRIPTION
            "Hex string of a option."
        ::= { hwVlanIfDhcp6sOptionEntry 9 }

    hwVlanIfDhcp6sOptionRowStatus OBJECT-TYPE
        SYNTAX RowStatus
        MAX-ACCESS read-create
        STATUS current
        DESCRIPTION
            "This object is used to configuration new rows in this table, modify existing rows, and to delete
            existing rows. Only three actions are used: active(1), createAndGo(4), destroy(6).
            While configuration new option, you must specify option type and value"
        ::= { hwVlanIfDhcp6sOptionEntry 10 }
    
    hwVlanIfDhcp6sIpInUseTable OBJECT-TYPE
        SYNTAX SEQUENCE OF HwVlanIfDhcp6sIpInUseEntry
        MAX-ACCESS not-accessible
        STATUS current
        DESCRIPTION
            "A table for displaying the information of ip allocation to clients
            for each vlanif DHCPv6 server pools"
        ::= { hwVlanMngObject 65026 }

    hwVlanIfDhcp6sIpInUseEntry OBJECT-TYPE
        SYNTAX HwVlanIfDhcp6sIpInUseEntry
        MAX-ACCESS not-accessible
        STATUS current
        DESCRIPTION
            "An entry of objects for displaying information
            of ip in use for each vlanif DHCPv6 server pools"
        INDEX { hwVlanIfDhcp6sIpInUseVlan, hwVlanIfDhcp6sIpInUseIP }
        ::= { hwVlanIfDhcp6sIpInUseTable 1 }

    HwVlanIfDhcp6sIpInUseEntry ::=
        SEQUENCE {
            hwVlanIfDhcp6sIpInUseVlan
                Integer32,
            hwVlanIfDhcp6sIpInUseIP
                Ipv6Address
         }

    hwVlanIfDhcp6sIpInUseVlan OBJECT-TYPE
        SYNTAX Integer32 (1..4094)
        MAX-ACCESS read-only
        STATUS current
        DESCRIPTION
            "Vlan information that ip address belongs to"
        ::= { hwVlanIfDhcp6sIpInUseEntry 1 }

    hwVlanIfDhcp6sIpInUseIP OBJECT-TYPE
        SYNTAX Ipv6Address
        MAX-ACCESS read-only
        STATUS current
        DESCRIPTION
            "Ipv6 address allocation to clients in DHCPv6 pools"
        ::= { hwVlanIfDhcp6sIpInUseEntry 2 }

    hwVlanIfDhcp6sPdInUseTable OBJECT-TYPE
        SYNTAX SEQUENCE OF HwVlanIfDhcp6sPdInUseEntry
        MAX-ACCESS not-accessible
        STATUS current
        DESCRIPTION
            "A table for displaying the information of ip allocation to prefix delegation clients
            for each vlanif DHCPv6 server pools"
        ::= { hwVlanMngObject 65027 }

    hwVlanIfDhcp6sPdInUseEntry OBJECT-TYPE
        SYNTAX HwVlanIfDhcp6sPdInUseEntry
        MAX-ACCESS not-accessible
        STATUS current
        DESCRIPTION
            "An entry of objects for displaying information
            of ip in use for each vlanif DHCPv6 server pools"
        INDEX { hwVlanIfDhcp6sPdInUseVlan, hwVlanIfDhcp6sPdInUseIP, hwVlanIfDhcp6sPdInUseAssignPrefixLen }
        ::= { hwVlanIfDhcp6sPdInUseTable 1 }

    HwVlanIfDhcp6sPdInUseEntry ::=
        SEQUENCE {
            hwVlanIfDhcp6sPdInUseVlan
                Integer32,
            hwVlanIfDhcp6sPdInUseIP
                Ipv6Address,
            hwVlanIfDhcp6sPdInUseAssignPrefixLen
                Unsigned32
         }

    hwVlanIfDhcp6sPdInUseVlan OBJECT-TYPE
        SYNTAX Integer32 (1..4094)
        MAX-ACCESS read-only
        STATUS current
        DESCRIPTION
            "Vlan information that ip address belongs to"
        ::= { hwVlanIfDhcp6sPdInUseEntry 1 }

    hwVlanIfDhcp6sPdInUseIP OBJECT-TYPE
        SYNTAX Ipv6Address
        MAX-ACCESS read-only
        STATUS current
        DESCRIPTION
            "Ipv6 address allocation to clients in DHCPv6 pools"
        ::= { hwVlanIfDhcp6sPdInUseEntry 2 }

    hwVlanIfDhcp6sPdInUseAssignPrefixLen OBJECT-TYPE
        SYNTAX Unsigned32 (1..128)
        MAX-ACCESS read-only
        STATUS     current
        DESCRIPTION
            "This object specifies the assignable prefix length."
        ::= { hwVlanIfDhcp6sPdInUseEntry 3 }

    hwVlanIfDhcpsOption121Table OBJECT-TYPE
           SYNTAX SEQUENCE OF HwVlanIfDhcpsOption121Entry
           MAX-ACCESS not-accessible
           STATUS current
           DESCRIPTION
              "
               A table for configuring 121 option to DHCP Server of vlan interface,
               include route info and so on.
              "
           ::= { hwVlanMngObject 65028 }

    hwVlanIfDhcpsOption121Entry OBJECT-TYPE
        SYNTAX HwVlanIfDhcpsOption121Entry
        MAX-ACCESS not-accessible
        STATUS current
        DESCRIPTION
            "
            An entry of objects for configuring 121 option to DHCP Server of vlan interface.
 	        The indexes of this entry is hwVlanInterfaceID, hwVlanIfDhcpsOpt121Dest,
            hwVlanIfDhcpsOpt121MaskLen, hwVlanIfDhcpsOpt121NextHop.
            "
        INDEX { hwVlanInterfaceID, hwVlanIfDhcpsOpt121Dest, hwVlanIfDhcpsOpt121MaskLen, hwVlanIfDhcpsOpt121NextHop }
        ::= { hwVlanIfDhcpsOption121Table 1 }

    HwVlanIfDhcpsOption121Entry ::=
        SEQUENCE {
            hwVlanIfDhcpsOpt121Dest
                IpAddress,
            hwVlanIfDhcpsOpt121MaskLen
                Integer32,
            hwVlanIfDhcpsOpt121NextHop
                IpAddress,
            hwVlanIfDhcpsOpt121RowStatus
                RowStatus
        }

    hwVlanIfDhcpsOpt121Dest OBJECT-TYPE
        SYNTAX IpAddress
        MAX-ACCESS read-only
        STATUS current
        DESCRIPTION
            "The destination address of route information in option121."
        ::= { hwVlanIfDhcpsOption121Entry 1 }

    hwVlanIfDhcpsOpt121MaskLen OBJECT-TYPE
        SYNTAX Integer32 (0..32)
        MAX-ACCESS read-only
        STATUS current
        DESCRIPTION
            "The mask length of route information in option121."
        ::= { hwVlanIfDhcpsOption121Entry 2 }

    hwVlanIfDhcpsOpt121NextHop OBJECT-TYPE
        SYNTAX IpAddress
        MAX-ACCESS read-only
        STATUS current
        DESCRIPTION
            "The next-hop address of route information in option121."
        ::= { hwVlanIfDhcpsOption121Entry 3 }

    hwVlanIfDhcpsOpt121RowStatus OBJECT-TYPE
        SYNTAX RowStatus
        MAX-ACCESS read-create
        STATUS current
        DESCRIPTION
            "This object is used to configuration new rows in this
            table, modify existing rows, and to delete
            existing rows.Only three actions are used: active(1),
            createAndGo(4), destroy(6).
            while configuration new option, you must specify option type
            and value"
        ::= { hwVlanIfDhcpsOption121Entry 4 }

    hwVlanTlsTable OBJECT-TYPE
           SYNTAX SEQUENCE OF HwVlanTlsEntry
           MAX-ACCESS not-accessible
           STATUS current
           DESCRIPTION
              "
               A table for configuring TLS VLAN.
              "
           ::= { hwVlanMngObject 65029 }

    hwVlanTlsEntry OBJECT-TYPE
        SYNTAX HwVlanTlsEntry
        MAX-ACCESS not-accessible
        STATUS current
        DESCRIPTION
            "
            An entry of objects for configuring TLS VLAN.
            "
        INDEX { hwVlanTlsIfIndex, hwVlanTlsDedicatedNetworkId, hwVlanTlsSVlanId }
        ::= { hwVlanTlsTable 1 }

    HwVlanTlsEntry ::=
        SEQUENCE {
            hwVlanTlsIfIndex
                Integer32,
            hwVlanTlsDedicatedNetworkId
                Integer32,
            hwVlanTlsSVlanId
                Integer32,
            hwVlanTlsCVLanIdList
            	OCTET STRING,
            hwVlanTlsVLanIdRowStatus
                RowStatus
        }

    hwVlanTlsIfIndex OBJECT-TYPE
        SYNTAX Integer32
        MAX-ACCESS not-accessible
        STATUS current   
        DESCRIPTION
            "Indicates the ifindex of the of uplink ports."
        ::= { hwVlanTlsEntry 1 }


    hwVlanTlsDedicatedNetworkId OBJECT-TYPE
        SYNTAX Integer32 (0..8)
        MAX-ACCESS not-accessible
        STATUS current        
        DESCRIPTION
            "Indicates the Dedicated network ID."
        ::= { hwVlanTlsEntry 2 }

    hwVlanTlsSVlanId OBJECT-TYPE
        SYNTAX Integer32 (1..4093)
        MAX-ACCESS not-accessible
        STATUS current   
        DESCRIPTION
            "Indicates the S-VLAN ID of the VLAN TLS config."
        ::= { hwVlanTlsEntry 3 }
                                                    
    hwVlanTlsCVLanIdList OBJECT-TYPE
        SYNTAX OCTET STRING
        MAX-ACCESS read-write
        STATUS current
        DESCRIPTION
            "Indicates the C-VLAN list of the VLAN TLS config."
        ::= { hwVlanTlsEntry 4 }

    hwVlanTlsVLanIdRowStatus OBJECT-TYPE
        SYNTAX RowStatus
        MAX-ACCESS read-create
        STATUS current
        DESCRIPTION
            "Indicates the row status, used for creating or deleting TLS VLAN configuration.
 	         Options:
 	         1. active(1)
 	         2. createAndGo(4)
 	         3. destroy(6)."
        ::= { hwVlanTlsEntry  5 }
END
