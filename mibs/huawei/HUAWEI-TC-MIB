-- ============================================================================
-- Copyright (C) 2025 by HUAWEI TECHNOLOGIES. All rights reserved.
--
-- Description: This module defines TEXTUAL-CONVENTION that is used by Huawei devices,
-- including HWFrameType, HWPCBType,HWSubPCBType, and HWPortType. The following talbe
-- lists the code area used by each product.

-- Reference:
-- Version: V60.01
-- History:562051

-- ============================================================================
    HUAWEI-TC-MIB DEFINITIONS ::= BEGIN
        IMPORTS
            Integer32,IpAddress, OBJECT-TYPE, MODULE-IDENTITY, OBJECT-IDENTITY,
            NOTIFICATION-TYPE
                FROM SNMPv2-SMI
            TEXTUAL-CONVENTION,DateAndTime,MacAddress
                FROM SNMPv2-TC
            huawei
                        FROM HUAWEI-MIB;

        huaweiTCMIB MODULE-IDENTITY
           LAST-UPDATED "202512232138Z"
            ORGANIZATION "Huawei Technologies Co.,Ltd."
            CONTACT-INFO
                "Huawei Industrial Base
                  Bantian, Longgang
                   Shenzhen 518129
                     People's Republic of China
                   Website: http://www.huawei.com
                   Email: support@huawei.com
		   "
		   DESCRIPTION
         "Huawei text conventions and common defination."
        
        REVISION "202512232138Z"
            DESCRIPTION "V60.01,
                Add: subbname8090DEVCARDNetEngine8000EM1E-B(225671), -- CARD NetEngine8000E M1E-B
            "

        REVISION "202512131419Z"
            DESCRIPTION "V60.00,
                Delete: virent8090DEVANRD001EH200(719707),       -- 2 Channel 100G/50G Base QSFP28 High Speed Interface Board.
                Modify: subbname8090DEVCR81VSUP100B1S(719702),   -- Multi-function Integrated Service Card(VSUP-100)
                Modify: subbname8090DEVCR81VSUP100B1(719703),   -- Multi-function Integrated Service Card(VSUPA-100)
                Add: subbname8090DEVCR8DVSUFWAE1(719751),  -- Versatile Service Flexible Card E(SP800A-E-G)
                
                "

        REVISION "202512091419Z"
            DESCRIPTION "V59.00,
                Modify: subbname8090DEVGPLI8KQ8CQE6(719704),       -- 8-Port 400GBase-QSFP-DD + 8-Port 100GBase-QSFP28 Integrated Line Processing Unit CM
                Modify: subbname8090DEVANKD001EV20A(719709),       -- 2 Channels 50G/1 Channel 100G Base QSFP28 High Speed Interface Board
                Modify: subbname8090DEVANKD001EV208(719710),       -- 2 Channels 50G/1 Channel 100G Base QSFP28 High Speed Interface Board
                Modify: subbname8090DEVGPI36YS10CQE2(719716),       -- 10-Port 100GBase-QSFP28 + 36-Port 25GE(SFP28)/10GE(SFP+)/GE(SFP) Integrated Line Processing Unit
                Modify: subbname8090DEVGPI40CQE3(719717),       -- 40-Port 100GBase-QSFP28 Integrated Line Processing Unit
                Modify: subbname8090DEVCR8DVSUFSPD0(719719),       -- Versatile Service Flexible Card E(SP800A-E-D)
                Modify: subbname8090DEVXHMDGSUPA0C2(719702),   -- Multi-function Integrated Service Card(VSUP-100)
                Modify: subbname8090DEVXHMDGSUPA0C3(719703),   -- Multi-function Integrated Service Card(VSUPA-100)
                Modify: subbname8090DEVXHEDMSSP8HE1(210037),   -- V8R25C10 for XHEDMSSP8HE1(SBOM) Multi-Function Service Flexible Card E(MSP800A-E)
                Modify: subbname8090DEVXHEDMSSP8HS1(210038),   -- V8R25C10 for XHEDMSSP8HS1(SBOM) Multi-Function Service Flexible Card(MSP800A-S)
                Add: subbname8090DEVANNDE4NB000(719750),  -- 4-Port 100GBase/50GBase-QSFP28 Physical Interface Card(PIC)
                " 

		REVISION "202512040000Z"
            DESCRIPTION "V58.00,
				fnameEG600-W-5G(668122),                  --EG600-W-5G FRAME
				fnameEG700-P-5G(668123),                  --EG700-P-5G FRAME
				fnameEG800-4C(668124),                    --EG800-4C FRAME
				bnameEG600-W-5G(668249),                 --EG600-W-5G Main Control Unit
				bnameEG700-P-5G(668250),                 --EG700-P-5G Main Control Unit
				bnameEG800-4C(668251),                   --EG800-4C Main Control Unit
                "

        REVISION "202512011022Z"
            DESCRIPTION "V57.07,
                Add: fnameAP361H(692547), bnameAP361H(692547),
                Add: fnameAP362H(692548), bnameAP362H(692548)
                "

        REVISION "202511291022Z"
            DESCRIPTION "V57.06,
                Add: virent8090DEVCR8DVSUFWAE0(679834),  -- V8R25C10 for CR8DVSUFWAE0(SBOM) Flexible Card Versatile Service Unit(VSUF-800A-G)
                "

        REVISION    "202511251400Z"
        DESCRIPTION "V57.05,
            fnameLingQu550LBox(687036) bnameLingQu550LBox(688727),
            fnameLingQu550BoxA(687037) bnameLingQu550BoxA(688728),
            fnameLingQu550BoxB(687038) bnameLingQu550BoxB(688729)"

        REVISION "202511241900Z"
            DESCRIPTION "V57.04,
                Add: bname and fname from S110E-24T to S110E-24P2J for oversea."

        REVISION "202511191130Z"
            DESCRIPTION "V57.03,
              Add: virent8090DEVCR8DSFU19TC0(686013),   -- V8R25C10 for CR8DSFU19TC0(SBOM) NetEngine 8000 X16 19.2Tbps Switch Fabric Unit(SFUI-19T2-A)
              Add: virent8090DEVCR8DSFU19TC1(686014),   -- V8R25C10 for CR8DSFU19TC1(SBOM) NetEngine 8000 X16 19.2Tbps Switch Fabric Unit(SFUIA-19T2-A)
              Add: virent8090DEVCR8D8SFU38A0(686015),   -- V8R25C10 for CR8D8SFU38A0(SBOM) NetEngine 8800 X16 38.4Tbps Switch Fabric Unit(SFUI-38T4-A, Enable 19.2T by default)"

        REVISION "202511181130Z"
            DESCRIPTION "V57.02,
              Add: fnameUSG6000F-S12        (16716218),      --000FF11BA
              Add: fnameUSG6000F-S13        (16716219),      --000FF11BB
              Add: fnameUSG6855G        (16716220),      --000FF1158
              Add: fnameUSG6875G        (16716221),      --000FF1159
              Add: fnameUSG6885G        (16716222),      --000FF115A
              Add: fnameEudemon1000E-W855        (16716223),      --000FF115B
              Add: fnameEudemon1000E-W875        (16716224),      --000FF115C
              Add: fnameEudemon1000E-W885        (16716225),      --000FF115D
              Add: fnameAntiDDoS1907        (16716226),      --000FF11C2

              Add: bnameSPUG-E9KE-01        (16749019),      --00FF91DB
              Add: bnameSPUG-USG-01        (16749020),      --00FF91DC
              Add: bnameSPUG-DDOS-01        (16749021),      --00FF91DD
              Add: bnameSPUG-IPS-01        (16749022),      --00FF91DE
              Add: bnameUSG6000F-S12        (16749023),      --00FF91DF
              Add: bnameUSG6000F-S13        (16749024),      --00FF91E1
              Add: bnameUSG6855G        (16749025),      --00FF91E2
              Add: bnameUSG6875G        (16749026),      --00FF91E3
              Add: bnameUSG6885G        (16749027),      --00FF91E4
              Add: bnameEudemon1000E-W855        (16749028),      --00FF91E5
              Add: bnameEudemon1000E-W875        (16749029),      --00FF91E6
              Add: bnameEudemon1000E-W885        (16749030),      --00FF91E7
              Add: bnameAntiDDoS1907        (16749031),      --00FF91E7
              Add: bnameSPUG-ADS-02-A        (16748987),      --00FF922C"
        REVISION "202511171517Z"
            DESCRIPTION "V57.01,
                Add: virent8090DEVANPM001AICQ0(215896),   -- V8R25C10 for ANPM001AICQ0(SBOM) ATN 905-L System,AC,4*GE/FE(o),4*GE/FE(e)
                Add: virent8090DEVCR8DIPU480Q0(800112),   -- V8R25C10 for CR8DIPU480Q0(SBOM) Integrated Network Processing Unit (IPUA-480), M8
                Add: virent8090DEVCR8DVSUPA0Q0(679816),    -- V8R25C10 for CR8DVSUPA0Q0(SBOM) Integrated Service Card 100(VSUP-100A)"
        
        REVISION "202511141517Z"
            DESCRIPTION "V56.03,
                Modify:  subbnameCE88SAND8YS4DQH(688168), --subbnameCE88SAND12FH(688168)"

        REVISION "202511100000Z"
            DESCRIPTION "V56.02,
                Add: fnameAirEngine5776I-X7EH(692532),      bnameAirEngine5776I-X7EH(692532),
                Add: fnameAirEngine8776I-X6ETHP-T(692534),  bnameAirEngine8776I-X6ETHP-T(692534),
                Add: fnameAirEngine6776-X7TH(692540),       bnameAirEngine6776-X7TH(692540),
                Add: fnameAirEngine8776-X5F-T(692536),      bnameAirEngine8776-X5F-T(692536),
                Add: fnameAP673H(692545),                   bnameAP673H(692545),
                "
       REVISION "202510311600Z"
          DESCRIPTION "V56.01,
              Add: subbname8090DEVCR59E8NBM(719720),       -- 8-Port 100GBase QSFP28 Fixed card
              Add: subbname8090DEVCR8DE4LBFECP(719730),       -- 4-Port 800GBase-QSFP-DD FlexE MACsec Flexible Card CM(P6T4-CM)
              Add: subbname8090DEVCR8DE4LBEECP(719731),       -- 4-Port 800GBase-QSFP-DD FlexE MACsec Flexible Card CM(P6T4-CM)
              Add: subbname8090DEVCR8DE4LBELCP(719732),       -- 4-Port 800GBase-QSFP-DD FlexE MACsec Flexible Card L CM(P6T4-L-CM)
              Add: subbname8090DEVCR8D8E4LBFC0(719733),       -- 4-Port 800GBase-QSFP-DD FlexE MACsec Flexible Card CM(P6T4-CM)
              Add: subbname8090DEVCR8D8E4LBFL0(719734),       -- 4-Port 800GBase-QSFP-DD FlexE MACsec Flexible Card L CM(P6T4-L-CM)
              Add: subbname8090DEVCR81VSUP100C1(719741),      -- CGN Versatile Service Flexible Card
              Add: subbname8090DEVCR8DE1NE2VQ0(719743),       -- 2-Port 50GBase/1-Port 100GBase-QSFP28 Physical Interface Card(PIC)
              Add: subbname8090DEVCR8D00EAGFQ0(719744),       --10-Port 100/1000Base-X-SFP  Physical Interface Card(PIC)
	          Add: subbname8090DEVCR5D00E8GEQ0(719745),       -- 8-Port 100/1000Base-RJ45 Physical Interface Card(PIC)"

        REVISION    "202510300000Z"
        DESCRIPTION "V55.05,
              Add:     subnameSPE-F08T000(536845),
              Modidy:  bname8031S5735I-S24F2T2XN-SPE-V2(538358), --S5735I-S24F2T2XN-SPE-V2 Main Control Unit"

        REVISION    "202510280000Z"
        DESCRIPTION "V55.05,
              Add:  fname8031S5735I-S24F2T2XN-SPE-V2(538186), --S5735I-S24F2T2XN-SPE-V2 FRAME
              Add:  bname8031S5735I-S24F2T2XN-SPE-V2(538338), --S5735I-S24F2T2XN-SPE-V2 Main Control Unit"

        REVISION    "202510270000Z"
        DESCRIPTION "V55.04,
              Add:  fnameAR6700V-L-16vCPU(668118),            --AR6700V-L-16vCPU FRAME
              Add:  fnameAR6700V-L-8vCPU(668119),             --AR6700V-L-8vCPU FRAME
              Add:  fnameAR6700V-L-4vCPU(668120),             --AR6700V-L-4vCPU FRAME
              Add:  fnameAR6700V-L-2vCPU(668121),             --AR6700V-L-2vCPU FRAME
              Add:  bnameAR5710-AR6700V-L-16vCPU(668245),    --AR6700V-L-16vCPU Main Control Unit
              Add:  bnameAR5710-AR6700V-L-8vCPU(668246),     --AR6700V-L-8vCPU Main Control Unit
              Add:  bnameAR5710-AR6700V-L-4vCPU(668247),     --AR6700V-L-4vCPU Main Control Unit
              Add:  bnameAR5710-AR6700V-L-2vCPU(668248),     --AR6700V-L-2vCPU Main Control Unit"

         REVISION "202510091600Z"
          DESCRIPTION "V55.03,
              Add: virent8090DEVGPLI8KQ8CQE6(719704),       -- 8-Port 400GBase-QSFP-DD + 8-Port 100GBase-QSFP28 Integrated Line Processing Unit CM
              Add: virent8090DEVANRD001EH200(719707),       -- 2 Channel 100G/50G Base QSFP28 High Speed Interface Board
              Add: virent8090DEVANKD001EV20A(719709),       -- 2 Channels 50G/1 Channel 100G Base QSFP28 High Speed Interface Board
              Add: virent8090DEVANKD001EV208(719710),       -- 2 Channels 50G/1 Channel 100G Base QSFP28 High Speed Interface Board
              Add: virent8090DEVGPI36YS10CQE2(719716),       -- 10-Port 100GBase-QSFP28 + 36-Port 25GE(SFP28)/10GE(SFP+)/GE(SFP) Integrated Line Processing Unit
              Add: virent8090DEVGPI40CQE3(719717),       -- 40-Port 100GBase-QSFP28 Integrated Line Processing Unit
              Add: virent8090DEVCR8DVSUFSPD0(719719),       -- Versatile Service Flexible Card E(SP800A-E-D)"

        REVISION "202509271600Z"
          DESCRIPTION "V55.02,
              Add: portnameDCDE01DSFP(688152),       -- The port with 100G DSFP type"

        REVISION "202509171515Z"
            DESCRIPTION "V55.01,
                Add: virent8090DEVCR8DVSUFAWD0(679824),  -- V8R25C10 for CR8DVSUFAWD0(SBOM) Flexible Card Versatile Service Unit(VSUF-800A-D)
                "

        REVISION "202509150000Z"
            DESCRIPTION "V55.00
                Modify: fnameAR5710-S52T2XE4-2025(668114),        --AR5710-S52T2XE4-2025 FRAME
                Modify: fnameAR5710-S28T2S2XE4-2025(668115),      --AR5710-S28T2S2XE4-2025 FRAME
                Modify: fnameAR5710-S52T2XE(668116),              --AR5710-S52T2XE FRAME
                Modify: fnameAR5710-S28T2S2XE(668117),            --AR5710-S28T2S2XE FRAME
                "

        REVISION "202509121419Z"
            DESCRIPTION "V54.08,
                Modify: subbname8090DEVCR8D6VSP8HS1(709779),   --Versatile Service Flexible Card(SP800-S)
                " 

        REVISION "202509120919Z"
            DESCRIPTION "V54.07,
                Add: virent8090DEVCR5DVSUIK08Z(434371),  -- V8R25C10 for CR5DVSUIK08Z(SBOM) Multi-Function Integrated Service Unit 400(VSUI-400A-S)
                Add: virent8090DEVCR5DVSUIK08A(434370),  -- V8R25C10 for CR5DVSUIK08A(SBOM) Enhanced Multi-Function Integrated Service Unit 400(VSUI-400A-E)
                "
        
        REVISION    "202509101422Z"
			DESCRIPTION "V54.06,
                Add: fnameNETENGINE-XH871(688921),        --Quidway fnameNETENGINE-XH871  FRAME for V8R25C10
                Add: fnameNETENGINE-8000-F2C-P(688961),   --Quidway fnameNETENGINE-8000-F2C-P  FRAME for V8R25C10
                Add: fnameNETENGINE-8000E-F2C-P(688962),  --Quidway fnameNETENGINE-8000E-F2C-P  FRAME for V8R25C10
                Add: virent8090DEVANHB0BKP2DF0(333021),   -- V8R25C10 for ANHB0BKP2DF0(SBOM) NetEngine XH871 Integrated Chassis Components(Port-side Intake, including 3 fan box, excluding power module)
                Add: virent8090DEVANHB0BKP2DF1(333012),   -- V8R25C10 for ANHB0BKP2DF1(SBOM) NetEngine XH871 Integrated Chassis Components(Port-side Exhaust, including 3 fan box, excluding power module)
                Add: virent8090DEVCR8B0BKP2CF5(136614),   -- V8R25C10 for CR8B0BKP2CF5(SBOM) NetEngine 8000 F2C-P Integrated Chassis Components(Port-side Intake, excluding power module)
                Add: virent8090DEVCR8B0BKP2CF6(136615),   -- V8R25C10 for CR8B0BKP2CF6(SBOM) NetEngine 8000 F2C-P Integrated Chassis Components(Port-side Exhaust, excluding power module)
                Add: virent8090DEVCR8B0BKP2CFH(136612),   -- V8R25C10 for CR8B0BKP2CFH(SBOM) NetEngine 8000E F2C-P Integrated Chassis Components(Port-side Intake, excluding power module)
                Add: virent8090DEVCR8B0BKP2CFI(136613),   -- V8R25C10 for CR8B0BKP2CFI(SBOM) NetEngine 8000E F2C-P Integrated Chassis Components(Port-side Exhaust, excluding power module)
                "
        
        REVISION "202509080000Z"
            DESCRIPTION "V54.05,
                Add: fnameAR5710-S52T2XE4-2025(668245),        --AR5710-S52T2XE4-2025 FRAME
                Add: fnameAR5710-S28T2S2XE4-2025(668246),      --AR5710-S28T2S2XE4-2025 FRAME
                Add: fnameAR5710-S52T2XE(668247),              --AR5710-S52T2XE FRAME
                Add: fnameAR5710-S28T2S2XE(668248),            --AR5710-S28T2S2XE FRAME
                Add: bnameAR5710-S52T2XE4-2025(668241),        --AR5710-S52T2XE4-2025 Main Control Unit
                Add: bnameAR5710-S28T2S2XE4-2025(668242),      --AR5710-S28T2S2XE4-2025 Main Control Unit
                Add: bnameAR5710-S52T2XE(668243),              --AR5710-S52T2XE Main Control Unit
                Add: bnameAR5710-S28T2S2XE(668244),            --AR5710-S28T2S2XE Main Control Unit"

        REVISION "202509050950Z"
            DESCRIPTION "V54.04,
                Add: bname and fname XH991032DQ.
                Add: bname and fname XH9930128DQ."
        
        REVISION "202509011700Z"
            DESCRIPTION "V54.03,
                Add: bname and fname from S110E-24T to S210-4P8UN2X.
                Add: bname from SRU750-24T24X to LPU750-20S4X.
                Add: fname of S750."

        REVISION "202509011600Z"
          DESCRIPTION "V54.02,
              Add: portnameDCDE01QSFPDD800G(688151),       -- The port with 800G QSFPDD type"

        REVISION "202509011100Z"
          DESCRIPTION "V54.01,
              Add: virent8090DEVXHMDGSUPA0C2(719702),   -- Multi-function Integrated Service Card(VSUP-100)
              Add: virent8090DEVXHMDGSUPA0C3(719703),   -- Multi-function Integrated Service Card(VSUPA-100)"
        

        REVISION    "202508290000Z"
        DESCRIPTION "V53.10,
                     Add: fnameMA5801CFL08(148547),              -- Backplane of the MA5801C-FL08.
                     Add: bnameV951NQHC(148752),                 -- 4*25GE board of MA5801C-FL08.
                     Add: bnameV951MPBA(148754),                 -- control board of MA5801C-FL08.
                     Add: bnameH901MPSK(148856),                 -- control board of MA5800-X2.
                     Add: bnameV951CIUA(148857),                 -- GPIO board of MA5801C-FL08.
                     Add: bnameH951PICC(148858),                 -- AC Power board of MA5801C-FL08.
                     Add: bnameV951FLHD(148859),                 -- 8*flex-PON board of MA5801C-FL08.
                    "

        REVISION    "202508271135Z"
            DESCRIPTION "V53.09,
                Add: virent8090DEVCR5D000CMU64(676000),    -- V8R25C10 for CR5D000CMU64(SBOM) Centralized Monitoring Module D
            "

        REVISION    "202508201041Z"
			DESCRIPTION "V53.08,
                Add: virent8090DEVCR8DSFUI4TCB(202519),   -- V8R25C10 for CR8DSFUI4TCB(SBOM) NetEngine 8100 X8 4.8Tbps Switch Fabric Unit(SFUIA-4.8T-C)
                Add: virent8090DEVCR8DSFU19TA3(686021),   -- V8R25C10 for CR8DSFU19TA3(SBOM) NetEngine 8000 X16 19.2Tbps Switch Fabric Unit(SFUI-19T2-A)
                Add: virent8090DEVCR8DSFU19TA4(686012),   -- V8R25C10 for CR8DSFU19TA4(SBOM) NetEngine 8000 X16 19.2Tbps Switch Fabric Unit(SFUIA-19T2-A)
                "
        
        REVISION    "202508151456Z"
			DESCRIPTION "V53.07,
                Add: virent8090DEVCR8DLPUF4TC0(364021),   -- V8R25C10 for CR8DLPUF4TC0(SBOM) Flexible Card Line Processing Unit(LPUF-4T8A)
                Add: virent8090DEVCR8DE8KE8NC7(109610),   -- V8R25C10 for CR8DE8KE8NC7(SBOM) 8-Port 400GBase-QSFP-DD + 8-Port 100GBase-QSFP28 Integrated Line Processing Unit CM(LPUI-4TA-CM,Enable 16*100GE by default)
                Add: virent8090DEVCR8DE8KE8EC6(514839),   -- V8R25C10 for CR8DE8KE8EC6(SBOM) 8-Port 400GBase-QSFP-DD + 8-Port 100GBase-QSFP28 Integrated Line Processing Unit E CM(LPUI-4TA-E-CM,Enable 16*100GE by default)
                Add: virent8090DEVCR8DE8KE8LC6(463240),   -- V8R25C10 for CR8DE8KE8LC6(SBOM) 8-Port 400GBase-QSFP-DD + 8-Port 100GBase-QSFP28 Integrated Line Processing Unit L CM(LPUI-4TA-L-CM,Enable 16*100GE by default)
            "
        REVISION    "202508140950Z"
        DESCRIPTION "V53.06,
                Add: bnameLingQu652V2(688724),
                Add: fnameLingQu652V2(687033),
                "

        REVISION    "202508131630Z"
			DESCRIPTION "V53.05,
                Add: virent8090DEVCR5DVSUIB070(696523),   -- V8R25C00 for CR5DVSUIB070(SBOM) Enhanced SA Service Unit 400(VSUI-400B-E)
            "
        REVISION "202508131530Z"
            DESCRIPTION "V53.04,
                Add: virent8090DEVCR5D00EDNB70(562308),    -- V8R25C10 for CR5D00EDNB70(SBOM) 16-Port 100GBase QSFP28 Integrated Line Process Unit(NE5000E LPUI-1T6-M)
                Add: virent8090DEVCR5D00EDNB71(562309),    -- V8R25C10 for CR5D00EDNB71(SBOM) 16-Port 100GBase QSFP28 Integrated Line Process Unit CM(NE5000E LPUI-1T6-M-CM)(4 ports enable)
                Modify: virent8090DEVCR5D00LRXF70(562306),   -- V8R24C00 for CR5D00LRXF70(SBOM) 72-Port 10GBase LAN/WAN-SFP+ Integrated Line Process Unit CM(NE5000E LPUI-1T6-K-CM)(12 ports enable)
                Modify: virent8090DEVCR5D00LRXF71(562307),   -- V8R24C00 for CR5D00LRXF71(SBOM) 72-Port 10GBase LAN/WAN-SFP+ Integrated Line Process Unit CM(NE5000E LPUI-1T6-L-CM)(12 ports enable)
            " 

        REVISION "202508121447Z"
            DESCRIPTION "V53.03,
                Add: subnameFAN-023A-F(536846)." 

        REVISION "202508121131Z"
            DESCRIPTION "V53.02,
                Add: portnameDCDE01SPE(688150),     -- The port with 10BASE-T1L type."

        REVISION    "202508112028Z"
             DESCRIPTION "V53.01,
                fnameCE9866U128DQ(687029),
                fnameCE9866M128DQ(687030),
                fnameCE9866T128DQ(687031),
                fnameCE8855HSAN40F(687032),
                bnameCE9866U128DQ(688716),
                bnameCE9866M128DQ(688717),
                bnameCE9866T128DQ(688718),
                bnameCE8855HSAN40F(688719)."

        REVISION    "202508111133Z"
             DESCRIPTION "V52.03,
                Modify: fname8031S210I-8T4SX(538137)
                Modify: fname8031S210I-8P4SX(538138)
                Modify: bname8031S210I-8T4SX(538309)
                Modify: bname8031S210I-8P4SX(538310)."

        REVISION    "202508111045Z"
			DESCRIPTION "V52.02,
                Add: virent8090DEVCR8DIPU480MF(800110),   -- V8R25C10 for CR8DIPU480MF(SBOM) Integrated Network Processing Unit (IPUA-480-EN), M8
                Add: virent8090DEVCR8DIPU480MI(800111),  -- V8R25C10 for CR8DIPU480MI(SBOM) Integrated Network Processing Unit (IPU-480-EN), M8
            "

        REVISION    "202508081542Z"
			DESCRIPTION "52.01,
				Add:virent8090DEVCR8D0MPU08WD(679810),  -- V8R25C10 for CR8D0MPU08WD(SBOM) NetEngine 8000E Main Processing Unit A1B-D(MPUA1B-D)
                Add:virent8090DEVCR8D0MPU16WD(679811),  -- V8R25C10 for CR8D0MPU16WD(SBOM) NetEngine 8000E Main Processing Unit A2B-D(MPUA2B-D)
                Add:virent8090DEVCR8D00EKWDD0(679812),  -- V8R25C10 for CR8D00EKWDD0(SBOM) Integrated Line Processing Unit(LPUI-4TA-D)
                Add:virent8090DEVCR8DEANEWDD0(679813),  -- V8R25C10 for CR8DEANEWDD0(SBOM) 10-Port 100GBase-QSFP28 + 36-Port 25GE(SFP28)/10GE(SFP+)/GE(SFP) Integrated Line Processing Unit(LPUI-2TA-E-D)
                Add:virent8090DEVCR8DVSUIWAE0(679814),  -- V8R25C10 for CR8DVSUIWAE0(SBOM) Dedicated Service Unit 400(VSUI-400A-E-D)
                Add:virent8090DEVCR8D00EKNBDP(679815),  -- V8R25C10 for CR8D00EKNBDP(SBOM) 40-Port 100GBase-QSFP28 Integrated Line Processing Unit(LPUI-4TA-E-D)
            "

        REVISION    "202508081026Z"
			DESCRIPTION "52.00,
				Add:virent8090DEVCR8DGSUPA0C3(679808),  -- V8R25C10 for CR8DGSUPA0C3(SBOM) Multi-function Integrated Service Card(VSUPA-100)
                Add:virent8090DEVCR8DGSUPA0C2(679809),  -- V8R25C10 for CR8DGSUPA0C2(SBOM) Multi-function Integrated Service Card(VSUP-100)
                Add:virent8090DEVCR8DIPU800MA(203628),  -- V8R25C10 for CR8DIPU800MA(SBOM) Integrated Network Processing Unit (IPUA-800-EN)
                Add:virent8090DEVCR8DIPU800MB(203629),  -- V8R25C10 for CR8DIPU800MB(SBOM) Integrated Network Processing Unit (IPU-800-EN)
                Add:virent8090DEVCR8DE8KE8NC5(109609),  -- V8R25C10 for CR8DE8KE8NC5(SBOM) 8-Port 400GBase-QSFP-DD + 8-Port 100GBase-QSFP28 Integrated Line Processing Unit CM(LPUI-4T-CM,Enable 16*100GE by default)
                Add:virent8090DEVCR8DE8KE8EC5(514838),  -- V8R25C10 for CR8DE8KE8EC5(SBOM) 8-Port 400GBase-QSFP-DD + 8-Port 100GBase-QSFP28 Integrated Line Processing Unit E CM(LPUI-4T-E-CM,Enable 16*100GE by default)
                Add:virent8090DEVCR8DE8KE8LC5(463239),  -- V8R25C10 for CR8DE8KE8LC5(SBOM) 8-Port 400GBase-QSFP-DD + 8-Port 100GBase-QSFP28 Integrated Line Processing Unit L CM(LPUI-4T-L-CM,Enable 16*100GE by default)
                Modify: fnameNETENGINE-XH16000E-M14-2AC(210015),       -- Quidway fnameNETENGINE-XH16000E-M14-2AC FRAME for V8R25C00
                Add: virent8090DEVXHEDMSUF80C1(210036),    -- V8R25C10 for XHEDMSUF80C1(SBOM) Flexible Card Multi-Function Service Unit 800(MSUF-800A)
                Add: virent8090DEVXHEDMSSP8HE1(210037),   -- V8R25C10 for XHEDMSSP8HE1(SBOM) Multi-Function Service Flexible Card E(MSP800A-E)
                Add: virent8090DEVXHEDMSSP8HS1(210038),   -- V8R25C10 for XHEDMSSP8HS1(SBOM) Multi-Function Service Flexible Card(MSP800A-S)
            "

        REVISION    "202508061437Z"
			DESCRIPTION "50.16,
				Add:subbnamePICGGXC511L1C1(720919),
				Add:subbnamePICGGXC511L1C2(720920)."

        REVISION "202508051145Z"
            DESCRIPTION "V50.02,
            The object identifier of AR502H-ELTE-V2 is added."

        REVISION    "202508051006Z"
			DESCRIPTION "V50.15,
                Add: subbname8090DEVCR8S16APTHE1(364093),            -- Threat Prortection Flexible Card S(TPP800A-S)
                Add: subbname8090DEVCR8S16APTHE2(364094),            -- Threat Prortection Flexible Card S(TPP800A-S)
                Add: subbname8090DEVCR8D000SA891(364095),            -- 8-Channel X.21/V.24 Board
                Add: subbname8090DEVCR8D000SA890(364096),            -- 8-Channel X.21/V.24 Board
            "
        
        REVISION    "202508042100Z"
			DESCRIPTION "V50.14,
                Modify: virent8090DEVGPVF1SPCATPU(161629),  -- V8R25C10 for GPVF1SPCATPU(PcbName)
            "
        REVISION    "202508011600Z"
			DESCRIPTION "V50.13,
                Add: virent8090DEVCR8S16APTHC1(161630),   -- V8R25C10 for CR8S16APTHC1(SBOM) Flexible Card Threat Prortection Unit(TPUF-800A)
                Add: virent8090DEVGPVF1SPCATPU(161629),  -- V8R25C10 for GPVF1SPCATPU(PcbName)
                Add:fnameSPNA907-S-AC(229723),            -- V8R25C10 for OptiX SPN A907-S chassis
                Add:virent8090DEVTPYM0HOSTA00(564557),    -- V8R25C10 for TPYM0HOSTA00(SBOM) SPN A907-S AC Power,with 4*GE/FE(o),4*GE/FE(e)
                Add: virent8090DEVCR8B0BKP2CFD(333220),   -- V8R25C00 for CR8B0BKP2CFD(SBOM) NetEngine 8000E F2D Programmable Computing Router Integrated Chassis Components(Port-side Intake, including 3 fan box, excluding power module)
                Add: virent8090DEVCR8B0BKP2CFE(333221),   -- V8R25C00 for CR8B0BKP2CFE(SBOM) NetEngine 8000E F2D Programmable Computing Router Integrated Chassis Components(Port-side Intake, including 3 fan box, excluding power module)
                Add: virent8090DEVCR8B0BKP2CFF(333222),   -- V8R25C00 for CR8B0BKP2CFF(SBOM) NetEngine 8000E F2D Programmable Computing Router Integrated Chassis Components(Port-side Exhaust, including 3 fan box, excluding power module)
                Add: virent8090DEVCR8B0BKP2CFG(333223),   -- V8R25C00 for CR8B0BKP2CFG(SBOM) NetEngine 8000E F2D Programmable Computing Router Integrated Chassis Components(Port-side Exhaust, including 3 fan box, excluding power module)                
            "

        REVISION    "202507282001Z"
			DESCRIPTION "V50.13,
                Add: bname from LQU521 to LQU523.
                Add: fname from LQU521 to LQU523."

        REVISION    "202507280950Z"
			DESCRIPTION "V50.11,
                Add: bname and fname from S5755-S48T8YZ-B to S6750-H48Y8C-B.
                Add: bname from LSG7M48VX1E2 to LSG7M24VX1E2.
                Add: bname from LSX7M48VX1E1 to LSX7M24VX1E1."

        REVISION    "202507251030Z"
			DESCRIPTION "V50.10,
                Add: subbname8090DEVXHMDE1KB01M0(548702),   -- 1-Port 400GBase-QSFP-DD Single-layer Physical Interface Card(PIC)
                Add: subbname8090DEVXHMDE4NB01M0(548703),   -- 4-Port 100GBase/50GBase-QSFP28 Physical Interface Card(PIC)
                Add: subbname8090DEVXHMDE4NB01M1(548704),   -- 4-Port 100GBase/50GBase-QSFP28 Physical Interface Card(PIC)(Enable 2*100GE by default)
                Add: subbname8090DEVXHMDEAGMXF00(548705),   -- 10-Port 10GE/GE LAN/WAN-SFP+ MACsec Physical Interface Card(PIC)
                Add: subbname8090DEVXHMDE4GMXF00(548706),   -- 4-Port 10GE-SFP+ FlexE MACsec Physical Interface Card(PIC)
            "

        REVISION    "202507242130Z"
			DESCRIPTION "V50.09,
                Add: virent8090DEVCR8PM1EBBSD0(120024),     --V8R25C10 CR8PM1EBBSD0(SBOM) NetEngine 8000E M1E-B, DC Power(Port Capacity 2*400/100GE+4*100/50GE+8*50/25/10/GE+16*25/10/GE,xclude auxiliary materials)
                Add: virent8090DEVCR8PM1EBBSA0(120023),     --V8R25C10 CR8PM1EBBSA0(SBOM) NetEngine 8000E M1E-B, AC Power(Port Capacity 2*400/100GE+4*100/50GE+8*50/25/10/GE+16*25/10/GE,xclude auxiliary materials)
                Add: virent8090DEVXHMD0IPU3T6A(210018),     --V8R25C00 for XHMD0IPU3T6A(SBOM) NetEngine XH16000E M14 Integrated Network Processing Unit (IPU-3T6-A)
                Add: fnameNETENGINE-8000E-M1E-B-DC(210125), -- V8R25C10 for NetEngine-8000E-M1E-B-DC chassis
                Add: fnameNETENGINE-8000E-M1E-B-AC(210127), -- V8R25C10 for NetEngine-8000E-M1E-B-AC chassis
                Add: fnameNETENGINE-XH16000E-M14-DC(210014),       --Quidway fnameNETENGINE-XH16000E-M14-DC FRAME for V8R25C00
                Add: fnameNETENGINE-XH16000E-M14-AC(210015),       --Quidway fnameNETENGINE-XH16000E-M14-AC FRAME for V8R25C00
            "
        
        REVISION "202507231800Z"
            DESCRIPTION "V50.08,
                Add: virent8090DEVCR5D00LRXF70(562306),   -- V8R25C00 for CR5D00LRXF70(SBOM) 72-Port 10GBase LAN/WAN-SFP+ Integrated Line Process Unit CM(NE5000E LPUI-1T6-K-CM)(12ports enable)
                Add: virent8090DEVCR5D00LRXF71(562307),   -- V8R25C00 for CR5D00LRXF71(SBOM) 72-Port 10GBase LAN/WAN-SFP+ Integrated Line Process Unit CM(NE5000E LPUI-1T6-L-CM)(12ports enable)
			"

        REVISION "202507230000Z"
            DESCRIPTION "V50.07,
				Add: fnameAirEngine5776E-26(692512)    bnameAirEngine5776E-26(692512)  
				Add: fnameAirEngine5773E-21(692513)    bnameAirEngine5773E-21(692513)   
                Add: fnameAirEngine5773E-23W(692518)   bnameAirEngine5773E-23W(692518)  
                Add: fnameAirEngine5773E-25HW(692519)  bnameAirEngine5773E-25HW(692519) 
                Add: fnameAirEngine5773E-23HW(692520)  bnameAirEngine5773E-23HW(692520) 
                Add: fnameAirEngine5776I-X7TH(692521)  bnameAirEngine5776I-X7TH(692521) 
                Add: fnameAirEngine7070-01-M(692524)   bnameAirEngine7070-01-M(692524)  
                Add: fnameAirEngine7070I-01-M(692525)  bnameAirEngine7070I-01-M(692525) 
                Add: fnameAirEngine7070I-01-MS(692526) bnameAirEngine7070I-01-MS(692526)
                Add: fnameAirEngine5773I-21(692527)    bnameAirEngine5773I-21(692527)   
                Add: fnameAirEngine3573I-21-M(692528)  bnameAirEngine3573I-21-M(692528) 
                Add: fnameAirEngine3576-56TP-M(692529) bnameAirEngine3576-56TP-M(692529)
			"
        REVISION    "202507221806Z"
        DESCRIPTION "V50.06,
                Add: bnameSMN(688712),
                Add: fnameSMN(687025),
                "

        REVISION    "202507221706Z"
        DESCRIPTION "V50.05,
                Add: bnameXHMM002FBXC7(716843),            -- V8R25C00 for NetEngine XH16000E M14 Fan Box(E) (XHMM002FBXC7)
            "

        REVISION    "202507211706Z"
        DESCRIPTION "V50.04,
                Add: fnamePTN6900-2-M4-DC(688839),            -- PTN6900-2-M4-DC (fnamePTN6900-2-M4-DC)
                Add: fnamePTN6900-2-M4-AC(688849),            -- PTN6900-2-M4-AC (fnamePTN6900-2-M4-AC)
            "

        REVISION    "202507181706Z"
        DESCRIPTION "V50.03,
                Add: virent8090DEVCR8B0BKP2CFJ(165980),   -- V8R25C00 for CR8B0BKP2CFJ(SBOM) NetEngine 8000 F2C Programmable Computing Router Integrated Chassis Components(Port-side Intake, excluding power module)
                Add: virent8090DEVCR8B0BKP2CFK(165981),   -- V8R25C00 for CR8B0BKP2CFK(SBOM) NetEngine 8000 F2C Programmable Computing Router Integrated Chassis Components(Port-side Exhaust, excluding power module)
            "

        REVISION    "202507181450Z"
        DESCRIPTION "V50.02,
                    Modify: virent8090DEVCR5D00EMNBC1(562149),    -- V8R24C00 for CR5D00EMNBC1(SBOM) NetEngine5000E 48-Port 100GBase QSFP28 Integrated Line Process Unit CM(NE5000E LPUI-8T-CM)(8 ports enable)
                    Modify: virent8090DEVCR5D00EEKBC1(562144),    -- V8R24C00 for CR5D00EEKBC1(SBOM) NetEngine5000E 20-Port 400GBase QSFP-DD Integrated Line Process Unit CM(NE5000E LPUI-8T-CM) (4 ports enable)
                    "

        REVISION    "202507170000Z"
        DESCRIPTION "V50.01,
                     Add: fnameRU-301(668109),                     --RU-301 FRAME
                     Add: fnameAR580(668110),                      --AR580 FRAME
                     Add: fnameAR580Plus(668111),                  --AR580Plus FRAME
                     Add: fnameAR580Pro(668112),                   --AR580Pro FRAME
                     Add: bnameRU-301(668233),                     --RU-301 Main Control Unit
                     Add: bnameSIC-2X2S-V2(668234),                --SIC-2X2S-V2 Lpu Control Unit
                     Add: bnameSIC-4CSTM1-V2(668235),              --SIC-4CSTM1-V2 Lpu Control Unit
                     Add: bnameSIC-NRGL-V2-2025(668236),           --SIC-NRGL-V2-2025 Lpu Control Unit
                     Add: bnameAR580(668237),                      --AR580 Main Control Unit
                     Add: bnameAR580Plus(668238),                  --AR580Plus Main Control Unit
                     Add: bnameAR580Pro(668239),                   --AR580Pro Main Control Unit
                    "

        REVISION    "202507161659Z"
        DESCRIPTION "V50.00,
                     Add: fnameMA5801FL16H2(148549),           -- Backplane of MA5801-FL16-H2.
                     Add: bnameV922MPCB(148863),               -- control board of MA5801-FL16-H2.
                     Add: bnameV922FLHF(148864),               -- 4*10GE board of MA5801-FL16-H2.
                     Add: bnameV922NXHC(148865),               -- 16*flex-PON board of MA5801-FL16-H2.
					 Add: bnameH902HTED(148866),               -- 8*50GPON board of MA5800.
                    "

        REVISION    "202507161555Z"
        DESCRIPTION "V49.02,
                    Add: virent8090DEVCR5D00EMNBC4(562151),    -- V8R25C10 for CR5D00EMNBC4(SBOM) 48-Port 100GBase QSFP28 Integrated Line Process Unit CM(NE5000E LPUI-8T-CM)
                    Add: virent8090DEVCR5D00EEKBC4(562152),    -- V8R25C10 for CR5D00EEKBC4(SBOM) 20-Port 400GBase QSFP-DD Integrated Line Process Unit CM(NE5000E LPUI-8T-CM)
                    "

        REVISION    "202507151700Z"
        DESCRIPTION "V49.01,
                    Add: fnameNETENGINE-8000-F2D(688950),     --Quidway fnameNETENGINE-8000-F2D  FRAME for V8R25C00
                    Add: fnameNETENGINE-8000E-F2D(688951),     --Quidway fnameNETENGINE-8000E-F2D  FRAME for V8R25C00
                    Add: virent8090DEVCR8B0BKP2DF4(333218),   -- V8R25C00 for CR8B0BKP2DF4(SBOM) NetEngine 8000E F2D Integrated Chassis Components(Port-side Intake, including 3 fan box, excluding power module)
                    Add: virent8090DEVCR8B0BKP2DF5(333219),   -- V8R25C00 for CR8B0BKP2DF5(SBOM) NetEngine 8000E F2D Integrated Chassis Components(Port-side Exhaust, including 3 fan box, excluding power module)
                    Add: virent8090DEVGPVF1SPCA(161617),   -- V8R25C00 for GPVF1SPCA(PcbName)
                    Add: virent8090DEVGPVF4SPCA(161618),   -- V8R25C00 for GPVF4SPCA(PcbName)
                    Add: virent8090DEVGPVF4SPCB(161619),   -- V8R25C00 for GPVF4SPCB(PcbName)
                    Add: virent8090DEVCR8DVSUF80C1(210046),    -- V8R25C00 for CR8DVSUF80C1(SBOM) Flexible Card Versatile Service Unit 800(VSUF-800)
                    Modify: virent8090CR8DLPUF2TL0(689211),   -- V8R25C00 for CR8DLPUF2TL0(SBOM) Flexible Card Line Processing Unit L(LPUF-2T-L)
                    Modify: virent8090CR8DLPUF2TL1(689212),   -- V8R25C00 for CR8DLPUF2TL1(SBOM) Flexible Card Line Processing Unit L(LPUF-2TA-L)
                    Modify: virent8090DEVXHXD0MPUAXC2(333212),   -- V8R25C00 for XHXD0MPUAXC2(SBOM) NetEngine XH16200 Main Processing Unit A10B(MPUA10B)
                    "
        REVISION    "202507150000Z"
        DESCRIPTION "V49.00,
                     Add: fnameCE885548CD8DQ(687024),
                     Add: bnameCE885548CD8DQ(688711),
                     Modify: fnameXH922064DQ(687003),fnameXH822064DQ(687004),
                     Modify: bnameXH922064DQ(688676),bnameXH822064DQ(688677),
                    "
        REVISION    "202507030000Z"
        DESCRIPTION "V47.05,
                     Add: fnameMA5801FL08H1(148548),           -- Backplane of MA5801-FL08-H1.
                     Add: bnameV922MPCG(148860),               -- control board of MA5801-FL08-H1.
                     Add: bnameV921FLHD(148861),               -- 4*GPON board of MA5801-FL08-H1.
                     Add: bnameV926NXHC(148862),               -- 2*XGE/GE board of MA5801-FL08-H1.
                    "

        REVISION "202506300000Z"
        DESCRIPTION "V47.04,
                Add: fnameLQ620V1(687023),     bnameLQ620V1(688710)"

        REVISION    "202506250000Z"
        DESCRIPTION "V47.03,
           Add: bnameARPDC260S12-DL(668232),             --Power Card, 260W DC"

        REVISION "202506240000Z"
            DESCRIPTION "V47.02,
                Add: fnameAirEngine8776-X7ET-T(692508),     bnameAirEngine8776-X7ET-T(692508),
                Add: fnameAirEngine8776-X7F-T(692509),      bnameAirEngine8776-X7F-T(692509),
                Add: fnameAirEngine8776-X7T-T(692510),      bnameAirEngine8776-X7T-T(692510),
                Add: fnameAirEngine8776-X6THP(692511),      bnameAirEngine8776-X6THP(692511),
                Add: fnameAirEngine6776-26HD(692514),       bnameAirEngine6776-26HD(692514),
                Add: fnameAirEngine6776-26HD-X773(692515),  bnameAirEngine6776-26HD-X773(692515),
                Add: fnameAirEngine5773-21HW(692516),       bnameAirEngine5773-21HW(692516),
                Add: fnameAP771(692517),                    bnameAP771(692517),
            "

        REVISION "202506210000Z"
            DESCRIPTION "V47.01,
                Delete: bnameV951CIUA(148857),                -- GPIO board of MA5801C-FL08.
                Delete: fnameMA5801CFL08(148547),             -- Backplane of the MA5801C-FL08.
                Delete: bnameV951FLHD(148736),                -- 8*flex-PON board of MA5801C-FL08.
                Delete: bnameV951MPBA(148752),                -- control board of MA5801C-FL08.
                Delete: bnameV951NQHC(148754),                -- 4*25GE board of MA5801C-FL08.
                Delete: bnameH951PICC(148858),                -- AC Power board of MA5801C-FL08."

        REVISION "202506191624Z"
            DESCRIPTION "V46.03,
            Change: bnameLQU520-2C(6886702)->bnameLQU520-2C(688702),
            Change: bnameLQU520-8N(6886703)->bnameLQU520-8N(688703),"
            
        REVISION "202506181059Z"
            DESCRIPTION "V46.02,
            Add : fnameLQU520-SW1(687013) - fnameLingQu651V2(687022),
            Add : bnameLQU520-SW1(688699) - bnameLingQu651V2(688709),"

        REVISION "202506172211Z"
            DESCRIPTION "V46.01,
                Add: virent8090DEVCR8B0BKP2CF9(165976),   -- V8R25C00 for CR8B0BKP2CF9(SBOM) NetEngine 8000E F2C Programmable Computing Router Integrated Chassis Components(Port-side Intake, excluding power module)
                Add: virent8090DEVCR8B0BKP2CFA(165977),   -- V8R25C00 for CR8B0BKP2CFA(SBOM) NetEngine 8000E F2C Programmable Computing Router Integrated Chassis Components(Port-side Intake, excluding power module)
                Add: virent8090DEVCR8B0BKP2CFB(165978),   -- V8R25C00 for CR8B0BKP2CFB(SBOM) NetEngine 8000E F2C Programmable Computing Router Integrated Chassis Components(Port-side Exhaust, excluding power module)
                Add: virent8090DEVCR8B0BKP2CFC(165979),   -- V8R25C00 for CR8B0BKP2CFC(SBOM) NetEngine 8000E F2C Programmable Computing Router Integrated Chassis Components(Port-side Exhaust, excluding power module)
            "

        REVISION "202506122018Z"
            DESCRIPTION "V46.00,
                Add: fnameCE6855ULLM(687007) - fnameCE986724DQ8EO(687012),
                Add: bnameXHMPUG(688690)     - bnameCE986724DQ8EO(688698),
                Change:  fnameCE986632DQ32EO(687002)->fnameCE986664DQ(687002),
                Change:  fnameXH922032DQ32EO(687003)->fnameXH922032DQ32EQ(687003),
                Change:  fnameXH822032DQ32EO(687004)->fnameXH822032DQ32EQ(687004),
                Change:  bnameCE986632DQ32EO(688675)->bnameCE986664DQ(688675),
                Change:  bnameXH922032DQ32EO(688676)->bnameXH922032DQ32EQ(688676),
                Change:  bnameXH822032DQ32EO(688677)->bnameXH822032DQ32EQ(688677),                              
            "

        REVISION "202506121653Z"
            DESCRIPTION "V45.05,
                Add: subbnameCE88SAND8YS4DQH(688168),
            "

        REVISION "202506111009Z"
            DESCRIPTION "V45.04,
                Add:  subbname8090DEVCR8D00P8CFC2(226891),            -- 8-Port STM-1c/8-Port STM-4c POS Card (PIC)(Default Enable 4*STM-1c)
                Add:  subbname8090DEVCR8D00P8CFC3(226892),            -- 8-Port STM-1c/8-Port STM-4c POS Card (PIC)(Default Enable 4*STM-1c)
                Add:  subbname8090DEVCR8D00P8CFD3(226893),            -- 8-Port STM-1c/8-Port STM-4c POS Card (PIC)(Default Enable 4*STM-1c)
                Add:  subbname8090DEVCR8D00P8CFD2(226894),            -- 8-Port STM-1c/8-Port STM-4c POS Card (PIC)(Default Enable 4*STM-1c)
                Add:  subbname8090DEVXHXD0LJXXCCP(364092),            -- 36-Port 10GBase LAN/WAN-SFP+ MACsec Flexible Card CM(P1T-CM)
            "

        REVISION "202506101456Z"
            DESCRIPTION "V45.03,
                Add:    bnameTPK1PIU(226720),                    -- ANK1PIU powerSupply
                Add:    bnameTND1PIU(226721),                    -- AND2PIU powerSupply
                "

        REVISION "202506091126Z"
            DESCRIPTION "V45.02,
                Add: subbname8090DEVXHMDE4NB00C3(709937),   -- 4-Port 100GBase/50GBase-QSFP28 Physical Interface Card CM(Enable 2*100GE by default)(PIC)
                "

        REVISION "202506062244Z"
            DESCRIPTION "V45.01,
                Add:    bnameCX6M001FBX71(561232),           -- CX67FCBA Fan
                Add:    bnameCX6M002FBX72(561233),           -- CX67FCBB Fan
                Add:    bnameCX6M002FBX73(561234),           -- CX67FCBC Fan
                Add:    bnamePAC3K2S54(675966),        -- F2AAPIU
                Add:    bnamePDC2K2S54(675967),        -- F2APIU
                Add:    bnamePDC1000S12-CB(675968),    -- F1APIU
                Add:    bnamePAC600S12-CB(675969),     -- F1AAPIU
                Add:    bnamePAC1K2S12-CB(675970),     -- F1AAPIU_B
                Add:    bnameDACS(675971),             -- DACS Module
                Add:    bnameTPJ1PIU(675972),          -- TPJ1PIU
                Add:    bnameTNF5PIU(675973),          -- TNF5PIU
                Add:    bnameANJ000APIU00(675974),     -- TNF5APIU
                Add:    bnamePAH2K4S53-CL(675975),     --V8R23C10 NetEngine-8000-M DP5U2K4APIU
                Add:    bnamePDC3KS54-CF(675976),     --V8R24C00 NetEngine-8000-F2 F2CPIU
                Add:    bnameANDD002PIU00(229035),        --Power board, 950 and 950B
                Add:    bnameTNF5APIU(229036),            --AC Power board, 980B
                "

        REVISION "202505151910Z"
            DESCRIPTION "V44.07,
                Change: bnameH901DXHD(148736),                -- 20GPON board of 21A version. 
                Change: bnameV951NQHC(148752),                -- 4*25GE board of MA5801C-FL08.
                Chabge: bnameV951MPBA(148754),                -- control board of MA5801C-FL08.
                Change: bnameH951PICC(148858),                -- AC Power board of MA5801C-FL08.
                Add:    bnameV951FLHD(148859),                -- 8*flex-PON board of MA5801C-FL08. 
                "

        REVISION "202505141720Z"
            DESCRIPTION "V44.06,
                Add: virent8090DEVCR5DSFUIT463(562305),   -- V8R25C00 for CR5DSFUIT463(SBOM) NE5000E CCC-A 8T Cluster Central Switch Fabric Unit (SFUI-8T-C)"

        REVISION "202505141530Z"
            DESCRIPTION "V44.05,
                Add: bnameAR180(668226),                      --AR180 Main Control Unit
                Add: bnameAR180PLUS(668227),                  --AR180PLUS Main Control Unit
                Add: bnameAR180PRO(668228),                   --AR180PRO Main Control Unit
                Add: bnameE3(668229),                         --E3 Main Control Unit
                Add: bnameAR280(668230),                      --AR280 Main Control Unit
                Add: bnameAR5510-S8T2S(668231),               --AR5510-S8T2S Main Control Unit
                Add: fnameAR180(668103),                       --AR180 Main Control Unit
                Add: fnameAR180PLUS(668104),                   --AR180PLUS Main Control Unit
                Add: fnameAR180PRO(668105),                    --AR180PRO Main Control Unit
                Add: fnameE3(668106),                          --E3 Main Control Unit
                Add: fnameAR280(668107),                       --AR280 Main Control Unit
                Add: fnameAR5510-S8T2S(668108),                --AR5510-S8T2S Main Control Unit
                " 
         
        REVISION "202505092050Z"
        DESCRIPTION "V44.04,
            Add: virent8090DEVCR8DVSUF8EC1(161625),   -- V8R25C00 for Flexible Card Versatile Service Unit 800(VSUF-800)
            Add: virent8090DEVCR8DVSUF8EC0(161626),   -- V8R25C00 for Flexible Card Versatile Service Unit 800(VSUF-800A)
            Add: virent8090DEVCR8DMSUFEC01(161627),   -- V8R25C00 for Flexible Card Multi-Function Service Unit 800(MSUF-800)
            Add: virent8090DEVCR8DMSUF8EC0(161628),   -- V8R25C00 for Flexible Card Multi-Function Service Unit 800(MSUF-800A)
            Add: virent8090DEVCR8DEANEWAD0(359892),   -- V8R25C00 for CR8DEANEWAD0(SBOM) 10-Port 100GBase-QSFP28 + 36-Port 25GE(SFP28)/10GE(SFP+)/GE(SFP) Integrated Line Processing Unit(LPUI-2TA-E-G)
            Add: virent8090DEVCR8D00EKWAD0(359891),   -- V8R25C00 for CR8D00EKWAD0(SBOM) Integrated Line Processing Unit(LPUI-4TA-G)
            Add: virent8090DEVCR8DVSUIWAC0(359893),   -- V8R25C00 for CR8DVSUIWAC0(SBOM) Dedicated Service Unit 400(VSUI-400A-E-G)
            Add: virent8090DEVCR8DVSUF80C2(161622),   -- V8R25C00 for CR8DVSUF80C2(SBOM) Flexible Card Versatile Service Unit 800(VSUF-800A)
            Add: virent8090DEVCR8D8VUF8HC1(161620),   -- V8R25C00 for CR8D8VUF8HC1(SBOM) Flexible Card Versatile Service Unit 800(VSUF-800)
            Add: virent8090DEVCR8DMSUF80C0(161623),   -- V8R25C00 for CR8DMSUF80C0(SBOM) Flexible Card Multi-Function Service Unit 800(MSUF-800)
            Add: virent8090DEVCR8DMSUF80C1(161624),   -- V8R25C00 for CR8DMSUF80C1(SBOM) Flexible Card Multi-Function Service Unit 800(MSUF-800A)
            Add: virent8090DEVCR8DVSUFWAC2(679807),   -- V8R25C00 for CR8DVSUFWAC2(SBOM) Flexible Card Dedicated Service Unit(VSUF-A-G)
            Add: virent8090DEVCR8D0MPUAWAG(359890),   -- V8R25C00 for CR8D0MPUAWAG(SBOM) NetEngine 8000E Main Processing Unit A1B-G(MPUA1B-G)
            Add: subbname8090DEVCR8DVSSP8HE1(709787),   --Versatile Service Flexible Card E(SP800-E)
            Add: subbname8090DEVCR8DVSSP8HS1(709783),   --Versatile Service Flexible Card(SP800-S)
            Add: subbname8090DEVCR8DVSSP8HE2(709788),   --Versatile Service Flexible Card E(SP800A-E)
            Add: subbname8090DEVCR8DVSSP8HS2(709784),   --Versatile Service Flexible Card(SP800A-S)
            Add: subbname8090DEVCR8DMSSP8HE0(709789),   --Multi-Function Service Flexible Card E(MSP800-E)
            Add: subbname8090DEVCR8DMSSP8HS0(709785),   --Multi-Function Service Flexible Card(MSP800-S)
            Add: subbname8090DEVCR8DMSSP8HE1(709790),   --Multi-Function Service Flexible Card E(MSP800A-E)
            Add: subbname8090DEVCR8DMSSP8HS1(709786),   --Multi-Function Service Flexible Card(MSP800A-S)
            Add: subbname8090DEVCR8D8VSP8HE1(709792),   --Versatile Service Flexible Card E(SP800-E)
            Add: subbname8090DEVCR8D8VSP8HS1(709778),   --Versatile Service Flexible Card(SP800-S)
            Add: subbname8090DEVCR8D6VSP8HE1(709791),   --Versatile Service Flexible Card E(SP800-E)
            Add: subbname8090DEVCR8D6VSP8HS1(709779),   --Versatile Service Flexible Card(SP800-S)"

        REVISION "202505091500Z"
        DESCRIPTION "V44.03,
            Add: subbname8090DEVCR8DEANBFECT(709926),            -- 10-Port 100GBase-QSFP28 FlexE Flexible Card CM(P2T-L-CM)
            Add: subbname8090DEVCR8D8EKE2NCQ(709927),            -- 2-Port 400GBase-QSFP-DD FlexE + 2-Port 100GBase-QSFP28 Flexible Card CM(P2T-L-CM)
            Add: subbname8090DEVCR8DEANBFECS(709928),            -- 10-Port 100GBase-QSFP28 FlexE Flexible Card CM(P2T-CM)
            Add: subbname8090DEVCR8D8EKE2NCP(709929),            -- 2-Port 400GBase-QSFP-DD FlexE + 2-Port 100GBase-QSFP28 Flexible Card CM(P2T-CM)
            Add: subbname8090DEVCR8DVSSP8EE1(709940),            -- Versatile Service Flexible Card E(SP800-E)
            Add: subbname8090DEVCR8DVSSP8EE0(709941),            -- Versatile Service Flexible Card E(SP800A-E)
            Add: subbname8090DEVCR8DVSSP8ES1(709942),            -- Versatile Service Flexible Card(SP800-S)
            Add: subbname8090DEVCR8DVSSP8ES0(709943),            -- Versatile Service Flexible Card(SP800A-S)
            Add: subbname8090DEVCR8DMSSP8EE0(709944),            -- Multi-Function Service Flexible Card E(MSP800-E)
            Add: subbname8090DEVCR8DMSSP8EE1(709945),            -- Multi-Function Service Flexible Card E(MSP800A-E)
            Add: subbname8090DEVCR8DMSSP8ES0(709946),            -- Multi-Function Service Flexible Card(MSP800-S)
            Add: subbname8090DEVCR8DMSSP8ES1(709947),            -- Multi-Function Service Flexible Card(MSP800A-S)"

        REVISION "202505072000Z"
        DESCRIPTION "V44.02,
            Add: subbname8090DEVCARD2NetEngineA817(333109) --CARD NetEngine A817,4E1"

        REVISION "202504302000Z"
            DESCRIPTION "V44.01,
                Add: bnameLSG7SRUDX201(713527)"

        REVISION "202504272000Z"
            DESCRIPTION "V44.00,
                Modified: virent8090DEVCR8DSFUIK0C2(333205),   -- V8R25C00 for CR8DSFUIK0C2(SBOM) NetEngine 8000 F 1T6 Switch Routing Unit(SRU-1T6-A)"

        REVISION "202504251200Z"
            DESCRIPTION "V42.07,
            Add: virent8090DEVCR5D00TPU060(562304),    -- V8R25C00 for CR5D00TPU060(SBOM) NetEngine5000E Threat Protection Unit(NE5000E TPUI-A)"

        REVISION    "202504231700Z"
            DESCRIPTION "V42.06,
                Add:    bnameH951PICB(148858),                -- AC Power board of MA5801C-FL08.
                Delete: bnameH951PICC(148858),                -- AC Power board of MA5801C-FL08."

        REVISION    "202504222340Z"
            DESCRIPTION "V42.05,
                Add: bnameXHMM002FBXC1(716841),
                Add: bnameXHMM002FBXC2(716842),"

        REVISION    "202504222330Z"
            DESCRIPTION "V42.04,
                Add: bnameSPUD-USG         (16749007),      --00FF91CF
                Add: subnameSPCD-USG-04       (16748618),    --00FF904A"
        REVISION    "202504222230Z"
            DESCRIPTION "V42.03,
                Add: subbname8090DEVXHMDE1KB00C0(709930),   -- 1-Port 400GBase-QSFP-DD Single-layer Physical Interface Card(PIC)
                Add: subbname8090DEVXHMDE1KB00C1(709931),   -- 1-Port 400GBase-QSFP-DD Single-layer Physical Interface Card CM(Enable 1*100G)(PIC)
                Add: subbname8090DEVXHMDE1KB00C2(709932),   -- 1-Port 400GBase-QSFP-DD Single-layer Physical Interface Card(PIC)
                Add: subbname8090DEVXHMDE1KB00C3(709933),   -- 1-Port 400GBase-QSFP-DD Single-layer Physical Interface Card CM(Enable 1*100G)(PIC)
                Add: subbname8090DEVXHMDE4NB00C0(709934),   -- 4-Port 100GBase/50GBase-QSFP28 Physical Interface Card(PIC)
                Add: subbname8090DEVXHMDE4NB00C1(709935),   -- 4-Port 100GBase/50GBase-QSFP28 Physical Interface Card CM(Enable 2*100GE by default)(PIC)
                Add: subbname8090DEVXHMDE4NB00C2(709936),   -- 4-Port 100GBase/50GBase-QSFP28 Physical Interface Card(PIC)
                Add: subbname8090DEVXHMDLAXF00C0(709938),   -- 4-Port 100GBase/50GBase-QSFP28 Physical Interface Card CM(Enable 2*100GE by default)(PIC)
                Add: subbname8090DEVXHMDLAXF00C1(709939),   -- 1-Port 400GBase-QSFP-DD Single-layer Physical Interface Card(PIC)
                "
        REVISION    "202504172230Z"
            DESCRIPTION "V42.02,
                Add: fnameNETENGINE-XH16100-M14-DC(690000),       --Quidway fnameNETENGINE-XH16100-M14-DC FRAME for V8R25C00
                Add: fnameNETENGINE-XH16100-M14-2AC(690001),       --Quidway fnameNETENGINE-XH16100-M14-2AC FRAME for V8R25C00
                Add: fnameNETENGINE-XH16200-M14-DC(690002),       --Quidway fnameNETENGINE-XH16200-M14-DC FRAME for V8R25C00
                Add: fnameNETENGINE-XH16200-M14-2AC(690003),       --Quidway fnameNETENGINE-XH16200-M14-2AC FRAME for V8R25C00
                Add: virent8090DEVXHMD0IPU3TC1(900004),   -- V8R25C00 for XHMD0IPU3TC1(SBOM) Integrated Network Processing Unit(IPUA-3T6-A)
                Add: virent8090DEVXHMD0IPU3TC2(900005),   -- V8R25C00 for XHMD0IPU3TC2(SBOM) Integrated Network Processing Unit(IPUA-3T6-A)"
    
        REVISION    "202504162230Z"
            DESCRIPTION "V42.01,
                Add: bnamePIU550W(716840),   -- V8R25C00 for PIU550W."

        REVISION    "202504111700Z"
            DESCRIPTION "V41.11,
                Add: bnameV951CIUA(148857),                -- GPIO board of MA5801C-FL08.
                Add: fnameMA5801CFL08(148547),             -- Backplane of the MA5801C-FL08.
                Add: bnameV951FLHD(148736),                -- 8*flex-PON board of MA5801C-FL08.
                Add: bnameV951MPBA(148752),                -- control board of MA5801C-FL08.
                Add: bnameV951NXHC(148754),                -- 4*25GE board of MA5801C-FL08.
                Add: bnameH951PICC(148858),                -- AC Power board of MA5801C-FL08."

        REVISION    "202504111200Z"
            DESCRIPTION "V41.10,
                Add: virent8090DEVCR8B0BKP2DF2(333206),   -- V8R25C00 for CR8B0BKP2DF2(SBOM) NetEngine 8000 F2D Integrated Chassis Components(Port-side Intake, including 3 fan box, excluding power module)
                Add: virent8090DEVCR8B0BKP2DF3(333207),   -- V8R25C00 for CR8B0BKP2DF3(SBOM) NetEngine 8000 F2D Integrated Chassis Components(Port-side Exhaust, including 3 fan box, excluding power module)
                Add: virent8090DEVCR8B0BKP2DF0(333208),   -- V8R25C00 for CR8B0BKP2DF0(SBOM) NetEngine 8000E F2D Integrated Chassis Components(Port-side Intake, including 3 fan box, excluding power module)
                Add: virent8090DEVCR8B0BKP2DF1(333209),   -- V8R25C00 for CR8B0BKP2DF1(SBOM) NetEngine 8000E F2D Integrated Chassis Components(Port-side Exhaust, including 3 fan box, excluding power module)
                Add: virent8090DEVXHXDLPUF4TC3(333210),   -- V8R25C00 for XHXDLPUF4TC3(SBOM) Flexible Card Line Processing Unit(LPUF-4T8A)
                Add: virent8090DEVXHXD0MPUAXC1(333211),   -- V8R25C00 for XHXD0MPUAXC1(SBOM) NetEngine XH16100 Main Processing Unit A10B(MPUA10B)
                Add: virent8090DEVXHXD0MPUAXC2(333212),   -- V8R25C00 for XHXD0MPUAXC2(SBOM) NetEngine XH16200 Main Processing Unit A12A(MPUA10B)
                Add: virent8090DEVXHXDSFUI9TC1(333213),   -- V8R25C00 for XHXDSFUI9TC1(SBOM) NetEngine XH16100 X8 9.6Tbps Switch Fabric Unit(SFUIA-9T6-B)
                Add: virent8090DEVXHXDSFUI9TC2(333214),   -- V8R25C00 for XHXDSFUI9TC2(SBOM) NetEngine XH16200 X8 9.6Tbps Switch Fabric Unit(SFUIA-9T6-B)
                Add: virent8090DEVXHXDLPUF4TC1(333215),   -- V8R25C00 for XHXDLPUF4TC1(SBOM) Flexible Card Line Processing Unit(LPUF-4T8A)
                Add: virent8090DEVXHXDLPUF2TC2(333216),   -- V8R25C00 for XHXDLPUF2TC2(SBOM) Flexible Card Line Processing Unit(LPUF-2T4A)
                Add: virent8090DEVXHXDLPUF2TC1(333217),   -- V8R25C00 for XHXDLPUF2TC1(SBOM) Flexible Card Line Processing Unit(LPUF-2T4A)
                Add: fnameNETENGINE-XH16100-X8-DC(688720),   -- Quidway fnameNETENGINE-XH16100-X8-DC FRAME for V8R25C00
                Add: fnameNETENGINE-XH16100-X8-HVDC(688721), -- Quidway fnameNETENGINE-XH16100-X8-HVDC FRAME for V8R25C00
                Add: fnameNETENGINE-XH16200-X8-DC(688722),   -- Quidway fnameNETENGINE-XH16200-X8-DC FRAME for V8R25C00
                Add: fnameNETENGINE-XH16200-X8-HVDC(688723), -- Quidway fnameNETENGINE-XH16200-X8-HVDC FRAME for V8R25C00
            "
        REVISION    "202504081915Z"
            DESCRIPTION "V41.09,
                Add: subbname8090DEVXHXDE3KBFEC1(709920),            -- 3-Port 400GBase-QSFP-DD FlexE MACsec Flexible Card CM(P2T4-CM,400GE Port Enabled with 100GE by default)
                Add: subbname8090DEVXHXDEBNBFEC1(709921),            -- 12-Port 100GBase-QSFP28 FlexE MACsec Flexible Card CM(P2T4-CM)
                Add: subbname8090DEVXHXDE6KBFEC1(709922),            -- 6-Port 400GBase-QSFP-DD FlexE MACsec Flexible Card CM(P4T8-CM,400GE Port Enabled with 100GE by default)
                Add: subbname8090DEVXHXDEFNBFEC1(709923),            -- 24-Port 100GBase-QSFP28 FlexE MACsec Flexible Card CM(P4T8-CM)
                Add: subbname8090DEVXHXDE3KBFEC2(709924),            -- 3-Port 400GBase-QSFP-DD FlexE MACsec Flexible Card CM(P2T4-CM,400GE Port Enabled with 100GE by default)
                Add: subbname8090DEVXHXDEBNBFEC2(709925),            -- 12-Port 100GBase-QSFP28 FlexE MACsec Flexible Card CM(P2T4-CM)"
         REVISION    "202504071915Z"
            DESCRIPTION "V41.08,
                Add: fnameUSG6000F-E06-D          (16716205),    --00FF11AD
                Add: fnameUSG6000F-E12-D          (16716206),    --00FF11AE
                Add: fnameUSG6000F-E06-D          (16716207),    --00FF11AF
                Add: fnameUSG6000F-S112        (16716208),      --00FF11B0
                Add: fnameUSG6000F-S330        (16716209),      --00FF11B1
                Add: fnameUSG6000F-S500        (16716210),      --00FF11B2
                Add: fnameUSG6000F-S55L        (16716211),      --00FF11B3
                Add: fnameUSG6000F-S530        (16716212),      --00FF11B4
                Add: fnameUSG6000F-S600        (16716213),      --00FF11B5
                Add: bnameMPUA-USG6000F-E06-D     (16749003),      --00FF91CB
                Add: bnameMPUA-USG6000F-E12-D     (16749004),      --00FF91CC
                Add: bnameMPUA-USG6000F-E06-D     (16749005),      --00FF91CD
                Add: bnameMPUA-USG6000F-S112        (16749006),      --00FF91CE
                Add: bnameSPUD-E9KE        (16749008),      --00FF91D0
                Add: bnameSPUD-ADS        (16749009),      --00FF91D1
                Add: bnameSPUD-IPS        (16749010),      --00FF91D2
                Add: bnameMPUA-USG6000F-S330(16749011),    --00FF91D3
                Add: bnameMPUA-USG6000F-S500(16749012),    --00FF91D4
                Add: bnameMPUA-USG6000F-S55L(16749013),    --00FF91D5
                Add: bnameLPUG-E-4CQ24XS(16749014),    --00FF91D7
                Add: bnameLPUG-U-4CQ24XS(16749015),    --00FF91D8
                Add: bnameLPUG-I-4CQ24XS(16749016),    --00FF91D9
                Add: bnameMPUA-USG6000F-S530        (16749017),      --00FF91D9
                Add: bnameMPUA-USG6000F-S600        (16749018),      --00FF91DA
                Add: subnameSPCD-E9KE-02       (16748612),    --00FF9044
                Add: subnameSPCD-ADS-02       (16748613),    --00FF9045
                Add: subnameSPCD-IPS-02       (16748614),    --00FF9046
                Add: subnameSPCD-USG-TP-02       (16748615),    --00FF9047
                Add: subnameSPCD-E9KE-TP-02       (16748616),    --00FF9048
                Add: subnameSPCD-E9KE-04       (16748619),    --00FF904B
                Add: subnameSPCD-ADS-04       (16748620),    --00FF904C
                Add: subnameSPCD-IPS-04       (16748621),    --00FF904D
                Add: subnameSPCD-USG-TP-04       (16748622),    --00FF904E
                Add: subnameSPCD-E9KE-TP-04       (16748623),    --00FF904F
                Add: subnameSPCD-USG-02       (16748625),    --00FF9051"
        REVISION    "202503192007Z"
            DESCRIPTION "V41.07,
                Add: virent8090DEVCR5DVSUIK082(210040),    -- V8R25C00 for CR5DVSUIK082(SBOM) Integrated Service Unit 400(VSUI-400-E)
                Add: virent8090DEVCR5DVSUIK081(210041),    -- V8R25C00 for CR5DVSUIK081(SBOM) Integrated Service Unit 400(VSUI-400-E)
                Add: virent8090DEVME0DVSUIK07M(210042),    -- V8R25C00 for ME0DVSUIK07M(SBOM) Integrated Service Unit 400(VSUI-400A-E)
                Add: virent8090DEVME0DVSUIK07L(210045),    -- V8R25C00 for ME0DVSUIK07L(SBOM) Integrated Service Unit 400(VSUI-400-E)"

        REVISION    "202503171748Z"
            DESCRIPTION "V41.06,
                Add: subbname8090DEVGPR32CQ56YS(709912),             -- 32-Port 400GBase-QSFPDD + 56-Port 100GBase-QSFP28
                Add: subbname8090DEVCR8DEANBFECQ(709913),            -- 10-Port 100GBase-QSFP28 FlexE Flexible Card CM(P2T-CM)
                Add: subbname8090DEVCR8D8ANBFECQ(709914),            -- 10-Port 100GBase-QSFP28 FlexE MACsec Flexible Card CM(P2T-CM)
                Add: subbname8090DEVCR8D8ANBFELQ(709915),            -- 10-Port 100GBase-QSFP28 FlexE MACsec Flexible Card L CM(P2T-L-CM)"

        REVISION    "202503171000Z"
            DESCRIPTION "V41.05,
                Add: subbname8090DEVCARDATN910E-A(225659) --CARD ATN910E-A"

        REVISION    "202503152230Z"
            DESCRIPTION "V41.04,
                Add: bnamePDC2K2S12-PB(716834),   -- V8R25C00 for PDC2K2S12-PB
                Add: bnamePDC2K2S12-PF(716835),   -- V8R25C00 for PDC2K2S12-PF
                Add: bnamePAC2KS12-PB(716836),    -- V8R25C00 for PAC2KS12-PB
                Add: bnamePAC1K8S12-PF(716837),   -- V8R25C00 for PAC1K8S12-PF
                Add: bnameFAN-150C-B(716838),     -- V8R25C00 for FAN-150C-B
                Add: bnameFAN-150C-F(716839),     -- V8R25C00 for FAN-150C-F"

        REVISION    "202503152130Z"
            DESCRIPTION "V41.03,
                Add: virent8090CR8DLPUF2TL0(689211),   -- V8R25C00 for CR8DLPUF2TL0(SBOM) Flexible Card Line Processing Unit(LPUF-2T-L)
                Add: virent8090CR8DLPUF2TL1(689212),   -- V8R25C00 for CR8DLPUF2TL1(SBOM) Flexible Card Line Processing Unit(LPUF-2TA-L)
                Add: virent8090CR8DLPUF2TB0(689213),   -- V8R25C00 for CR8DLPUF2TB0(SBOM) Flexible Card Line Processing Unit(LPUF-2T)
                Add: virent8090CR8DLPUF2TB1(689214),   -- V8R25C00 for CR8DLPUF2TB1(SBOM) Flexible Card Line Processing Unit(LPUF-2TA)"
        
        REVISION    "202503112130Z"
            DESCRIPTION "V41.02,
                Add: subbnameTPN2EX10P(229285),        --10 Channels 10 GE Optical Interface Board(physical board, with 8 port enabled by default) (SFP+)
                Add: subbnameTPT1FV2P(229287),         --2 Channels 50 GE FlexE Optical Interface Board(physical board, with 1 port enabled by default)"

        REVISION    "202503082050Z"
            DESCRIPTION "V40.11,
                Add: subbname8090DEVXHXDEBNBFEC0(709909),            -- 12-Port 100GBase-QSFP28 FlexE MACsec Flexible Card CM(P2T4-CM)
                Add: subbname8090DEVXHXDE6KBFEC3(709910),            -- 3-Port 400GBase-QSFP-DD FlexE MACsec Flexible Card CM(P2T4-CM,400GE Port Enabled with 100GE by default)
                Add: subbname8090DEVXHXDE6KBFEC3(709911),            -- 6-Port 400GBase-QSFP-DD FlexE MACsec Flexible Card CM(P4T8-CM,400GE Port Enabled with 100GE by default)
                Add: bnameGXCOMMPOWER(564556),    -- GXCOMMPOWER"

        REVISION    "202503062050Z"
            DESCRIPTION "V40.01,
                Modified: virentCX61DEVCX6D0SRUA510(537017),     -- Two piece 5802, 200G SFU, used with X8 SRUA200A MPU
                Modified: virentCX62DEVCX6D0MPUB411(538003),       -- for CX600-DO Main Processing Unit B4(Including 1*2G Memory and 1*1G CF Card)
                Modified: virent8090DEVCR5D0SRUA570(561170),     -- Two piece 5802, 200G SFU, used with X8 SRUA200A MPU
                Modified: virentME60DEVME0D0SRUA570(159798),   -- V6R3C05 for ME0D0SRUA570(SBOM),Switch and Route Processing Unit A5(Including 1*2G Memory and 1*1G CF Card)
                Modified: virentPTN6900DEVTNRD0SRUA570(229400),   --Switch and Route Processing Unit A6(Including 1*2G Memory and 2*1G CF Card)
                Delete: bnameTPND02CXPA00(229598),               --OptiX PTN 980,TPN2CXPA0,System Control,Cross-connect and Multi-protocol Process Unit"

        REVISION    "202503032050Z"
            DESCRIPTION "V39.10,
                Add: bnameH901MPLHE(148854),         --  control board of EA5800"

        REVISION "202502272050Z"
      		DESCRIPTION "V39.09,
        		Add: fnameATN910D-C-AC(229685),  -- ATN910DCCHASSIS, AC Power
                Add: fnameATN910D-C-DC(229686),  -- ATN910DCCHASSIS, DC Power
                Add: fname910E-F(225430), -- 910E-F
                Add: virent8090CR5D00ICUC52(567019), -- Cluster Internal Communication Unit C
                Add: virent8090TPT2CXPA(689210),   -- OptiX PTN 980B,TPT2CXPA,System Control,Cross-connect and Multi-protocol Process Unit"

        REVISION "202502252050Z"
      		DESCRIPTION "V39.08,
        		Add: fnameATN910E-A-DC(210012),          -- V8R25C00 for ATN910E-A DC chassis
                Add: virent8090DEVANEMHSTA0100(120021),  -- V8R25C00 for ANEMHSTA0100(SBOM) ATN 910E, DC Power, Port Capacity 2*400GE/100GE+4*100GE/50GE+8*50GE/25GE/10GE/GE+16*25GE/10GE/GE, all the GE ports is enabled"
        
        REVISION "202502211600Z"
      		DESCRIPTION "V39.07,
        		Add: subbname8090DEVCR5D00C4CFC2(225806), -- 4-Port Channelized STM-1c POS-SFP Physical Interface Card(PIC)
                Add: subbname8090DEVCR8DC4CF00F0(225807), -- 4-Port Channelized STM-1c POS-SFP Flexible Interface Card(PIC)"

        REVISION "202502210000Z"
      		DESCRIPTION "V39.06,
        		Add: bnameCEX7SFU04GM(688683),
                Add: bnameCEX7SFU08GM(688684),
                Add: bnameCEX7SFU16GM(688685),
                Add: bnameCEX8SFU08GM(688686),
                Add: bnameCEX8SFU16GM(688687),
                Add: bnameCEX9SFU08GM(688688),
                Add: bnameCEX9SFU16GM(688689)."

        REVISION "202502200000Z"
      		DESCRIPTION "V39.05,
        		S5755-S24UN8YZ to S5751-L24P2PN2X-RUA are added.
        		LSX7SFUAX500 to LSX7C16BX1E0 are added."

        REVISION "202502192132Z"
          DESCRIPTION "V39.04,
              Add: subbname8090DEVCR8DEE5NBCL0(709900),            -- 5-Port 100GBase-QSFP28 FlexE MACsec Flexible Card L CM(P1T-L-CM)
              Add: subbname8090DEVCR8DEE5NBCC0(709901),            -- 5-Port 100GBase-QSFP28 FlexE MACsec Flexible Card CM(P1T-CM)
              Add: subbname8090DEVCR8DEE5NBCE0(709902),            -- 5-Port 100GBase-QSFP28 FlexE MACsec Flexible Card E CM(P1T-E-CM)
              Add: subbname8090DEVCR8DELJXXCL0(709903),            -- 36-Port 10GBase LAN/WAN-SFP+ MACsec Flexible Card L CM(P1T-L-CM)
              Add: subbname8090DEVCR8DELJXXCC0(709904),            -- 36-Port 10GBase LAN/WAN-SFP+ MACsec Flexible Card CM(P1T-CM)
              Add: subbname8090DEVCR8DELJXXCE0(709905),            -- 36-Port 10GBase LAN/WAN-SFP+ MACsec Flexible Card E CM(P1T-E-CM)
              Add: subbname8090DEVCR8DEE1K1NLP(709906),            -- 1-Port 400GBase-QSFP-DD FlexE + 1-Port 100GBase-QSFP28 Flexible Card L CM(P1T-L-CM,400GE Port Enabled with 100GE by default)
              Add: subbname8090DEVCR8DEE1K1NCP(709907),            -- 1-Port 400GBase-QSFP-DD FlexE + 1-Port 100GBase-QSFP28 Flexible Card CM(P1T-CM,400GE Port Enabled with 100GE by default)
              Add: subbname8090DEVCR8DEE1K1NEP(709908),            -- 1-Port 400GBase-QSFP-DD FlexE + 1-Port 100GBase-QSFP28 Flexible Card E CM(P1T-E-CM,400GE Port Enabled with 100GE by default)"

        REVISION "202502171918Z"
          DESCRIPTION "V39.03,
              Add: virent8090DEVCR8DELPF1TL0(313612),   -- V8R24C10 for CR8DELPF1TL0(SBOM) Flexible Card Line Processing Unit L(LPUF-1T-L)
              Add: virent8090DEVCR8DELPF1TC0(313613),   -- V8R24C10 for CR8DELPF1TC0(SBOM) Flexible Card Line Processing Unit (LPUF-1T)
              Add: virent8090DEVCR8DELPF1TE0(313614),   -- V8R24C10 for CR8DELPF1TE0(SBOM) Flexible Card Line Processing Unit E(LPUF-1T-E)
              Add: virent8090DEVWDNDNNSRCPA1(313615),   -- V8R25C00 for WDNDNNSRCPA1(SBOM) S-Router Control Process Unit
              Add: fnameNETENGINE-8000-NTN(685653),      --NETENGINE-8000-NTN"

        REVISION "202502131918Z"
          DESCRIPTION "V39.02,
              Add: subbname8090DEVIG2D84KBFECP(709896),   -- 4-Port 400GBase-QSFP-DD FlexE MACsec Flexible Card(P3T2)
              Add: subbname8090DEVIG2D8DNBFECQ(709897),   -- 16-Port 100GBase-QSFP28 FlexE MACsec Flexible Card(P3T2)"

        REVISION "202502131500Z"
          DESCRIPTION "V39.01,
              Add: virent8090DEVCR8DSFUIK0E1(333203),   -- V8R25C00 for CR8DSFUIK0E1(SBOM) NetEngine 8000E F 1T6 Switch Routing Unit(SRUA-1T6-A)
              Add: virent8090DEVCR8DSFUIK0E2(333204),   -- V8R25C00 for CR8DSFUIK0E2(SBOM) NetEngine 8000E F 1T6 Switch Routing Unit(SRU-1T6-A)
              Add: virent8090DEVCR8DSFUIK0C2(333205),   -- V8R25C00 for CR8DSFUIK0C2(SBOM) NetEngine 8000 F 1T6 Switch Routing Unit(SRU-1T6-A)"

        REVISION "202502102221Z"
        DESCRIPTION "V39.00,
            Add: bnameH901FLRF(148851),                -- 16*XGS combo board of MA5800.
            Add: subbnameH901CPCJ(148528),             -- Clock subboard of MA5800-X2 H901MPSJ
            Add: bnameH901MPSJ(148804),                -- control board of MA5800-X2.
            Add: bnameH901FLBF(148852),                -- 16*XGS combo board of MA5800.
            Add: bnameH901HEED(148853),                -- 50G XPON board of MA5800."
        
        REVISION "202502081714Z"
        DESCRIPTION "V38.03,
            Add: subbname8090DEVCARDNetEngineA817(333110),     --CARD NetEngine A817"

        REVISION "202502081014Z"
        DESCRIPTION "V36.14,
            Add: subbnameTPN2MD1(229286),          --32 Channels E1 Interface Board
            Add: subbname8090DEVCR8D6E1K1NCP(709887),            -- 1-Port 400GBase-QSFP-DD FlexE + 1-Port 100GBase-QSFP28 Flexible Card CM(P1T-CM,400GE Port Enabled with 100GE by default)
            Add: subbname8090DEVCR8D6E1K1NEP(709888),            -- 1-Port 400GBase-QSFP-DD + 1-Port 100GBase-QSFP28 FlexE MACsec Flexible Card E CM(P1T-E-CM,400GE Port Enabled with 100GE by default)
            Add: subbname8090DEVCR8D6LJXXCC0(709889),            -- 36-Port 10GBase LAN/WAN-SFP+ MACsec Flexible Card CM(P1T-CM)
            Add: subbname8090DEVCR8D6LJXXCE0(709890),            -- 36-Port 10GBase LAN/WAN-SFP+ MACsec Flexible Card E CM(P1T-E-CM)
            Add: subbname8090DEVCR8D6MUF00X1(709891),            -- 16-Port 10GE(SFP+)/GE(SFP) + 16-Port 155M/16-Port 622M/8-Port 2.5G/2-Port 10GPOS Flexible Card (P1T-CM)
            Add: subbname8090DEVCR8D62KE2NC0(709892),            -- 2-Port 400GBase-QSFP-DD FlexE + 2-Port 100GBase-QSFP28 Flexible Card CM(P2T-CM)
            Add: subbname8090DEVCR8D6E5NBCC0(709893),            -- 5-Port 100GBase-QSFP28 FlexE MACsec Flexible Card CM(P1T-CM)
            Add: subbname8090DEVCR8D6E5NBCE0(709894),            -- 5-Port 100GBase-QSFP28 FlexE MACsec Flexible Card E CM(P1T-E-CM)
            Add: subbname8090DEVCR8D6ANBFECQ(709895),            -- 10-Port 100GBase-QSFP28 FlexE MACsec Flexible Card CM(P2T-CM)"

        REVISION "202502071140Z"
        DESCRIPTION "V14.34,
           Add: fnameNETENGINE-A817-AC(210008),      -- V8R25C00 for NetEngine-A817-AC chassis
           Add: virent8090DEVCP8PHST10A20(210009),   -- V8R25C00 for CP8PHST10A20(SBOM) NetEngine A817 AC System (4*GE/FE(o)+4*GE/FE(e)+4*E1)
           "
        
        REVISION "202501261920Z"
            DESCRIPTION "V36.13,
                Modify: virent8090DEVCR8DEANEWAD0(539207),   -- V8R25C00 for CR8DEANEWAD0 10-Port 100GBase-QSFP28 + 36-Port 25GE(SFP28)/10GE(SFP+)/GE(SFP) Integrated Line Processing Unit CM(LPUI-2T-CM) ->
			virent8090DEVGPLI36YS10CQE3(539207),   -- V8R25C00 for CR8DEANEWAD0 10-Port 100GBase-QSFP28 + 36-Port 10GE(SFP+)/GE(SFP)."


        
        REVISION "202501241202Z"
            DESCRIPTION "V36.12,
                Modify: fnameCE986666DQ(687002)->fnameCE986632DQ32EO(687002),
                Modify: fnameXH922066DQ(687003)->fnameXH922032DQ32EO(687003),
                Modify: fnameXH822066DQ(687004)->fnameXH822032DQ32EO(687004),
                Modify: bnameCE986666DQ(688675)->bnameCE986632DQ32EO(688675),
                Modify: bnameXH922066DQ(688676)->bnameXH922032DQ32EO(688676),
                Modify: bnameXH822066DQ(688677)->bnameXH822032DQ32EO(688677),
                " 

        REVISION "202501231647Z"
            DESCRIPTION "V36.11,
                Add: fnameAR5710-H4T4N2X(668095),              --AR5710-H4T4N2X Main Control Unit
                Add: fnameAR5710-H4T4N2X-LTE4EA(668096),       --AR5710-H4T4N2X-LTE4EA Main Control Unit
                Add: fnameAR5710-H2T4N2X-NRGL(668097),         --AR5710-H2T4N2X-NRGL Main Control Unit
                Add: fnameAR5710-H2T4PN2X-NRGL(668098),        --AR5710-H2T4PN2X-NRGL Main Control Unit
                Add: fnameAR5710-S8P1XDSE-2LTE4EA(668099),     --AR5710-S8P1XDSE-2LTE4EA Main Control Unit
                Add: fnameAR5710-S8TWDSE-LTE4EA(668100),       --AR5710-S8TWDSE-LTE4EA Main Control Unit
                Add: fnameAR5710-S8T1XWE-LTE4CN(668101),       --AR5710-S8T1XWE-LTE4CN Main Control Unit
                Add: fnameAR5510-S8T2XE-NRGL(668102),          --AR5510-S8T2XE-NRGL Main Control Unit
                Add: bnameAR5710-H4T4N2X(668217),             --AR5710-H4T4N2X Main Control Unit
                Add: bnameAR5710-H4T4N2X-LTE4EA(668218),      --AR5710-H4T4N2X-LTE4EA Main Control Unit
                Add: bnameAR5710-H2T4N2X-NRGL(668219),        --AR5710-H2T4N2X-NRGL Main Control Unit
                Add: bnameAR5710-H2T4PN2X-NRGL(668220),       --AR5710-H2T4PN2X-NRGL Main Control Unit
                Add: bnameAR5710-S8P1XDSE-2LTE4EA(668221),    --AR5710-S8P1XDSE-2LTE4EA Main Control Unit
                Add: bnameAR5710-S8TWDSE-LTE4EA(668222),      --AR5710-S8TWDSE-LTE4EA Main Control Unit
                Add: bnameAR5710-S8T1XWE-LTE4CN(668223),      --AR5710-S8T1XWE-LTE4CN Main Control Unit
                Add: bnameAR5510-S8T2XE-NRGL(668224),         --AR5510-S8T2XE-NRGL Main Control Unit
                Add: bnameSIC-1V35B-V2(668225),               --SIC-1V35B-V2 Lpu Control Unit
                " 

        REVISION "202501231000Z"
          DESCRIPTION "V36.10,
              Add: fnameNETENGINE-6000-X4-DC(688716),   -- Quidway fnameNETENGINE-6000-X4-DC FRAME for V8R25C00
              Add: fnameNETENGINE-6000-X4-HVDC(688717), -- Quidway fnameNETENGINE-6000-X4-HVDC FRAME for V8R25C00
              Add: fnameNETENGINE-6000-X8-DC(688718),   -- Quidway fnameNETENGINE-6000-X8-DC FRAME for V8R25C00
              Add: fnameNETENGINE-6000-X8-HVDC(688719), -- Quidway fnameNETENGINE-6000-X8-HVDC FRAME for V8R25C00
              Add: virent8090DEVCR8D6LPF1TC0(679800),   -- V8R25C00 for CR8D6LPF1TC0(SBOM) Flexible Card Line Processing Unit (LPUF-1T)
              Add: virent8090DEVCR8D6LPF2TC0(679801),   -- V8R25C00 for CR8D6LPF2TC0(SBOM) Flexible Card Line Processing Unit (LPUF-2T)
              Add: virent8090DEVCR8D6LPF1TE0(679802),   -- V8R25C00 for CR8D6LPF1TE0(SBOM) Flexible Card Line Processing Unit E(LPUF-1T-E)
              Add: virent8090DEVCR8D6MPUA1C0(679803),   -- V8R25C00 for CR8D6MPUA1C0(SBOM) NetEngine 6000 Main Processing Unit A1(MPUA1)
              Add: virent8090DEVCR8D6SFU2TA0(679804),   -- V8R25C00 for CR8D6SFU2TA0(SBOM) NetEngine 6000 X4 2Tbps Switch Fabric Unit(SFUI-2T-A)
              Add: virent8090DEVCR8D6SFU2TB0(679805),   -- V8R25C00 for CR8D6SFU2TB0(SBOM) NetEngine 6000 X8 2Tbps Switch Fabric Unit(SFUI-2T-B)
              Add: virent8090DEVCR8D6VUF8HC1(679806),   -- V8R25C00 for CR8D6VUF8HC1(SBOM) Flexible Card Versatile Service Unit 800(VSUF-800)" 
        REVISION "202501221448Z"
          DESCRIPTION "V36.09,
              Add: subbname8090DEVANND001EY800(709807),            -- 8 Channels 25G (SFP28) High Speed Interface Board
              Add: subbname8090DEVANOD00E8XM2A(709808),            -- 8 Channels 25G (SFP28) High Speed Interface Board
              Add: subbname8090DEVANNDE1NBFM02(709818),            -- 1-Port 100GBase/50GBase-QSFP28 FlexE MACsec+8-Port 10GE(SFP+)/GE(SFP) MACsec Physical Interface Card(PIC)" 
        REVISION "202501201923Z"
          DESCRIPTION "V36.08,
              Add: virent8090DEVXHXDLPUF2TC0(364090),   -- V8R25C00 for XHXDLPUF2TC0(SBOM) Flexible Card Line Processing Unit(LPUF-2T4A)
              Add: virent8090DEVXHXDLPUF4TC0(364091),   -- V8R25C00 for XHXDLPUF4TC0(SBOM) Flexible Card Line Processing Unit(LPUF-4T8A)" 
        REVISION "202501201702Z"
          DESCRIPTION "V36.07,
              Add: virent8090DEVCR8DSFU09TA0(896529),   -- V8R24C10 for CR8DSFU09TA0(SBOM) NetEngine 8000 X4 9.6Tbps Switch Fabric Unit(SFUI-9T6-A)
              Add: virent8090DEVCR8DSFUI9TB5(896530),   -- V8R24C10 for CR8DSFUI9TB5(SBOM) NetEngine 8000 X4 9.6Tbps Switch Fabric Unit(SFUIA-9T6-A)"

        REVISION "202501171702Z"
          DESCRIPTION "V36.06,
              Add: virent8090DEVXHEDE6LEJKXS(462882),   -- V8R25C00 for XHEDE6LEJKXS(SBOM) 6-Port 800GBase-QSFP-DD + 36-Port 400GBase-QSFP-DD Integrated Line Processing Unit CM(LPUI-19T2-CM,Enable 36*100GE by default)
              Add: virent8090DEVXHEDSFU19TBA(896531),   -- V8R25C00 for XHEDSFU19TBA(SBOM) NetEngine XH16000E X8 19.2Tbps Switch Fabric Unit(SFUIA-19T2-B)
              Add: virent8090DEVCR8DVSUPA0F2(679798),    -- V8R25C00 for CR8DVSUPA0F2(SBOM) Multi-function Integrated Service Card(VSUP-100)
              Add: virent8090DEVCR8DVSUPA0F3(679799),    -- V8R25C00 for CR8DVSUPA0F3(SBOM) Multi-function Integrated Service Card(VSUPA-100)"
        REVISION "202501170912Z"
          DESCRIPTION "V36.05,
              Add: fnameNETENGINE-XH861-E-AC(210004),      -- Quidway fnameNETENGINE-XH861-E-AC FRAME for V8R25C00
              Add: fnameNETENGINE-XH861-E-DC(210002),      -- Quidway fnameNETENGINE-XH861-E-DC FRAME for V8R25C00
              Add: fnameNETENGINE-XH861-E(210003),         -- Quidway fnameNETENGINE-XH861-E FRAME for V8R25C00(AC+DC)
              Add: virent8090DEVXHAPHST3EA00(210006),   -- V8R25C00 for XHAPHST3EA00(SBOM) NetEngine XH861 E, AC Power, Port Capacity 4*100GE/50GE+16*25GE/10GE/GE/FE+8*10GE/GE/FE, all the GE/FE ports is enabled
              Add: virent8090DEVXHAPHST3ED00(210005),   -- V8R25C00 for XHAPHST3ED00(SBOM) NetEngine XH861 E, DC Power, Port Capacity 4*100GE/50GE+16*25GE/10GE/GE/FE+8*10GE/GE/FE, all the GE/FE ports is enabled
              Add: virent8090DEVXHAPHST3AD00(210007),   -- V8R25C00 for XHAPHST3AD00(SBOM) NetEngine XH861 E, AC+DC Power, Port Capacity 4*100GE/50GE+16*25GE/10GE/GE/FE+8*10GE/GE/FE, all the GE/FE ports is enabled"
        REVISION "202501141000Z"
          DESCRIPTION "V36.04,
              Add: subbname8090DEVNSRCPA1(548688),            -- 1-Port 100GBase/50GBase-QSFP28 FlexE MACsec+8-Port 10GE(SFP+)/GE(SFP) MACsec Physical Interface Card(PIC)
              Add: subbname8090DEVNSRCPA1A(548689),            -- VIRTUALPIC_NSRCPA1A_CARD"
        REVISION "202501140000Z"
          DESCRIPTION "V36.03,
              Add: bname and fname from S5735-L24P4XE-A-V2-BJEX to S550-48T8Y."
        
        REVISION "202501131720Z"
            DESCRIPTION "V36.02,
                Add: subbname8090DEVCARDNetEngineXH861E(235933),     --CARD NetEngine XH861E"
 
        REVISION "202501112200Z"
            DESCRIPTION "V36.01,
            Add: subbname8090DEVDSVIRTUALPIC(709990),         --DS_FLEXE_VIRTUAL_CARD"
        REVISION "202501102200Z"
            DESCRIPTION "V35.06,
            Delete: subbname8090DEVDS_FLEXE_VIRTUAL_CARD(709990),         --DS_FLEXE_VIRTUAL_CARD"

        REVISION "202501102100Z"
            DESCRIPTION "V35.05,
            Add: subbname8090DEVDS_FLEXE_VIRTUAL_CARD(709990),         --DS_FLEXE_VIRTUAL_CARD"

        REVISION "202501082100Z"
            DESCRIPTION "V35.04,
            Add: virent8090DEVCR8D0MPUAX6(364080),    -- V8R24C10 for CR8D0MPUAX6(SBOM) NetEngine 8000E Main Processing Unit A1(MPUA1)
            Add: virent8090DEVCR8D0MPUAXCB(364081),   -- V8R24C10 for CR8D0MPUAXCB(SBOM) NetEngine 8000E Main Processing Unit A1B(MPUA1B)
            Add: virent8090DEVCR8D0MPUAXC8(364082),   -- V8R24C10 for CR8D0MPUAXC8(SBOM) NetEngine 8000E Main Processing Unit A2(MPUA2)
            Add: virent8090DEVCR8D0MPUAXC6(364083),   -- V8R24C10 for CR8D0MPUAXC6(SBOM) NetEngine 8000E Main Processing Unit A2B(MPUA2B)"

        REVISION "202501080930Z"
            DESCRIPTION "V35.03,
            Add: bnamePTN7900TPA2EX16P(229712),   --TPA2EX16P,16-Port 10 Gigabit Adaptive Ethernet Switching Processing Board(physical board, with 8 port enabled by default)
                 bnamePTN7900TPA1EX24P(229713),   --TPA1EX24P,24-Port 10 Gigabit Ethernet Switching Processing Board(physical board, with 16 port enabled by default)
                 bnamePTN7900TPA3FH2P(229714),   --TPA3FH2P,2-port 100Gigabit Ethernet FlexE Service Processing Board(physical board, with 1 port enabled by default)
                 bnamePTN7900TPA5FH4P(229715),   --TPA5FH4P,4-port 100Gigabit Ethernet FlexE Service Processing Board(physical board, with 1 port enabled by default)
                 bnamePTN7900TPD1FH8P(229716),   --TPD1FH8P,8-port 100Gigabit Ethernet FlexE Service Processing Board(physical board, with 4 port enabled by default)
                 bnamePTN7900TPA5FV8P(229717),   --TPA5FV8P,8-port 50Gigabit Ethernet FlexE Service Processing Board(physical board, with 4 port enabled by default)"

        REVISION "202501072100Z"
            DESCRIPTION "V35.02,
            Add: virent8090DEVCR5DSFUIT462(562303),    -- V8R25C00 for CR5DSFUIT462(SBOM) NE5000E-20 8T CLC Integrated Switch Fabric Unit for Multi-Chassis(SFUI-8T-M)"

        REVISION "202501071542Z"
            DESCRIPTION "V35.01,
            The object identifier of AR502H-NRGL-V2 is added."

        REVISION "202501070905Z"
            DESCRIPTION "V34.03,
            Modify: virent8090DEVCR81IPU2TABS(219999) -> virent8090DEVCR8D0IPU2TM4(219999)
                    virent8090DEVCR81IPU1T2A9S(219921) -> virent8090DEVCR8DIPU1T2MC(219921)"
        
        REVISION "202501020930Z"
            DESCRIPTION "V34.02,
            Add: fnameAirEngine5773H-21(692507),
                 bnameAirEngine5773H-21(692507)"

        REVISION "202412310930Z"
            DESCRIPTION "V34.10,
            Add: virent8090DEVCR8DEANEWAD0(539207),   -- V8R25C00 for CR8DEANEWAD0 10-Port 100GBase-QSFP28 + 36-Port 25GE(SFP28)/10GE(SFP+)/GE(SFP) Integrated Line Processing Unit CM(LPUI-2T-CM)."


       REVISION "202412300910Z"
            DESCRIPTION "V34.00,
            Modify: bnameCEXLPUJ2(688681) -> bnameXHL40DQJ2LC(688681)."

        REVISION    "202412202100Z"
            DESCRIPTION "V30.10,
            Add: subbname8090DEVCR8DEFNBFCC1(709839),            -- 24-Port 100GBase-QSFP28 FlexE MACsec Flexible Card CM(P6T4-CM)
            Add: subbname8090DEVCR8DE1KE1NCQ(709826),            -- 1-Port 400GBase-QSFP-DD FlexE + 1-Port 100GBase-QSFP28 Flexible Card CM(P1T-CM,400GE Port Enabled with 100GE by default)
            Add: subbname8090DEVCR8DE1KE1NEQ(709827),            -- 1-Port 400GBase-QSFP-DD FlexE + 1-Port 100GBase-QSFP28 Flexible Card E CM(P1T-E-CM,400GE Port Enabled with 100GE by default)
            Add: subbname8090DEVCR8DEDNBFECQ(709858),            -- 16-Port 100GBase-QSFP28 FlexE MACsec Flexible Card CM(P3T2-CM)
            Add: subbname8090DEVCR8DEDNBFEEQ(709859),            -- 16-Port 100GBase-QSFP28 FlexE MACsec Flexible Card E CM(P3T2-E-CM)
            Add: subbname8090DEVCR8DE4KBFECQ(709848),            -- 4-Port 400GBase-QSFP-DD FlexE MACsec Flexible Card CM(P3T2-CM,400GE Port Enabled with 100GE by default)
            Add: subbname8090DEVCR8DE4KBFEEQ(709849),            -- 4-Port 400GBase-QSFP-DD FlexE MACsec Flexible Card E CM(P3T2-E-CM,400GE Port Enabled with 100GE by default)
            Add: subbname8090DEVCR8DE00E8KN1(709805),            -- 8-Port 400GBase-QSFP-DD FlexE MACsec Flexible Card CM(P6T4-CM,400GE Port Enabled with 100GE by default)
            Add: subbname8090DEVCR8DE00E8KE1(709806),            -- 8-Port 400GBase-QSFP-DD FlexE MACsec Flexible Card E CM(P6T4-E-CM,400GE Port Enabled with 100GE by default)"

        REVISION    "202412162000Z"
            DESCRIPTION "V30.09,
            Add: virent8090DEVCR8DIPU1T2ML(263593),   -- V8R24C10 for CR8DIPU1T2ML(SBOM) Integrated Network Processing Unit (IPU-1T2-EN)
            Add: virent8090DEVCR8D0IPU3TM9(660086),   -- V8R24C10 for CR8D0IPU3TM9(SBOM) Integrated Network Processing Unit (IPU-3T6-A)
            Add: virent8090DEVCR8DUIPU2TM7(985137),   -- V8R24C10 for CR8DUIPU2TM7(SBOM) Integrated Network Processing Unit (IPU-2T-AU)
            Add: virent8090DEVCR8D0IPU3TM8(213467),   -- V8R24C10 for CR8D0IPU3TM8(SBOM) Integrated Network Processing Unit (IPU-3T6-E-B)
            Add: virent8090DEVCR8DUIPU2TM8(962666),   -- V8R24C10 for CR8DUIPU2TM8(SBOM) Integrated Network Processing Unit (IPU-2T-E-BU)"

        REVISION    "202412161000Z"
            DESCRIPTION "V30.08,
            Add: bnameCR8MM82FBXC4(564555),    -- NetEngine 8000E M8 Fan Box"

        REVISION    "202412121100Z"
            DESCRIPTION "V30.07,
            The object identifier of S5735I-H8T4S2XN is renamed S5735I-H8T4S2XN-V2,
            Modify: fname8031S5735I-H8T4S2XN(537853)->fname8031S5735I-H8T4S2XN-V2(537853)
            Modify: fnane8031S5735I-S48T4XE-V2(538049)->fname8031S5735I-S48T4XE-V2(538049)
            Modify: bname8031S5735I-H8T4S2XN(538036)->bname8031S5735I-H8T4S2XN-V2(538036)"
        
        REVISION    "202412121100Z"
            DESCRIPTION "V30.06,
            Add: subbname8090DEVIG2D00SP8001(709781),            -- Service Processing Flexible Card(SP800)-with 8*10GE port
            Add: subbname8090DEVIG2D00SP8002(709782),            -- Service Processing Enhanced Flexible Card(SP800E)-with 8*10GE port"

        REVISION    "202412111100Z"
            DESCRIPTION "V30.05,
            Modify: bnameCESFU08GL2(688511)->bnameCESFU08GL(688511)
            Modify: bnameCESFU04GL2(688512)->bnameCESFU04GL(688512)
            Modify: bnameCESFU16GL2(688514)->bnameCESFU16GL(688514)
            Modify: bnamePAC2KS12PB(688590)->bnamePAC2KS12PB(688590)
            Add: bnameCEX9SFU16GL(688682) "

        REVISION    "202412101100Z"
            DESCRIPTION "V30.04,
            Add: virent8090DEVCR8DVSUIK0C6(364077),   -- V8R24C10 for CR8DVSUIK0C6(SBOM) Multi-Function Integrated Service Unit 400(MSUI-400-E)
            Add: virent8090DEVCR8DVSUIK0C7(364078),   -- V8R24C10 for CR8DVSUIK0C7(SBOM) Multi-Function Integrated Service Unit 400(MSUI-400A-E)"

        REVISION    "202412090000Z"
            DESCRIPTION "V30.03,
            Add: virent8090DEVCR5D00E8KB66(562196),    -- V8R24C00 for CR5D00E8KB66(SBOM) 8-Port 400GBase QSFP-DD Integrated Line Process Unit(NE5000E LPUI-3T2-E)
            Add: virent8090DEVCR5D00EINB66(562197),    -- V8R24C00 for CR5D00EINB66(SBOM) 32-Port 100GBase QSFP28 Integrated Line Process Unit(NE5000E LPUI-3T2-E)
            Add: virent8090DEVCR5D00E8KB67(562198),    -- V8R24C00 for CR5D00E8KB67(SBOM) 8-Port 400GBase QSFP-DD Integrated Line Process Unit CM(NE5000E LPUI-3T2-E-CM)(2 ports enable)
            Add: virent8090DEVCR5D00EINB67(562199),    -- V8R24C00 for CR5D00EINB67(SBOM) 32-Port 100GBase QSFP28 Integrated Line Process Unit CM(NE5000E LPUI-3T2-E-CM)(8 ports enable)"

        REVISION    "202412090000Z"
            DESCRIPTION "V30.02,
            Add: subbname8090DEVCR8DE4NB00M4(709872),   -- 4-Port 100GBase/50GBase-QSFP28 Physical Interface Card(PIC)
            Add: subbname8090DEVCR8DE4NB00M5(709873),   -- 4-Port 100GBase/50GBase-QSFP28 Physical Interface Card CM(Enable 2*100GE by default)(PIC)
            Add: subbname8090DEVCR8D0LJXXCCQ(513270),   -- 36-Port 10GBase LAN/WAN-SFP+ MACsec Flexible Card CM(P1T-CM)
            Add: subbname8090DEVANNDE8EFFEC1(549699),   -- 8-Port 10GE-SFP+ FlexE High Speed Interface Board
            Add: subbname8090DEVCR8DE4KBFECS(709847),   -- 4-Port 400GBase-QSFP-DD FlexE MACsec Flexible Card CM(P3T2-CM,400GE Port Enabled with 100GE by default)
            Add: subbname8090DEVCR5D00LAXF92(709874),   -- 10-Port 10GE/GE LAN/WAN-SFP+ MACsec Physical Interface Card(PIC)
            Add: subbname8090DEVCARDNetEngineXH821(235930),  --CARD NetEngine XH821
            Add: subbname8090DEVCARDNetEngineXH821E(235931),  --CARD NetEngine XH821 E
            Add: subbname8090DEVCARDNetEngineXH86(235932),   --CARD NetEngine XH861
            Add: subbname8090DEVCR59TDNBA1(709798),  --16xOTU4/16x100GE QSFP28 Fixed card
            Add: subbname8090DEVCR8D800E8KC2(709869), --8-Port 400GBase-QSFP-DD FlexE MACsec Flexible Card CM(P6T4-CM,400GE Port Enabled with 100GE by default)
            Add: subbname8090DEVCR8DEFNBFCE1(709838), --24-Port 100GBase-QSFP28 FlexE MACsec Flexible Card E CM(P6T4-E-CM)
            Add: subbname8090DEVCR8DG80400C0(548792), --4 Channels C37.94 and 4 Channels 64K Physical Interface Card
            Add: subbname8090DEVCR59TDNBA0(709797), --16xOTU4/16x100GE QSFP28 Fixed card
            Add: subbname8090DEVCR8DE2NBMSF2(548700), --2-Port 100GBase/50GBase-QSFP28 Interface Card(PIC)
            Add: subbname8090DEVCR8DE2NBMSF3(548701), --2-Port 100GBase/50GBase-QSFP28 Interface Card(PIC)
            Add: subbname8090DEVCR8DEDNBFECT(709857), --2-Port 100GBase/50GBase-QSFP28 Interface Card(PIC)"

        REVISION    "202412060000Z"
            DESCRIPTION "V30.01,
            Add: bnameTPP1FAN(226711),                    -- PTN 910E-F,TPP1FAN
            Add: bnameTPP1APIU(226712),                   -- PTN 910E-F,TPP1APIU
            Add: bnameTPP1PIU(226713),                    -- PTN 910E-F, TPP1PIU
            Add: bnameTPQ1FAN01(226714),                  -- OptiX PTN 990E,TPQ1FAN
            Add: bnameTPR1FAN01(229021),                  -- PTN970C,TPR1FAN01,Fan Box
            Add: bnamePOWER(226715),                      -- powerSupply
            Add: bnameDEVFAN(226716),                     -- PTN 916-F,FAN01,Fan Box
            Add: bnameTPT1FAN01(226717),                  -- OptiX PTN 980B,TPT1FAN
            Add: bnameTPI1FAN01(226718),                  -- OptiX SPN 985,TPI1FAN01
            Add: bnameTPU1FAN01(226719),                  -- OptiX PTN 990B,TPU1FAN"

        REVISION     "202412020000Z"
        DESCRIPTION  "V30.00,
                    Modify: from bnameH902DPWA(148850) to bnameH901DPWB(148850),    -- Wind resistance board of MA5800T.
                     "

        REVISION    "202411300000Z"
            DESCRIPTION "V29.00,
            Modidy: subbnameAirEngine6776-X6ETH(692494),
                    fnameAirEngine6776-X6ETH(692494),
                    bnameAirEngine6776-X6ETH(692494)"

        REVISION "202411280000Z"
            DESCRIPTION "V28.00,
            Modified the description of bnameC04Q40E(157013) from Control and forwarding board of MC5101-C04Q40-E to Control and forwarding board of MC5101-C04Q40E.
            Add: fnameMC5101C04Q40E(148546),        --  Backplane of the MC5101-C04Q40E.
            Add: bnamePAC1K2S12(157014),            --  Power board of MC5101-C04Q40E.
            Add: bnamePAC600S12(157015),            --  Power board of MC5101-C04Q40E.
            Add: bnamePDC1K2S12(157016),            --  Power board of MC5101-C04Q40E."

        REVISION    "202411110000Z"
            DESCRIPTION "V27.00,
            Add: bnameH902DPWA(148850),                 -- Wind resistance board of MA5800T."

        REVISION "202411110000Z"
            DESCRIPTION "V26.00,
            Add: bnameHA01PDMA(148849),                --  Power board of MA5800T-X8."

        REVISION "202411081245Z"
            DESCRIPTION "V25.04,
            Add: virentPTN7900VPICTPD1FHL4(229720)"

       REVISION "202411060910Z"
            DESCRIPTION "V25.03,
            Add: fnameCE588548T8YS(688335) - fnameXH1680016LC(687006).
            Add: bnameCE588548T8YS(688672) - bnameCEXLPUJ2(688681)."

         REVISION "202411050910Z"
            DESCRIPTION "V25.02,
            Add: bnameLSG3C08HX1E0(659779)."
         REVISION "202410310910Z"
            DESCRIPTION "V25.01,
            Add: Bname and fname of the s5735,s5755,s5751,s310,s220."

         REVISION "202410300910Z"
            DESCRIPTION "V24.03,
            Add: bnameHA01ATHF(148805),                --  16*GPON, XGSPON and 50GPON combo board of MA5800T."
        
        REVISION "202410281626Z"
            DESCRIPTION "V24.02,
            Add: virent8090DEVCR81LPUFT073(689379),   -- V8R24C10 for CR81LPUFT073(SBOM) Flexible Card Line Processing Unit(LPUF-1TA)
            Add: virent8090DEVCR8DLPUF3TC4(718759),   -- V8R24C10 for CR8DLPUF3TC4(SBOM) Flexible Card Line Processing Unit(LPUF-3T2)
            Add: bnameTPID01CXPA01(226709),               --OptiX SPN 985,TPI1CXPA0,System Control,Cross-connect and Multi-protocol Process Unit
            Add: fnameSPN985-DC(226708),                              -- SPN985-DC chassis
            Add: fnameSPN985-AC(226710),                              -- SPN985-AC chassis"
            
        REVISION "202410281126Z"
            DESCRIPTION "V24.01,
            Add: bnameCR8M002FBXC5(564514),
            Add: bnameCR8M004FBXC1(564554)"

        REVISION "202410181530Z"
            DESCRIPTION "V24.00,
            Add: virent8090DEVIG2D00SPUH02(359889),
            Modify: virent8090DEVIG2D00SPUH01(359885)"

        REVISION "202410101955Z"
            DESCRIPTION "V23.02,
            Add: subbnamePIC620V1ROH(720918)"

        REVISION "202410081100Z"
            DESCRIPTION "V23.01,
                Add: virent8090DEVIG2DLPUFT6TA(165936),   -- V8R24C10 for IG2DLPUFT6TA(SBOM) Flexible Card Line Processing Unit(LPUF-6T4A)"
    
        REVISION "202409301100Z"
            DESCRIPTION "V23.00,
                Add: subbname8090DEVCR8D800E8KE1(709866),            -- 8-Port 400GBase-QSFP-DD FlexE MACsec Flexible Card E CM(P6T4-E-CM,400GE Port Enabled with 100GE by default)
                Add: subbname8090DEVCR8D800E8KL1(709867),            -- 8-Port 400GBase-QSFP-DD FlexE MACsec Flexible Card L CM(P6T4-L-CM,400GE Port Enabled with 100GE by default)
                Add: subbname8090DEVCR8D800E8KC1(709868),            -- 8-Port 400GBase-QSFP-DD FlexE MACsec Flexible Card CM(P6T4-CM,400GE Port Enabled with 100GE by default)
                Add: subbname8090DEVCR8DE4KBFECP(709840),            -- 4-Port 400GBase-QSFP-DD FlexE MACsec Flexible Card CM(P3T2-CM,400GE Port Enabled with 100GE by default)
                Add: subbname8090DEVCR8DE4KBFEEP(709841),            -- 4-Port 400GBase-QSFP-DD FlexE MACsec Flexible Card E CM(P3T2-E-CM,400GE Port Enabled with 100GE by default)
                Add: subbname8090DEVCR8DE4KBFELP(709842),            -- 4-Port 400GBase-QSFP-DD FlexE MACsec Flexible Card L CM(P3T2-L-CM,400GE Port Enabled with 100GE by default)
                Add: subbname8090DEVCR8D84KBFECP(709843),            -- 4-Port 400GBase-QSFP-DD FlexE MACsec Flexible Card CM(P3T2-CM,400GE Port Enabled with 100GE by default)
                Add: subbname8090DEVCR8D84KBFEEP(709844),            -- 4-Port 400GBase-QSFP-DD FlexE MACsec Flexible Card E CM(P3T2-E-CM,400GE Port Enabled with 100GE by default)
                Add: subbname8090DEVCR8D84KBFELP(709845),            -- 4-Port 400GBase-QSFP-DD FlexE MACsec Flexible Card L CM(P3T2-L-CM,400GE Port Enabled with 100GE by default)
                Add: subbname8090DEVCR8DEDNBFECP(709850),            -- 16-Port 100GBase-QSFP28 FlexE MACsec Flexible Card CM(P3T2-CM)
                Add: subbname8090DEVCR8DEDNBFEEP(709851),            -- 16-Port 100GBase-QSFP28 FlexE MACsec Flexible Card E CM(P3T2-E-CM)
                Add: subbname8090DEVCR8DEDNBFELP(709852),            -- 16-Port 100GBase-QSFP28 FlexE MACsec Flexible Card L CM(P3T2-L-CM)
                Add: subbname8090DEVCR8D8DNBFECP(709853),            -- 16-Port 100GBase-QSFP28 FlexE MACsec Flexible Card CM(P3T2-CM)
                Add: subbname8090DEVCR8D8DNBFEEP(709854),            -- 16-Port 100GBase-QSFP28 FlexE MACsec Flexible Card E CM(P3T2-E-CM)
                Add: subbname8090DEVCR8D8DNBFELP(709855),            -- 16-Port 100GBase-QSFP28 FlexE MACsec Flexible Card L CM(P3T2-L-CM)
                Add: subbname8090DEVCR8DEDNBFECR(709856),            -- 16-Port 100GBase-QSFP28 FlexE MACsec Flexible Card CM(P3T2-CM)
                Add: subbname8090DEVCR8DE4KBFECR(709846),            -- 4-Port 400GBase-QSFP-DD FlexE MACsec Flexible Card CM(P3T2-CM,400GE Port Enabled with 100GE by default)
                Add: subbname8090DEVCR8DEFNBFCC0(709831),            -- 24-Port 100GBase-QSFP28 FlexE MACsec Flexible Card CM(P6T4-CM)
                Add: subbname8090DEVCR8DEFNBFCE0(709832),            -- 24-Port 100GBase-QSFP28 FlexE MACsec Flexible Card E CM(P6T4-E-CM)
                Add: subbname8090DEVCR8DEFNBFCL0(709833),            -- 24-Port 100GBase-QSFP28 FlexE MACsec Flexible Card L CM(P6T4-L-CM)
                Add: subbname8090DEVCR8D8EFNBFC0(709834),            -- 24-Port 100GBase-QSFP28 FlexE MACsec Flexible Card CM(P6T4-CM)
                Add: subbname8090DEVCR8D8FNBFCE0(709835),            -- 24-Port 100GBase-QSFP28 FlexE MACsec Flexible Card E CM(P6T4-E-CM)
                Add: subbname8090DEVCR8D8EFNBFL0(709836),            -- 24-Port 100GBase-QSFP28 FlexE MACsec Flexible Card L CM(P6T4-L-CM)
                Add: subbname8090DEVCR8D000600C0(709837),            -- 6 Channes E&M Interface Board
                Add: subbname8090DEVCR8DE1KE1NCP(709820),            -- 1-Port 400GBase-QSFP-DD FlexE + 1-Port 100GBase-QSFP28 Flexible Card CM(P1T-CM,400GE Port Enabled with 100GE by default)
                Add: subbname8090DEVCR8DE1KE1NEP(709821),            -- 1-Port 400GBase-QSFP-DD FlexE + 1-Port 100GBase-QSFP28 Flexible Card E CM(P1T-E-CM,400GE Port Enabled with 100GE by default)
                Add: subbname8090DEVCR8D8E1K1NCP(709822),            -- 1-Port 400GBase-QSFP-DD FlexE + 1-Port 100GBase-QSFP28 Flexible Card CM(P1T-CM,400GE Port Enabled with 100GE by default)
                Add: subbname8090DEVCR8D8E1K1NEP(709823),            -- 1-Port 400GBase-QSFP-DD FlexE + 1-Port 100GBase-QSFP28 Flexible Card E CM(P1T-E-CM,400GE Port Enabled with 100GE by default)
                Add: subbname8090DEVCR8D8E1K1NLP(709824),            -- 1-Port 400GBase-QSFP-DD FlexE + 1-Port 100GBase-QSFP28 Flexible Card L CM(P1T-L-CM,400GE Port Enabled with 100GE by default)
                Modify: subbname8090DEVCR8DE00E8KN0(709860),            -- 8-Port 400GBase-QSFP-DD FlexE MACsec Flexible Card CM(P6T4-CM,400GE Port Enabled with 100GE by default)
                Modify: subbname8090DEVCR8DE00E8KE0(709861),            -- 8-Port 400GBase-QSFP-DD FlexE MACsec Flexible Card E CM(P6T4-E-CM,400GE Port Enabled with 100GE by default)
                Modify: subbname8090DEVCR8DE00E8KL0(709862),            -- 8-Port 400GBase-QSFP-DD FlexE MACsec Flexible Card L CM(P6T4-L-CM,400GE Port Enabled with 100GE by default)
                Add: subbname8090DEVCR8D800E8KC0(709863),            -- 8-Port 400GBase-QSFP-DD FlexE MACsec Flexible Card CM(P6T4-CM,400GE Port Enabled with 100GE by default)
                Add: subbname8090DEVCR8D800E8KE0(709864),            -- 8-Port 400GBase-QSFP-DD FlexE MACsec Flexible Card E CM(P6T4-E-CM,400GE Port Enabled with 100GE by default)
                Add: subbname8090DEVCR8D800E8KL0(709865),            -- 8-Port 400GBase-QSFP-DD FlexE MACsec Flexible Card L CM(P6T4-L-CM,400GE Port Enabled with 100GE by default)
                Add: subbname8090DEVIG2DE4KEDND1(709780),            -- 4-Port 400GBase-QSFP-DD + 16-Port 100GBase-QSFP28 FlexE MACsec Flexible Card(P6T4)
                Add: subbname8090DEVANOD001EY401(225652),   -- 4 Channels 25G (SFP28)/4 Channels 10G (SFP+) High Speed Interface Board
                Add: subbname8090DEVANOD001EY410(225658),   -- 4 Channels 25G (SFP28)/4 Channels 10G (SFP+) High Speed Interface Board
                Add: subbname8090DEVCR8DE1KB00M5(709870),   -- 1-Port 400GBase-QSFP-DD Single-layer Physical Interface Card(PIC)
                Add: subbname8090DEVCR8DE1KB00M6(709871),   -- 1-Port 400GBase-QSFP-DD Single-layer Physical Interface Card CM(Enable 1*100G)(PIC)
                Add: subbname8090DEVANODE1KB00M1(709875),   -- 1-Port 400GBase-QSFP-DD Physical Interface Card(PIC)
                Add: subbname8090DEVANODE1KB00M2(709876),   -- 1-Port 400GBase-QSFP-DD Physical Interface Card CM(Enable 1*100G)(PIC)
                Add: subbname8090DEVANODE1KB00D1(709877),   -- 1-Port 400GBase-QSFP-DD Physical Interface Card(PIC)
                Add: subbname8090DEVANOD00EM8F01(709878),   -- 8 Channels GE/FE Electrical Interface Board
                Add: subbname8090DEVANOD00EM8FE0(709879),   -- 8 Channels GE/FE Electrical Interface Board
                Add: subbname8090DEVANOD0EM10F00(709880),   -- 10 Channels GE/FE Optical Interface Board
                Add: subbname8090DEVANOD0EM10GE0(709881),   -- 10 Channels GE/FE Optical Interface Board
                Add: subbname8090DEVANOD01EXAS01(709882),   -- 10 Channels 10GE Optical Interface Board(SFP+)
                Add: subbname8090DEVANOD01EXAS10(709883),   -- 10 Channels 10GE Optical Interface Board(SFP+)
                Add: subbname8090DEVANODE2NB00C2(709884),   -- 2-Port 100GBase/50GBase-QSFP28 Interface Card(PIC)
                Add: subbname8090DEVANODE2NB00D2(709885),   -- 2-Port 100GBase/50GBase-QSFP28 Interface Card(PIC)
                Add: subbname8090DEVANND000EM890(709886),   -- 6 Channes E&M Interface Board
                Add: subbname8090DEVCR59E2EBA(709825),         -- 2-Port 800GBase QSFP-DD"

        REVISION "202409271400Z"
            DESCRIPTION "V22.02,
                Add: portnameAR01OPENGE(667683), -- V8R24C10 for OpenGE port type,
                Add: portnameAR01VGE(667684), -- V8R24C10 for VGE port type"
        REVISION "202409191400Z"
            DESCRIPTION "V22.01,
                Add: virent8090DEVTPIM0HOSTA00(221266), -- V8R24C10 for TPIM0HOSTA00(SBOM) SPN A907-I - AC Power,with 6*GE/FE(o),8*GE/FE(e) Natural heat dissipation without fans,
                Add: fnameSPNA907-I-AC(229574), -- V8R24C10 for SPNA907-I-AC chassis"

        REVISION "202409181400Z"
            DESCRIPTION "V21.04,
                Modify: fnameNETENGINE-XH16000-X8-DC(688689),      -- Quidway fnameNETENGINE-XH16000-X8-DC for V8R24C00,
                Modify: fnameNETENGINE-XH16000-X8-HVDC(688690),    -- Quidway fnameNETENGINE-XH16000-X8-HVDC for V8R24C00,
                Modify: fnameNETENGINE-XH16000-X8-HVDC(688690),    -- Quidway fnameNETENGINE-XH16000-X8-HVDC for V8R24C00,
                Modify: fnameNETENGINE-XH16000-X8-HVDC(688690),    -- Quidway fnameNETENGINE-XH16000-X8-HVDC for V8R24C00,
                Modify: virent8090DEVCR8D0MPUAXC5(364028),   -- V8R24C00 for CR8D0MPUAXC5(SBOM) NetEngine XH16000 Main Processing Unit A10B(MPUA10B),
			    Modify: virent8090DEVCR8D0MPUAXC9(364029),	-- V8R24C00 for CR8D0MPUAXC9(SBOM) NetEngine XH16000E Main Processing Unit A10B(MPUA10B),
			    Modify: virent8090DEVCR8DSFUI9TB2(678752),   -- V8R24C00 for CR8DSFUI9TB2(SBOM) NetEngine XH16000 X8 9.6Tbps Switch Fabric Unit(SFUIA-9T6-B),
			    Modify: virent8090DEVCR8DSFUI9TB9(678753),   -- V8R24C00 for CR8DSFUI9TB9(SBOM) NetEngine XH16000E X8 9.6Tbps Switch Fabric Unit(SFUIA-9T6-B)"

        REVISION "202409181000Z"
            DESCRIPTION "V21.03,
                Add: fname8031S5735I-H8T2XN-V2(537980),
                Add: fname8031S5735I-H8U2XN-V2(537981),
                Add: fname8031S5735I-S8U2XN-V2(537982),
                Add: fnane8031S5735I-S48T4XE-V2(538049),
                Add: bname8031S5735I-H8T2XN-V2(538163),
                Add: bname8031S5735I-H8U2XN-V2(538164),
                Add: bname8031S5735I-S8U2XN-V2(538165),
                Add: bname8031S5735I-S48T4XE-V2(538224)"
         
    REVISION "202409070000Z"
      DESCRIPTION "V14.69,
        Add:bnameSPUG-USG-04        (16748998),      --00FF91C6
        Add:bnameSPUG-E9KE-04        (16748999),      --00FF91C7
        Add:fnameMPUA-USG6560F-D(16716203),    --00FF11AB
        Add:bnameMPUA-USG6560F-D(16749001),    --00FF91C9
        Add:fnameMPUA-Eudemon1000E-F06-D(16716204),    --00FF11AC
        Add:bnameMPUA-Eudemon1000E-F06-D(16749002),    --00FF91CA"

        REVISION "202409061710Z"
            DESCRIPTION "V21.01,
                Add:virent8090DEVIG2DVSUI80E2(359885),   -- V8R24C10 for IG2DVSUI80E2(SBOM) Integrated Service Unit 800 E(VSUI-800-E)"

        REVISION "202409051035Z"
            DESCRIPTION "V20.03,
            	Modify: fnameNETENGINE-8000-M14K-4AC(688400),       -- NETENGINE-8000-M14K-4AC (fnameNETENGINE-8000-M14K-4AC)
            	Modify: fnameNETENGINE-8000-M14K-2AC(688402),    -- NETENGINE-8000-M14K-2AC (fnameNETENGINE-8000-M14K-2AC)
            	Add: fnameNETENGINE-XH12000-X16-DC(688788),      -- Quidway fnameNETENGINE-XH12000-X16-DC for V8R24C10
				Add: fnameNETENGINE-XH12000-X16-HVDC(688789),    -- Quidway fnameNETENGINE-XH12000-X16-HVDC for V8R24C10
            	Add: virent8090DEVCR8D8MPUA1C1(364070),   -- V8R24C10 for CR8D8MPUA1C1(SBOM) NetEngine XH12000 Main Processing Unit A1A(MPUA1A)
                Add: virent8090DEVCR8D8MPUA2C1(364071),   -- V8R24C10 for CR8D8MPUA2C1(SBOM) NetEngine XH12000 Main Processing Unit A2A(MPUA2A)
                Add: virent8090DEVCR8D8SFU9TB1(364072),   -- V8R24C10 for CR8D8SFU9TB1(SBOM) NetEngine XH12000 X8 9.6Tbps Switch Fabric Unit(SFUIA-9T6-B)
                Add: virent8090DEVCR8D8LPF6TL1(364073),   -- V8R24C10 for CR8D8LPF6TL1(SBOM) Flexible Card Line Processing Unit L(LPUF-6T4-L)
                Add: virent8090DEVCR8D8LPF6TE1(364074),   -- V8R24C10 for CR8D8LPF6TE1(SBOM) Flexible Card Line Processing Unit E(LPUF-6T4-E)
                Add: virent8090DEVCR8D8SFU9TC1(364075),   -- V8R24C10 for CR8D8SFU9TC1(SBOM) NetEngine XH12000 X16 9.6Tbps Switch Fabric Unit(SFUIA-9T6-C)
                Add: virent8090DEVCR8DLPUF3TC3(364076),   -- V8R24C10 for CR8DLPUF3TC3(SBOM) Flexible Card Line Processing Unit(LPUF-3T2)            
                Add: virent8090DEVCR81IPU1T2A9S(219921),   -- V8R24C10 for CR81IPU1T2A9S(SBOM) Integrated Network Processing Unit (IPU-1T2-E)
                Add: virent8090DEVCR81IPU2TABS(219999),   -- V8R24C10 for CR81IPU2TABS(SBOM) Integrated Network Processing Unit (IPU-2T-E)
                Add: virent8090DEVCP8PHST2EA2C(525150),  --NetEngine A822 E AC Chassis (2*10GE/GE/FE(o)+4*GE/FE(o)+8*GE/FE(e))
                Add: virent8090DEVANPM01HOST8(525151),  --ATN 905-S System,AC,4*GE/FE(o),4*GE/FE(e)
                Add: virent8090DEVHGFM0HOSTE00(229553),           -- V8R23C00 for HGFM0HOSTE00(SBOM) HG-FM CPE-02-E AC Power,with 4*GE/FE(o),4*GE/FE(e),4*E1"
        
        REVISION "202409041135Z"
            DESCRIPTION "V20.02,
                Add: fnameLQC315L1(688333),           --LQC315-L1 Main Control Unit
                Add: fnameLingQu620V1(688334),        --LingQu620V1 Main Control Unit
                Add: bnameLQC315L1(688670),           --LQC315-L1 Main Control Unit
                Add: bnameLingQu620V1(688671),        --LingQu620V1 Main Control Unit"

        REVISION "202409041106Z"
            DESCRIPTION "V20.01,
                Add: bnameAR5710-S8T1XWE(668210),             --AR5710-S8T1XWE Main Control Unit
                Add: bnameAR5710-S8T1XWE-NRGL(668211),        --AR5710-S8T1XWE-NRGL Main Control Unit
                Add: bnameAR5710-S8P2XE-NRGL(668212),         --AR5710-S8P2XE-NRGL Main Control Unit
                Add: bnameAR5710-S8T2XE-NRGL(668213),         --AR5710-S8T2XE-NRGL Main Control Unit
                Add: bnameAR5710-S8T2S(668214),               --AR5710-S8T2S Main Control Unit
                Add: bnameSIC-NRGL-V2(668215),                --SIC-NRGL-V2 Lpu Control Unit
                Add: fnameAR5710-S8T1XWE(668089),              --AR5710-S8T1XWE Main Control Unit
                Add: fnameAR5710-S8T1XWE-NRGL(668090),         --AR5710-S8T1XWE-NRGL Main Control Unit
                Add: fnameAR5710-S8P2XE-NRGL(668091),          --AR5710-S8P2XE-NRGL Main Control Unit
                Add: fnameAR5710-S8T2XE-NRGL(668092),          --AR5710-S8T2XE-NRGL Main Control Unit
                Add: fnameAR5710-S8T2S(668093),                --AR5710-S8T2S Main Control Unit" 
 
 
        REVISION "202409021453Z"
            DESCRIPTION "V20.00,
                Modify: frombnameDEVPOWER(3706) to bnameDEVPOWER(229031),          -- Power module
                Modify: frombname8090DEVPOWERAC(561238) to bname8090DEVPOWERAC(229032),       -- AC/AC Power Module
                Modify: frombnameDP32PDC1K6A1(564506) to bnameDP32PDC1K6A1(229028),    --V8R13C00 NetEngine-8000-M14 DP32PDC1K6A1, M14
                Modify: frombnamePAC1K5S53-AL(564508) to bnamePAC1K5S53-AL(229030),    --V8R13C00 NetEngine-8000-M14 PAC1K5S53-AL, M14
                Modify: from bnameDP22PDC1K2A1(229013) to bnameDP22PDC1K2A1(229029),    --V8R22C00 NetEngine-8000-M4 DP22PDC1K2A1
                Add: bnameCX6X0PWRDC70(229033),        --CX600-X2 DC/DC Power Module
                Add: bnameCX6X0PWRAC70(229034),        --CX600-X2 AC/DC Power Module"

        REVISION    "202408310000Z"
            DESCRIPTION "V19.02,
                     Add: bnameC04Q40E(157013),                 --  Control and forwarding board of MC5101-C04Q40-E.
                     "

		REVISION    "202408280000Z"
			DESCRIPTION "V19.01,
                Add: virent8090DEVCR8PM1ABASDD(333126),     --V8R24C10 CR8PM1ABASDD(SBOM) NetEngine 8000E M1A, DC Power,Port Capacity 16*10GE+12*GE(o)+4*GE(e)
                Add: virent8090DEVCR8PM1ABASAD(333127),     --V8R24C10 CR8PM1ABASAD(SBOM) NetEngine 8000E M1A, AC Power,Port Capacity 16*10GE+12*GE(o)+4*GE(e)
                Add: virent8090DEVCR8PM1ABASDE(333128),     --V8R24C10 CR8PM1ABASDE(SBOM) NetEngine 8000E M1A, DC Power,Port Capacity 16*10GE+12*GE(o)+4*GE(e)
                Add: virent8090DEVCR8PM1ABASAE(333129),     --V8R24C10 CR8PM1ABASAE(SBOM) NetEngine 8000E M1A, AC Power,Port Capacity 16*10GE+12*GE(o)+4*GE(e)
                Add: virent8090DEVCR8PM1CBASAT(333130),     --V8R24C10 CR8PM1CBASAT(SBOM) NetEngine 8000E M1C, AC Power,Port Capacity 16*10GE+8*GE(o)+4*GE(e), None of the ports are available by default
                Add: virent8090DEVCR8PM1CBASD3(333131),     --V8R24C10 CR8PM1CBASD3(SBOM) NetEngine 8000E M1C, DC Power,Port Capacity 16*10GE+8*GE(o)+4*GE(e), None of the ports are available by default
                Add: virent8090DEVCR8PM1CBASAR(333132),     --V8R24C10 CR8PM1CBASAR(SBOM) NetEngine 8000E M1C, AC Power,Port Capacity 16*10GE+8*GE(o)+4*GE(e), None of the ports are available by default
                Add: virent8090DEVCR8PM1CBASD2(333133),     --V8R24C10 CR8PM1CBASD2(SBOM) NetEngine 8000E M1C, DC Power,Port Capacity 16*10GE+8*GE(o)+4*GE(e), None of the ports are available by default
                Add: virent8090DEVCR8PM1DBASD1(333134),     --V8R24C10 CR8PM1DBASD1(SBOM) NetEngine 8000E M1D, DC Power,Port Capacity 4*100GE/50GE+16*25GE/10GE/GE/FE+8*10GE/GE/FE,exclude auxiliary materials
                Add: virent8090DEVCR8PM1DBASA1(333135),     --V8R24C10 CR8PM1DBASA1(SBOM) NetEngine 8000E M1D, AC Power,Port Capacity 4*100GE/50GE+16*25GE/10GE/GE/FE+8*10GE/GE/FE,exclude auxiliary materials
                Add: virent8090DEVCR8PM1DBASA0(333136),     --V8R24C10 CR8PM1DBASA0(SBOM) NetEngine 8000E M1D, AC Power,Port Capacity 4*100GE/50GE+16*25GE/10GE/GE/FE+8*10GE/GE/FE,exclude auxiliary materials
                Add: virent8090DEVCR8PM1DBASD0(333137),     --V8R24C10 CR8PM1DBASD0(SBOM) NetEngine 8000E M1D, DC Power,Port Capacity 4*100GE/50GE+16*25GE/10GE/GE/FE+8*10GE/GE/FE,exclude auxiliary materials
                Add: subbnameCARDNetEngine8000EM1A(333138),    --NetEngine8000E M1A
                Add: subbnameCARDNetEngine8000EM1C(333139),    --NetEngine8000E M1C
                Add: subbnameCARDNetEngine8000EM1D(333140),    --NetEngine8000E M1D
                Add: fnameNETENGINE-8000E-M1A-AC(688710),
                Add: fnameNETENGINE-8000E-M1A-DC(688711),
                Add: fnameNETENGINE-8000E-M1C-AC(688712),
                Add: fnameNETENGINE-8000E-M1C-DC(688713),
                Add: fnameNETENGINE-8000E-M1D-AC(688714),
                Add: fnameNETENGINE-8000E-M1D-DC(688715),"

 		REVISION    "202408260000Z"
			DESCRIPTION "V19.00,
                Add: bnameHA01PDMB(148842),     --  Power board of MA5800T-X8.
                Add: bnameH908CSHF(148843),     --- 16*XGS combo board of MA5800.
                Add: bnameH909CGHF(148844),     --- 16*XGS combo board of MA5800.
                Add: bnameH908FLHF(148845),     --- 16*XGS combo board of MA5800.
                Add: bnameH905OGHK(148846),     --- 24/48 P2P board of MA5800.
                Add: bnameH908CSHFE(148847),    --- 16*XGS combo board of EA5800.
                Add: fname5800TX8HA01BPMA(148543),   -- Backplane of MA5800T-X8/EA5800T-X8.
                Add: fname5800TX15HA01BPIA(148544),  -- Backplane of MA5800T-X15.
                Add: fnameMA5801CG04H2(148545),      -- Backplane of MA5801.
                Add: bnameV921CGHC(148848),          -- 4*XG/G combo board of MA5801-CG04-H2.
            "
                        
        REVISION "202408220000Z"
            DESCRIPTION "V18.04,
                Add: fnameAirEngine5776I-X7H
                Add: fnameAirEngine5776-57T
	        	Add: fnameAirEngine5776-57
	        	Add: fnameAP761E
	        	Add: fnameAP271E"

        REVISION "202408201520Z"
            DESCRIPTION "V18.03,
                Add: fnameNETENGINE-XH861-AC(336971),        -- Quidway fnameNETENGINE-XH861-AC FRAME for V8R24C10
                Add: fnameNETENGINE-XH861-DC(336972),        -- Quidway fnameNETENGINE-XH861-DC FRAME for V8R24C10
                Add: fnameNETENGINE-XH861(336973),           -- Quidway fnameNETENGINE-XH861 FRAME for V8R24C10(AC+DC)
                Add: virent8090DEVANHMHSTA0204(359886),   -- V8R24C10 for ANHMHSTA0204(SBOM) NetEngine XH861, AC Power, Port Capacity 4*100GE/50GE+16*25GE/10GE/GE/FE+8*10GE/GE/FE, all the GE/FE ports is enabled
                Add: virent8090DEVANHMHSTA0104(359887),   -- V8R24C10 for ANHMHSTA0104(SBOM) NetEngine XH861, DC Power, Port Capacity 4*100GE/50GE+16*25GE/10GE/GE/FE+8*10GE/GE/FE, all the GE/FE ports is enabled
                Add: virent8090DEVANHMHSTA0334(359888),   -- V8R24C10 for ANHMHSTA0334(SBOM) NetEngine XH861, AC+DC Power, Port Capacity 4*100GE/50GE+16*25GE/10GE/GE/FE+8*10GE/GE/FE, all the GE/FE ports is enabled"

        REVISION "202408201020Z"
            DESCRIPTION "V18.02,
                Add: fname8031S6730S-S48X6Q-A1(538027), bname8031S6730S-S48X6Q-A1(538202),
                Add: fname8031S6730S-H48X6C-A1(538028), bname8031S6730S-H48X6C-A1(538203)"

        REVISION "202408191208Z"
            DESCRIPTION "V18.01,
                Add:fnameNETENGINE-8000E-M4-AC(688916),     -- V8R24C10 NETENGINE-8000E-M4-DC (fnameNETENGINE-8000E-M4-DC)
                Add:fnameNETENGINE-8000E-M4-DC(688917),     -- V8R24C10 NETENGINE-8000E-M4-DC (fnameNETENGINE-8000E-M4-DC)
                Add:virent8090DEVCR8PM4BASACD(883662),   -- V8R24C10 for CR8PM4BASACD(SBOM) NetEngine 8000E M4 Integrated AC Chassis Components(Including AC Power,Fan Box)
                Add:virent8090DEVCR8PM4BASACC(468719),   -- V8R24C10 for CR8PM4BASACC(SBOM) NetEngine 8000E M4 Integrated AC Chassis Components(Including AC Power,Fan Box)
                Add:virent8090DEVCR8PM4BASDCC(863701),   -- V8R24C10 for CR8PM4BASDCC(SBOM) NetEngine 8000E M4 Integrated DC Chassis Components(Including DC Power,Fan Box)
                Add:virent8090DEVCR8PM4BASDCD(992877),   -- V8R24C10 for CR8PM4BASDCD(SBOM) NetEngine 8000E M4 Integrated DC Chassis Components(Including DC Power,Fan Box)"

        REVISION "202408170850Z"
            DESCRIPTION "V17.02,
                Modify: from banme to bname"
        REVISION "202408161456Z"
            DESCRIPTION "V17.01,
                Add: bnameANOD000FAN00(564553),    --V8R24C10 ATN980E Fan Box"
        REVISION "202408132045Z"
            DESCRIPTION "V17.00,
                Modify: from bnameTNC1PIU(155701) to bnameTNCM000PIU00(155701),           -- power board of ATN931 Box type device
                Modify: from bnameATNANC1PIU(225295) to bnameANCD000PIU00(225295),           --Power board, 910 and 910I
                Modify: from bnameATNAND1PIU(225397) to bnameATNAND2PIU(225397),             --Power board, 950 and 950B
                Modify: from bnameATN910IPIU(225340) to bnameANCD00APIU00(225340),           --Power board, 910I-AC
                Modify: from bnameATNTNF5PIU(225342) to bnameANJ0000PIU00(225342),           --DC Power board, 980B
                Add: bnameANND000FAN00(229011),
                Add: bnameANTD000FAN00(229012),
                Add: bnamePDC260S12-CL(229014),
                Add: bnamePAC300S12-CL(229016),
                Add: bnameCR8MM60FBXC0(229017),
                Add: bnameTNRMM82FBXC1(229022),
                Add: bnameCX67FCBA(229023),
                Add: bnameCX67FCBB(229024),
                Add: bnameCX68FCBC(229025),
                Add: bnameEXTPOWER(229026),
                Add: bnameNECD001FAN00(229027),        --Fan board, 910 and 910I"

        REVISION "202408121527Z"
          DESCRIPTION "V16.05,
            Add:fnameNETENGINE-8000E-F1A(688790), --Quidway fnameNETENGINE-8000E-F1A FRAME for V8R24C10
            Add:fnameNETENGINE-8000E-F1A-C(688791),     --Quidway fnameNETENGINE-8000E-F1A-C FRAME for V8R24C10
            Add:fnameATNDEV980E-AC(229813),          --980E  chassis
            Add:fnameATNDEV980E-DC(229814),          --980E  chassis
            Add:fnameNETENGINE-XH16000-M14-DC(688914),  --Quidway fnameNETENGINE-XH16000-M14-DC FRAME for V8R24C10
            Add:fnameNETENGINE-XH16000-M14-2AC(688915), --Quidway fnameNETENGINE-XH16000-M14-2AC FRAME for V8R24C10
            Add:virent8090DEVANND03CXPA01(165928),   -- V8R24C10 for ANND03CXPA01(SBOM) System Control,Cross-connect and Multi-protocol Process Unit with 800G
            Add:virent8090DEVANND03CXPA02(165929),   -- V8R24C10 for ANND03CXPA02(SBOM) System Control,Cross-connect and Multi-protocol Process Unit with 1T6
            Add:virent8090DEVANND03CXPA03(165930),   -- V8R24C10 for ANND03CXPA03(SBOM) System Control,Cross-connect and Multi-protocol Process Unit with 2T4
            Add:virent8090DEVANOD00CXPA00(165931),   -- V8R24C10 for ANOD00CXPA00(SBOM) System Control,Cross-connect and Multi-protocol Process Unit with 2T4
            Add:virent8090DEVANOD00CXPA01(165932),   -- V8R24C10 for ANOD00CXPA01(SBOM) System Control,Cross-connect and Multi-protocol Process Unit with 800G
            Add:virent8090DEVANOD00CXPA02(165926),   -- V8R24C10 for ANOD00CXPA02(SBOM) System Control,Cross-connect and Multi-protocol Process Unit with 1T6
            Add:virent8090DEVANOD00CXPA03(165927),   -- V8R24C10 for ANOD00CXPA03(SBOM) System Control,Cross-connect and Multi-protocol Process Unit with 2T4
            Add:virent8090DEVCR8D0IPU3TM7(803818),   -- V8R24C10 for CR8D0IPU3TM7(SBOM) NetEngine XH16000 M14 Integrated Network Processing Unit (IPU-3T6-A)
            Add:virent8090DEVCR8D0SFUT6D3(441887),   -- V8R24C10 for CR8D0SFUT6D3(SBOM) NetEngine 8000E F 6T4 Switch Routing Unit(SRU-6T4-B)
            Add:virent8090DEVCR8DSFUIK0D2(441888),   -- V8R24C10 for CR8DSFUIK0D2(SBOM) NetEngine 8000E F 2T Switch Routing Unit(SRU-2T-A)
            Add:virent8090DEVCR8DMPUF8AF3(441889),   -- V8R24C10 for CR8DMPUF8AF3(SBOM) NetEngine 8000E F Main Processing Unit B2A(MPUB2)
            Add:virent8090DEVCR8B0BKP03D8(230970),   -- V8R24C10 for CR8B0BKP03D8(SBOM) NetEngine 8000E F1A Integrated Chassis Components(Port-side Intake)
            Add:virent8090DEVCR8B0BKP03D9(188350),   -- V8R24C10 for CR8B0BKP03D9(SBOM) NetEngine 8000E F1A Integrated Chassis Components(Port-side Exhaust)
            Add:virent8090DEVCR8B0BKP03DA(964754),   -- V8R24C10 for CR8B0BKP03DA(SBOM) NetEngine 8000E F1A Integrated Chassis Components(Port-side Intake)
            Add:virent8090DEVCR8B0BKP03DB(253627),   -- V8R24C10 for CR8B0BKP03DB(SBOM) NetEngine 8000E F1A Integrated Chassis Components(Port-side Exhaust)
            Add:virent8090DEVCR8B0BKP03E5(884337),   -- V8R24C10 for CR8B0BKP03E5(SBOM) NetEngine 8000E F1A-C Integrated Chassis Components(Port-side Intake)
            Add:virent8090DEVCR8B0BKP03E4(518968),   -- V8R24C10 for CR8B0BKP03E4(SBOM) NetEngine 8000E F1A-C Integrated Chassis Components(Port-side Intake)
            Add:virent8090DEVCR8B0BKP03E6(193036),   -- V8R24C10 for CR8B0BKP03E6(SBOM) NetEngine 8000E F1A-C Integrated Chassis Components(Port-side Intake, excluding Power)
            Add:virent8090DEVCR8D0IPU1T2MS(800026),  -- V8R24C10 for CR8D0IPU1T2MS(SBOM) Integrated Network Processing Unit (IPUA-1T2-E)
            Add:virent8090DEVCR8DIPU480ME(800027),   -- V8R24C10 for CR8DIPU480ME(SBOM) Integrated Network Processing Unit (IPU-480-E)
            Add:virent8090DEVCR8D0IPU1T2MR(800028),  -- V8R24C10 for CR8D0IPU1T2MR(SBOM) Integrated Network Processing Unit (IPU-1T2-E)
            Add:virent8090DEVCR8DIPU1T2M7(800029),   -- V8R24C10 for CR8DIPU1T2M7(SBOM) Integrated Network Processing Unit (IPU-1T2-AU)
            Add:virent8090DEVCR8DIPU2T4MC(800030),   -- V8R24C10 for CR8DIPU2T4MC(SBOM) Integrated Network Processing Unit (IPU-2T4-A)
            Add:virent8090DEVCR8DIPU1T2M8(800031),   -- V8R24C10 for CR8DIPU1T2M8(SBOM) Integrated Network Processing Unit (IPU-1T2-E-BU)
            Add:virent8090DEVCR8DIPU2T4MD(800032),   -- V8R24C10 for CR8DIPU2T4MD(SBOM) Integrated Network Processing Unit (IPU-2T4-E-B)
            Add:subbname8090DEVIG2D0LJXX0CP(513269),   -- 36-Port 10GBase LAN/WAN-SFP Flexible Card(P1T)
            Add:subbname8090DEVIG2D0E5NBCCP(513233),   -- 5-Port 100GBase-QSFP28 FlexE MACsec Flexible Card(P1T)"

    REVISION "202408120000Z"
      DESCRIPTION "V16.04,
        Add:fnameMPUA-USG6000F-S115(16716201),    --00FF11A9
        Add:bnameMPUA-USG6000F-S115(16748996),    --00FF91C4
        Add:fnameMPUA-USG6000F-S125(16716202),    --00FF11AA
        Add:bnameMPUA-USG6000F-S125(16748997),    --00FF91C5"

        REVISION "202408081000Z"
        DESCRIPTION "V16.03,
          The object identifier of S5735-L48PN4XE-A-V2 to S5735R-L48P4X-A-V2 is add." 
       
        REVISION "202408071700Z"
          DESCRIPTION "V16.03,
            The object identifier of AR502H-LTE4AU-V2 is added,
            The object identifier of AR502H-LTE4CN-V2 is added,
            The object identifier of AR502H-LTE4EA-V2 is added."

        REVISION "202408071410Z"
		  DESCRIPTION "V15.37,
            Add: virent8090DEVCR5D00E4LB61(562302),    -- V8R24C10 for CR5D00E4LB61(SBOM) 4-Port 800GBase QSFP-DD Integrated Line Process Unit(NE5000E LPUI-3T2-E)"

        REVISION "202408061045Z"
		  DESCRIPTION "V15.36,
            Modify: bnameGM110SDI(688633) -> bnameGM110NIC(688633), 
            Modify: fnameGM110SDI(688310) -> fnameGM110NIC(688310), "

        REVISION "202408011045Z"
		  DESCRIPTION "V15.35,
            Add: fnameAR6140E-L14T2X4-V2(668085),          --AR6140E-L14T2X4-V2 FRAME
            Add: bnameAR6140E-L14T2X4-V2(668206),          --AR6140E-L14T2X4-V2 Main Control Unit"
         
		REVISION "202407271128Z"
		  DESCRIPTION "V15.34,
			Add:fnameNETENGINE-8000E-F8A(688700),    -- Quidway fnameNETENGINE-8000E-F8A FRAME for V8R24C10
			Add:virent8090DEVCR8DMPUF8AB1(560450),   -- V8R24C10 for CR8DMPUF8AB1(SBOM) NetEngine 8000E F Main Processing Unit B2A(MPUB2A)
			Add:virent8090DEVCR8DLPUF3TE1(359884),   -- V8R24C10 for CR8DLPUF3TE1(SBOM) Flexible Card Line Processing Unit E(LPUF-3T2-E)
			Add:virent8090DEVCR8DLPUF3TC1(718758),   -- V8R24C10 for CR8DLPUF3TC1(SBOM) Flexible Card Line Processing Unit(LPUF-3T2)
            Add:virent8090DEVCR8DLPUF3TL1(673964),   -- V8R24C10 for CR8DLPUF3TL1(SBOM) Flexible Card Line Processing Unit L(LPUF-3T2-L)
            Add:virent8090DEVCR8D8LPU3TE1(743906),   -- V8R24C10 for CR8D8LPU3TE1(SBOM) Flexible Card Line Processing Unit E(LPUF-3T2-E)
            Add:virent8090DEVCR8D8LPU3TC1(113208),   -- V8R24C10 for CR8D8LPU3TC1(SBOM) Flexible Card Line Processing Unit(LPUF-3T2)
            Add:virent8090DEVCR8D8LPF3TL1(678178),   -- V8R24C10 for CR8D8LPF3TL1(SBOM) Flexible Card Line Processing Unit L(LPUF-3T2-L)
            Add:virent8090DEVCR8DLPUF3TM2(516642),   -- V8R24C10 for CR8DLPUF3TM2(SBOM) Flexible Card Line Processing Unit E(LPUF-3T2A-E)
            Add:virent8090DEVCR8DLPUF3TD3(737819),   -- V8R24C10 for CR8DLPUF3TD3(SBOM) Flexible Card Line Processing Unit(LPUF-3T2A)
            Add:virent8090DEVCR8DLPUF3TL2(108614),   -- V8R24C10 for CR8DLPUF3TL2(SBOM) Flexible Card Line Processing Unit L(LPUF-3T2A-L)
            Add:virent8090DEVCR8DLPUF3TE2(953479),   -- V8R24C10 for CR8DLPUF3TE2(SBOM) Flexible Card Line Processing Unit E(LPUF-3T2-E)
            Add:virent8090DEVCR8DLPUF3TC2(400248),   -- V8R24C10 for CR8DLPUF3TC2(SBOM) Flexible Card Line Processing Unit(LPUF-3T2)
            Add:virent8090DEVCR8DLPUF3TF2(584451),   -- V8R24C10 for CR8DLPUF3TF2(SBOM) Flexible Card Line Processing Unit L(LPUF-3T2-L)
			Add:virent8090DEVCR8D0IPU2TM3(759613),   -- V8R24C10 for CR8D0IPU2TM3(SBOM) Integrated Network Processing Unit (IPUA-2T-E)
            Add:virent8090DEVCR8DIPU1T2M9(993660),   -- V8R24C10 for CR8DIPU1T2M9(SBOM) Integrated Network Processing Unit (IPUA-1T2-E)"

        REVISION "202407261115Z"
          DESCRIPTION "V15.33,
          Add:fnameUSG12000-H6          (16716192),    --00FF11A0
          Add:fnameAntiDDoS12000-H6          (16716193),    --00FF11A1
          Add:fnameIPS12000-H6          (16716194),    --00FF11A2
          Add:fnameEudemon1000E-C0    (16716195),    --00FF11A3
          Add:fnameEudemon1000E-M0    (16716196),    --00FF11A4
          Add:fnameEudemon1000E-S0    (16716197),    --00FF11A5
          Add:fnameUSG6636F        (16716198),      --00FF11A6
          Add:fnameUSG6656F        (16716199),      --00FF11A7
          Add:fnameUSG6686F        (16716200),      --00FF11A8

          Delete:bname-PDC240S12-CN       (16748993),    --00FF9222

          Add:bnameLPUG-U-16CQ24XS    (16748979),      --00FF9214
          Add:bnameLPUG-I-16CQ24XS    (16748980),      --00FF9215
          Add:bnameLPUG-U-8CQ24XS	    (16748981),      --00FF9216
          Add:bnameLPUG-I-8CQ24XS	    (16748982),      --00FF9217
          Add:bnameSPUG-USG-03        (16748983),      --00FF9218
          Add:bnameSPUG-DDOS-03       (16748984),      --00FF9219
          Add:bnameSPUG-IPS-03        (16748985),      --00FF922A
          Add:bnameSPUG-USG-02        (16748986),      --00FF922B
          Add:bnameSPUG-DDOS-02       (16748987),      --00FF922C
          Add:bnameSPUG-IPS-02        (16748988),      --00FF922D
          Add:bnameMPUA-USG-H6        (16748989),      --00FF922E
          Add:bnameMPUA-USG-H6-T      (16748990),      --00FF922F
          Add:bnameSPUG-DDOS-04       (16748991),      --00FF9220
          Add:bnameSPUG-IPS-04        (16748992),      --00FF9221
          Add:bnameMPUA-USG6636F        (16748993),      --00FF91C1
          Add:bnameMPUA-USG6656F        (16748994),      --00FF91C2
          Add:bnameMPUA-USG6686F        (16748995),      --00FF91C3"

		REVISION "202407251005Z"
          DESCRIPTION "V15.32,
            Add: fnameNETENGINE-8000E-M14-Z-4AC(688903),  -- NETENGINE-8000E-M14-Z-4AC (fnameNETENGINE-8000E-M14-Z-4AC)
            Add: fnameNETENGINE-8100-M14-2AC(688902),    -- NETENGINE-8100-M14-2AC (fnameNETENGINE-8100-M14-2AC)
            Add: virent8090DEVANND02CXPAQ1(228006),  -- V8R24C10 ATN 980C,ANN3CXPA21,System Control,Cross-connect and Multi-protocol Process Unit with 800G
            Add: virent8090DEVANND02CXPAQ2(228007),  -- V8R24C10 ATN 980C,ANN3CXPA11,System Control,Cross-connect and Multi-protocol Process Unit with 360G
            Add: fnameSIG16000-X4-DC(688910),       -- Quidway fnameSIG16000-X4-DC for V8R24C10
            Add: fnameSIG16000-X4-HVDC(688911),     -- Quidway fnameSIG16000-X4-HVDC for V8R24C10
            Add: fnameSIG16000-X8-DC(688912),       -- Quidway fnameSIG16000-X8-DC for V8R24C10
            Add: fnameSIG16000-X8-HVDC(688913),     -- Quidway fnameSIG16000-X8-HVDC for V8R24C10
            Add: virent8090DEVIG2D0MPUAXCA(165919),   -- V8R24C10 for IG2D0MPUAXCA(SBOM) SIG16000 Main Processing Unit A10A(MPUA10A)
            Add: virent8090DEVIG2DSFUI2TD1(165920),   -- V8R24C10 for IG2DSFUI2TD1(SBOM) SIG16000 X4 2Tbps Switch Fabric Unit(SFUIA-2T-A)
            Add: virent8090DEVIG2D8SFU9TD0(165921),   -- V8R24C10 for IG2D8SFU9TD0(SBOM) SIG16000 X4 9.6Tbps Switch Fabric Unit(SFUIA-9T6-D)
            Add: virent8090DEVIG2DSFUI2TD2(165922),   -- V8R24C10 for IG2DSFUI2TD2(SBOM) SIG16000 X8 2Tbps Switch Fabric Unit(SFUIA-2T-B)
            Add: virent8090DEVIG2DSFUI9TB1(165923),   -- V8R24C10 for IG2DSFUI9TB1(SBOM) SIG16000 X8 9.6Tbps Switch Fabric Unit(SFUIA-9T6-B)
            Add: virent8090DEVIG2DLPUFT072(165924),   -- V8R24C10 for IG2DLPUFT072(SBOM) Flexible Card Line Processing Unit (LPUF-1TA)
            Add: virent8090DEVIG2D8LPU3TC1(165925),   -- V8R24C10 for IG2D8LPU3TC1(SBOM) Flexible Card Line Processing Unit(LPUF-3T2)"

		REVISION "202407251005Z"
          DESCRIPTION "V15.31,
            Add: fnameCE6857S48S6CQ(688332),
            Add: bnameCE6857S48S6CQ(688669),	"
			
          REVISION "202407241005Z"
          DESCRIPTION "V15.30,
            Add: fnameAR617(668083),                       --AR617 FRAME
            Add: fnameAR617-LTE4EA(668084),                --AR617-LTE4EA FRAME
            Add: bnameAR617(668204),                       --AR617 Main Control Unit
            Add: bnameAR617-LTE4EA(668205),                --AR617-LTE4EA Main Control Unit"
            

    REVISION "202407231606Z"
            DESCRIPTION "V15.29,
                Add: virent8090DEVCR5D00E8KB65(562300),    -- V8R24C00 for CR5D00E8KB65(SBOM) 8-Port 400GBase QSFP-DD Integrated Line Process Unit CM(NE5000E LPUI-3T2-D-CM)
                Add: virent8090DEVCR5D00EINB65(562301),    -- V8R24C00 for CR5D00EINB65(SBOM) 32-Port 100GBase QSFP28 Integrated Line Process Unit CM(NE5000E LPUI-3T2-D-CM)"
		 
		 REVISION "202407221000Z"
         DESCRIPTION "V15.28,
            Add: fname8031S5731I-L8T2SN(537976),
            Add: fname8031S5731I-L8T2S2XN(537977),
            Add: fname8031S5731I-L8P2S2XN(537978),
            Add: fname8031S5731I-L16T2S2XN(537979),
            Add: bname8031S5731I-L8T2SN(538159),
            Add: bname8031S5731I-L8T2S2XN(538160),
            Add: bname8031S5731I-L8P2S2XN(538161),
            Add: bname8031S5731I-L16T2S2XN(538162)"
		 
		 REVISION "202407181000Z"
         DESCRIPTION "V15.27,
            Add: fnameXH9330128EO(688331),
			Add: bnameXH9330128EO(688668)"
			  		  
		    REVISION "202407151000Z"
			DESCRIPTION "V15.26,
			  ADD: virent8090DEVANHMHSTA5600(689138),   -- V8R24C00 for ANHMHSTA5600(SBOM) ATN 910D-A, DC Power, Port Capacity 2*100GE/50GE+8*25GE/10GE/GE/FE+16*10GE/GE/FE, default all the GE/FE ports is enabled
              ADD: virent8090DEVANHMHSTA5601(689139),   -- V8R24C00 for ANHMHSTA5601(SBOM) ATN 910D-A, AC Power, Port Capacity 2*100GE/50GE+8*25GE/10GE/GE/FE+16*10GE/GE/FE, default all the GE/FE ports is enabled"
            REVISION "202407131000Z"
              DESCRIPTION "V15.25,
              Add: bnamePTN7900TPD1FHL4(229697),   --TPD1FHL4,4-Port 400 Gigabit ethernet switching flexe service processing board,1*1,"
            REVISION "202407081500Z"
            DESCRIPTION "V15.24,
	        Add:subbnamePICL1HROH(720896),
		Add:subbnamePICL1HUB(720897),
		Add:subbnamePICL1ROH(720898),
		Add:subbnamePICL2ROH(720899),
		Add:subbnamePICL2UB(720900),
	        Add:subbnamePICL2HCCS(720901),
		Add:subbnamePICL3ROH(720902),
		Add:subbnamePICL3UB(720903),
		Add:subbnamePICL4ROH(720904),
		Add:subbnamePICL4UB(720905),
	        Add:subbnamePICTGL2ROH(720906),
		Add:subbnamePICTGL2HCCS(720907),
		Add:subbnamePICGGXC511L1A1(720908),
		Add:subbnamePICGGXC511L1A2(720909),
		Add:subbnamePICGGXC511L1B1(720910),
		Add:subbnamePICGGXC511L1B2(720911),
		Add:subbnamePICBUX510HCCS(720912),
	        Add:subbnamePICBUX510UB(720913),
		Add:subbnamePICEVBROH(720914),
		Add:subbnamePICEVBHCCS(720915),
		Add:subbnamePICEVBUB(720916),
                Add:subbnamePICL1HCCS(720917),
		Add:portnameROHPORTF200G(692224),
		Add:portnameROHPORTE200G(692225),
		Add:portnameR2EPORTE200G(692226),
            	Add:portnameR2EPORTF200G(692227),
		Add:portnameHCCSPORTF200G(692228),
		Add:portnameHCCSPORTE200G(692229),
		Add:portnameUBGPORTF200G(692230),
                Add:portnameUBGPORTE200G(692231),
                Add:portnameUBG2EPORTE200G(692232),
                Add:portnameUBG2EPORTF200G(692233),"
	 REVISION "202407081400Z"
            DESCRIPTION "V15.23,
	    Modify:AirEngine5562-17W-V2(692501)"
				
		REVISION "202406271400Z"
            DESCRIPTION "V15.22,
                ADDsubbnameAirEngine5762C-10-V2(692470),
                subbnameAirEngine5562-10-V2(692471),
                subbnameAirEngine3562-10-M(692472),
                subbnameAirEngine3562-10-T(692473),
                subbnameAirEngine5762C-10SW-V2(692474),
                subbnameAirEngine5562-10SW-V2(692475),
                subbnameAirEngine3562-10SW-M(692476),
                subbnameAirEngine3562-10SW-T(692477),
                subbnameeKitEngine5763S-11(692478),
                subbnameeKitEngine5763S-12(692479),
                subbnameAP361E(692480),
                subbnameeKitEngine5763S-12SW(692481),
                subbnameeKitEngine6760S-56(692482),
                subbnameAirEngine5773-23W(692483),
                subbnameAirEngine6776I-X6ETH(692484),
                subbnameAirEngine5573-23W(692485),
                subbnameAirEngine5576I-X6EH(692486),
                subbnameeKitEngine5773S-21(692487),
                subbnameeKitEngine5776RS-X6(692488),
                subbnameAP673E(692489),
                subbnameAP572(692490),
                subbnameAP772(692491),
                subbnameAP772E(692492),
                subbnameAirEngine6776-X6H(692493),
                subbnameAirEngine6776-X6ETH(692494),
                subbnameAirEngine5776-56T(692495),
                subbnameAirEngine5776I-X6H(692496),
                subbnameAirEngine5776I-X6EH(692497),
                subbnameAirEngine6776-58TI-K(692498),
                subbnameAirEngine6776I-X6ETH-K(692499),
				subbnameAirEngine5762C-17W-V2(692500),
				subbnamegine5562-17W-V2(692501),
				"

		REVISION "202406241400Z"
            DESCRIPTION "V15.21,
                ADD:subbnameXH90D32CQF(688167),
                Modify:fnameLCN5000IT51XCUAHPCL1 (688286)->fnameLQG311-L1 (688286),
                Modify:fnameLCN5000IT51XCUBAIL1 (688287)->fnameLQU311-L1 (688287), 
                Modify:fnameLCN500032CQ8DQ (688288)->fnameLQG311-L2 (688288), 
                Modify:fnameLCN5000IT51XCLBL2HCCS (688289)->fnameLQC311-L2 (688289), 
                Modify:fnameLCN5000IT51XCUCL3 (688290)->fnameLQG311-L3 (688290), 
                Modify:fnameLCN5000IT51XCLBL4 (688291)->fnameLQG311-L4 (688291)
                
                Modify:bnameLCN5000IT51XCUAHPCL1 (688584)->bnameLQG311-L1 (688584),
                Modify:bnameLCN5000IT51XCUBAIL1 (688585)->bnameLQU311-L1 (688585),
                Modify:bnameLCN500032CQ8DQ (688586)->bnameLQG311-L2 (688586),
                Modify:bnameLCN5000IT51XCLBL2HCCS (688587)->bnameLQC311-L2 (688587), 
                Modify:bnameLCN5000IT51XCUCL3 (688588)->bnameLQG311-L3 (688588), 
                Modify:bnameLCN5000IT51XCLBL4 (688589)->bnameLQG311-L4 (688589)"

		
		REVISION "202406201200Z"
            DESCRIPTION "V15.20,
                Modify: virent8090DEVCR8DLPUFT6L4(165894),   -- V8R24C00 for CR8DLPUFT6L4(SBOM) Flexible Card Line Processing Unit L(LPUF-6T4-L)
                Modify: virent8090DEVCR8DLPUFT6E4(165896),   -- V8R24C00 for CR8DLPUFT6E4(SBOM) Flexible Card Line Processing Unit E(LPUF-6T4-E)
                Modify: virent8090DEVCR8DLPUFT6LA(165897),   -- V8R24C00 for CR8DLPUFT6LA(SBOM) Flexible Card Line Processing Unit L(LPUF-6T4A-L)
                Modify: virent8090DEVCR8DLPUFT6EA(165899),   -- V8R24C00 for CR8DLPUFT6EA(SBOM) Flexible Card Line Processing Unit E(LPUF-6T4A-E)
                Modify: virent8090DEVCR8D8LPF6TC0(165900),   -- V8R24C00 for CR8D8LPF6TC0(SBOM) Flexible Card Line Processing Unit (LPUF-6T4)
                Modify: virent8090DEVCR8D8LPF6TE0(165901),   -- V8R24C00 for CR8D8LPF6TE0(SBOM) Flexible Card Line Processing Unit E(LPUF-6T4-E)"

        REVISION "202406131200Z"
            DESCRIPTION "V15.19,
               Add:hwPhysicalBoardModuleH901MPLH(148840),     --- MPLH main board.
               "

		 REVISION "202406062045Z"
            DESCRIPTION "V15.18,
                Add:subbname8090DEVCR8DE8YBMSF0(549693),     --  8-Port 25GE(SFP28)/10GE(SFP+) MACsec Physical Interface Card (PIC)
                Add:subbname8090DEVCR8DE8YBMSF1(549694),     --  8-Port 25GE(SFP28)/10GE(SFP+) MACsec Physical Interface Card (PIC)
			    Add:subbname8090DEVCR8DL8EFFEC1(549696),     --  8-Port 10GE LAN/WAN-SFP+ FlexE MACsec Physical Interface Card(PIC)
                Add:subbname8090DEVCR8D00L8XFD1(549698),     --  8-Port 10GE LAN/WAN-SFP+ FlexE MACsec Physical Interface Card(PIC)
                Add:subbname8090DEVCR8D00L8XFD0(549697),     --  8-Port 10GE LAN/WAN-SFP+ FlexE MACsec Physical Interface Card(PIC)
			    Add:subbname8090DEVGFL1KQGA(549679),        -- 1-Port 400GBase-QSFP-DD Interface Card(PIC)
                Add:subbname8090DEVGFL8CQGA(549678),        -- 8-Port 100GBase-QSFP28 Interface Card(PIC)
                Add:subbname8090DEVGFL4CQ40XSGA(549677),   -- 4-Port 100GBase-QSFP28 + 40-port 10GE/GE LAN/WAN-SFP+ Interface Card(PIC)
                Add:subbname8090DEVGFL2KQGA(549783),            -- 2-Port 400GBase-QSFP-DD Interface Card(PIC)
                Add:subbname8090DEVGFL72XSGBA(549676),      -- 72-port 10GE MACsec Physical Interface Card(PIC)"
				
      REVISION "202406052045Z"
            DESCRIPTION "V15.17,
                Add: bnameCR8M004FBXC0(564552),    --V8R24C00 NetEngine 8000 M4 Fan Box
                Add:virent8090DEVCP8PHST2EA15(525145),   -- V8R24C00 for CP8PHST2EA15(SBOM) NetEngine A831 E DC Chassis(3*10G/GE/FE(o)+7*GE/FE(o)+4*GE/FE(e))
                Add:virent8090DEVCP8PHST2EA14(689137),   -- V8R24C00 for CP8PHST2EA14(SBOM) NetEngine A812 E-S DC Chassis(10*GE/FE(o)+4*GE/FE(e))"

        REVISION "202406051136Z"
            DESCRIPTION "V15.16,
                Add: fname and bname for S220S-8T2J to S530-48S4XE"

	 REVISION "202406031136Z"
            DESCRIPTION "V15.15,
                Modify: fnameNETENGINE-XH821-AC(154341),       -- V8R24C00 for NETENGINE-XH821-AC chassis
                Modify: fnameNETENGINE-XH821-E-AC(154351),     -- V8R24C00 for NETENGINE-XH821-E-AC chassis"

        REVISION "202405281136Z"
            DESCRIPTION "V15.14,
                Add: subbname8090DEVCR8DFA0E00M1(548790),      -- 4-Port FXS/FXO + 2-Port E&M + 2-Port RS232 + 2-Port RS485 Physical Interface Card(PIC)
                Add: subbname8090DEVCR8DFA0E00M2(548791),      -- 4-Port FXS/FXO + 2-Port E&M + 2-Port RS232 + 2-Port RS485 Physical Interface Card(PIC)
                Add: subbname8090DEVCR5D00E1ND7A(513232),   -- 1-Port 100GBase-QSFP28 Flexible Card A(P246-A)
                Add: subbname8090DEVCR5D00E1ND7B(513234),   -- 1-Port 100GBase-QSFP28 Flexible Card A(P246-A)
                Add: subbname8090DEVCR5D00E1ND7C(513235),   -- 1-Port 100GBase-QSFP28 Flexible Card A(P246-A)
                Add: subbname8090DEVME03E1NBJ0(513236),     -- 1-Port 100GBase-QSFP28 Flexible Card A(BP246-A)
                Add: subbname8090DEVGPR16KQ56CQS(226960),     -- 16-Port 400GBase-QSFPDD + 56-Port 100GBase-QSFP28
                Add: subbname8090DEVCR8DE4KEDNL0(709810),     -- 4-Port 400GBase-QSFP-DD + 16-Port 100GBase-QSFP28 FlexE Flexible Card L CM(P6T4-L-CM,400GE Port Enabled with 100GE by default)
                Add: subbname8090DEVCR8DE4KEDND0(709811),     -- 4-Port 400GBase-QSFP-DD + 16-Port 100GBase-QSFP28 FlexE Flexible Card CM(P6T4-CM,400GE Port Enabled with 100GE by default)
                Add: subbname8090DEVCR8DE4KEDNE0(709812),     -- 4-Port 400GBase-QSFP-DD + 16-Port 100GBase-QSFP28 FlexE Flexible Card E CM(P6T4-E-CM,400GE Port Enabled with 100GE by default)
                Add: subbname8090DEVCR8D84KEDNL0(709813),     -- 4-Port 400GBase-QSFP-DD + 16-Port 100GBase-QSFP28 FlexE Flexible Card L CM(P6T4-L-CM,400GE Port Enabled with 100GE by default)
                Add: subbname8090DEVCR8D84KEDNC0(709814),     -- 4-Port 400GBase-QSFP-DD + 16-Port 100GBase-QSFP28 FlexE Flexible Card CM(P6T4-CM,400GE Port Enabled with 100GE by default)
                Add: subbname8090DEVCR8D84KEDNE0(709815),     -- 4-Port 400GBase-QSFP-DD + 16-Port 100GBase-QSFP28 FlexE Flexible Card E CM(P6T4-E-CM,400GE Port Enabled with 100GE by default)
                Add: subbname8090DEVCR8DE4KEDND1(709816),     -- 4-Port 400GBase-QSFP-DD + 16-Port 100GBase-QSFP28 FlexE Flexible Card CM(P6T4-CM,400GE Port Enabled with 100GE by default)
                Add: subbname8090DEVCR8DE4KEDND9(709817),     -- 4-Port 400GBase-QSFP-DD + 16-Port 100GBase-QSFP28 FlexE Flexible Card CM(P6T4-CM,400GE Port Enabled with 100GE by default)
                Add: subbname8090DEVCR59EFNBA0(709800),     --  24-Port 100GBase QSFP28
                Add: subbname8090DEVCR59EFNBA1(709801),     --  24-Port 100GBase QSFP28
                Add: subbname8090DEVCR59EAKBA0(709802),     --  10-Port 400GBase QSFP-DD
                Add: subbname8090DEVCR59EAKBA1(709803),     --  10-Port 400GBase QSFP-DD
                Add: subbname8090DEVCR5D0LAXFE7P(513240),   -- 10-Port 10GBase LAN/WAN-SFP+ MACsec Flexible Card(P246-A)
                Add: subbname8090DEVCR5D0LAXFE7Q(513241),   -- 10-Port 10GBase LAN/WAN-SFP+ MACsec Flexible Card(P246-A)
                Add: subbname8090DEVCR5D0LAXFE7R(513242),   -- 10-Port 10GBase LAN/WAN-SFP+ MACsec Flexible Card(P246-A)
                Add: subbname8090DEVME0D0LAXFH7K(513243),   -- 10-Port 10GBase LAN/WAN-SFP+ MACsec Flexible Card(P246-A)
			    Add: virent8090DEVCR8DE1KB00F1(548784),            -- 1-Port 400GBase-QSFP-DD Combined Line Processing Unit CM Basic Setup Bundle(Including LPUC-400-CM, default enable 100G)
                Add: virent8090DEVCR8DE8NB00F1(548785),            -- 8-Port 100GBase-QSFP28 Combined Line Processing Unit(LPUC-800-CM)
                Add: virent8090DEVCR8DEKNBXFF1(548786),            -- 4-Port 100GBase-QSFP28 + 40-port 10GE/GE LAN/WAN-SFP+ Combined Line Processing Unit(LPUC-800-CM)
                Add: virent8090DEVCR8DE2KB00F1(548787),            -- 2-Port 400GBase-QSFP-DD Combined Line Processing Unit(LPUC-800-CM)
                Add: virent8090DEVCR8DERXFMSF1(548788),            -- 72-port 10GE/GE LAN/WAN-SFP+ MACsec Combined Line Processing Unit(LPUC-800-CM)
                Add: subbname8090DEVME0D00L1NB7K(548789),            -- 1-Port 100GBase-QSFP28 Flexible Card A(BP246-A)
                Add: subbname8090DEVCR8DE8YF0026(513244),            -- 8-Port 25GE(SFP28)/10GE(SFP+)  Physical Interface Card (PIC)
                Add: subbname8090DEVCR8DE8EFFEC2(513245),            -- 8-Port 10GE-SFP+ FlexE Physical Interface Card(PIC)
                Add: subbname8090DEVCR8DE8YF0025(513246),            -- 8-Port 10GE-SFP+ FlexE Physical Interface Card(PIC)
                Add: subbname8090DEVCR8DE8EFFEC1(513247),            -- 8-Port 10GE-SFP+ FlexE Physical Interface Card(PIC)
                Add: subbname8090DEVCR8DG80E00M1(513248),            -- 10-Port C37.94 Physical Interface Card(PIC)
                Add: subbname8090DEVCR8DG80E00M2(513249),            -- 10-Port C37.94 Physical Interface Card(PIC)
                Add: subbname8090DEVCR8DE00E8KL0(513237),            -- 8-Port 400GBase-QSFP-DD FlexE MACsec Flexible Card L CM(P6T4-L-CM,400GE Port Enabled with 100GE by default)
                Add: subbname8090DEVCR8DE00E8KN0(513238),            -- 8-Port 400GBase-QSFP-DD FlexE MACsec Flexible Card CM(P6T4-CM,400GE Port Enabled with 100GE by default)
                Add: subbname8090DEVCR8DE00E8KE0(513239),            -- 8-Port 400GBase-QSFP-DD FlexE MACsec Flexible Card E CM(P6T4-E-CM,400GE Port Enabled with 100GE by default)
                Add: subbname8090DEVCR8DE6LEJKXA(709804),            -- 6-Port 800GBase-QSFP-DD + 36-Port 400GBase-QSFP-DD Integrated Line Processing Unit CM(LPUIA-19T2-CM,Enable 6*400GE + 36*100GE by default)"

      REVISION "202405270924Z"
            DESCRIPTION "V15.13,
                Add:virent8090DEVCR5DVSUIK096(688696),    -- V8R24C00 for CR5DVSUIK096(SBOM) Integrated Service Unit(SAC)
                Add:virent8090DEVCR5DVSUIK097(688697),    -- V8R24C00 for CR5DVSUIK097(SBOM) Integrated Service Unit(SAC-E)
                Add:virent8090DEVME0DVSUIK096(688698),    -- V8R24C00 for ME0DVSUIK096(SBOM) Integrated Service Unit(SAC)
                Add:virent8090DEVME0DVSUIK097(688699),    -- V8R24C00 for ME0DVSUIK097(SBOM) Integrated Service Unit(SAC-E)"

      REVISION "202405252045Z"
            DESCRIPTION "V15.12,
                Add: bnameCP8MM60FBXC0(564551),    --V8R24C00 NetEngine A835 T Fan Box"

	REVISION "202405251049Z"
            DESCRIPTION "V15.11,               
            ADD:fnameXH90304C(688315) to fnameLingQu630V1(688330),
			ADD:bnameCEXSFU16GH2(688650) to bnameLingQu630V1(688667),"
		 
    REVISION "202405211656Z"
            DESCRIPTION "V15.10,
                Add:virent8090DEVTPND02CXPC00(932127),   -- V8R24C00 for TPND02CXPC00(SBOM) OptiX PTN 980, TPN2CXPC, System Control,Cross-connect and Multi-protocol Process Unit
		Add:virent600DEVCR8B0BKP03E3(688691),    -- V8R24C00 NetEngine-8000-F1A CR8B0BKP03E3(SBOM), F1A-C"
	
    REVISION "202405201049Z"
            DESCRIPTION "V15.09,               
                Modify:fnameAC650-512AP(692463),   --wlan
				       bnameAC650-512AP(692463),   --wlan"

    REVISION "202405200949Z"
            DESCRIPTION "V15.08,               
                Add:bnameSIC-NREA-V2(668203),            --SIC-NREA-V2 Lpu Control Unit"
                
    REVISION "202405172045Z"
            DESCRIPTION "V15.07,
                Add: bnameCR8MM82FBXC3(564549),    --V8R24C00 NetEngine 8000 M8 CR8MM82FBXC3, M8
                Add: bnameTNRMM82FBXC3(564550),    --V8R24C00 PTN6900-2-M8C TNRMM82FBXC3, M8"

    REVISION "202405151929Z"
            DESCRIPTION "V15.06,
                Add: virent8090DEVCR8DIPU2T4M1(165911),   -- V8R24C00 for CR8DIPU2T4M1(SBOM) Integrated Network Processing Unit (IPU-2T4-A)
                Add: virent8090DEVCR8DIPU1T2MA(165912),   -- V8R24C00 for CR8DIPU1T2MA(SBOM) Integrated Network Processing Unit (IPU-1T2-AU)
                Add: virent8090DEVCR8DIPU2T4M2(165913),   -- V8R24C00 for CR8DIPU2T4M2(SBOM) Integrated Network Processing Unit (IPU-2T4-E-B)
                Add: virent8090DEVCR8DIPU1T2MB(165914),   -- V8R24C00 for CR8DIPU1T2MB(SBOM) Integrated Network Processing Unit (IPU-1T2-E-BU)
                Add: virent8090DEVTNRDIPU2T4M1(165915),   -- V8R24C00 for TNRDIPU2T4M1(SBOM) Integrated Network Processing Unit (IPU-2T4-A)
                Add: virent8090DEVTNRDIPU1T2M1(165916),   -- V8R24C00 for TNRDIPU1T2M1(SBOM) Integrated Network Processing Unit (IPU-1T2-AU)
                Add: virent8090DEVTNRDIPU2T4M2(165917),   -- V8R24C00 for TNRDIPU2T4M2(SBOM) Integrated Network Processing Unit (IPU-2T4-E-B)
                Add: virent8090DEVTNRDIPU1T2M2(165918),   -- V8R24C00 for TNRDIPU1T2M2(SBOM) Integrated Network Processing Unit (IPU-1T2-E-BU)"
   
    REVISION "202405141929Z"
            DESCRIPTION "V15.05,
                Add: bnameCR8MM60FBXC2(564548),    --V8R24C00 NetEngine-8000E-M6 CR8MM60FBXC2, M6"

    REVISION "202405080949Z" 
            DESCRIPTION "V15.04
                Modify: virent8090DEVCR8DSFU19TA0(896523),   -- V8R24C00 for CR8DSFU19TA0(SBOM) NetEngine 8000 X4 19.2Tbps Switch Fabric Unit(SFUI-19T2-A)
                Modify: virent8090DEVCR8DSFU19TB0(896524),   -- V8R24C00 for CR8DSFU19TB0(SBOM) NetEngine 8000 X8 19.2Tbps Switch Fabric Unit(SFUI-19T2-B)
                Add: virent8090DEVCR8DSFU14TD0(896525),   -- V8R24C00 for CR8DSFU14TD0(SBOM) NetEngine 8000 X16 14.4Tbps Switch Fabric Unit(SFUI-14T4-D)
                Add: virent8090DEVCR8DSFU14TD0A(896526),   -- V8R24C00 for CR8DSFU14TD0A(SBOM) NetEngine 8000 X16 14.4Tbps Switch Fabric Unit(SFUIA-14T4-D)
                Add: virent8090DEVCR8DSFU19TA0A(896527),   -- V8R24C00 for CR8DSFU19TA0A(SBOM) NetEngine 8000 X4 19.2Tbps Switch Fabric Unit(SFUIA-19T2-A)
                Add: virent8090DEVCR8DSFU19TB0A(896528),   -- V8R24C00 for CR8DSFU19TB0A(SBOM) NetEngine 8000 X8 19.2Tbps Switch Fabric Unit(SFUIA-19T2-B)
                Add:virent8090DEVHGFM0HOSTF01(564547),           -- V8R24C00 for HGFM0HOSTF01(SBOM) HG-FM CPE-02-S AC Power,with 4*GE/FE(o),4*GE/FE(e),includes auxiliary materials
                Add:fnameHG-FM-CPE-02-S-AC(229722),              -- V8R24C00 for HG-FM-CPE-02-S chassis
                Add: virent8090DEVCP8PHST3A00(284791),   -- V8R24C00 for CP8PHST3A00(SBOM) NetEngine XH821 AC Chassis(A) ((2*10GE/GE/FE(o)+4*GE(o)(default 4*GE,RTU can be upgrade to 4*10GE)+4*GE/FE(o)+8*GE/FE(e)
                Add: virent8090DEVCP8PHST3EA00(284792),   -- V8R24C00 for CP8PHST3EA00(SBOM) NetEngine XH821 E AC Chassis(A) (6*10GE/GE/FE(o)+4*GE/FE(o)+8*GE/FE(e), Default 2*10GE/GE/FE(o)+8*GE/FE(o)+8*GE/FE(e))
                Add: fnameNETENGINE-XH-A821-AC(154341),       -- V8R24C00 for NETENGINE-XH-A821-AC chassis
                Add: fnameNETENGINE-XH-A821-E-AC(154351),     -- V8R24C00 for NETENGINE-XH-A821-E-AC chassis
				Add: fnameNETENGINE-XH12000-X8-DC(688689),      -- Quidway fnameNETENGINE-XH12000-X8-DC for V8R24C00
			    Add: fnameNETENGINE-XH12000-X8-HVDC(688690),    -- Quidway fnameNETENGINE-XH12000-X8-HVDC for V8R24C00
			    Add: fnameNETENGINE-XH8000E-X8-DC(688687),      -- Quidway fnameNETENGINE-XH8000E-X8-DC for V8R24C00
			    Add: fnameNETENGINE-XH8000E-X8-HVDC(688688),    -- Quidway fnameNETENGINE-XH8000E-X8-HVDC for V8R24C00
			    Add: virent8090DEVCR8D0MPUAXC5(364028),   		-- V8R24C00 for CR8D0MPUAXC5(SBOM) NetEngine XH12000 Main Processing Unit A10B(MPUA10B)
			    Add: virent8090DEVCR8D0MPUAXC9(364029),			-- V8R24C00 for CR8D0MPUAXC9(SBOM) NetEngine XH8000E Main Processing Unit A10B(MPUA10B)
			    Add: virent8090DEVCR8DSFUI9TB2(678752),         -- V8R24C00 for CR8DSFUI9TB2(SBOM) NetEngine XH12000 X8 9.6Tbps Switch Fabric Unit(SFUIA-9T6-B)
			    Add: virent8090DEVCR8DSFUI9TB9(678753),         -- V8R24C00 for CR8DSFUI9TB9(SBOM) NetEngine XH8000E X8 9.6Tbps Switch Fabric Unit(SFUIA-9T6-B)
			    Add: virent8090DEVCR8DLPUFT6TB(165909),         -- V8R24C00 for CR8DLPUFT6TB(SBOM) Flexible Card Line Processing Unit(LPUF-6T4B)
			    Add: virent8090DEVCR8XLPUFT6TA(165910),         -- V8R24C00 for CR8XLPUFT6TA(SBOM) Flexible Card Line Processing Unit(LPUF-6T4A)"
		
		REVISION "202405060949Z" 
            DESCRIPTION "V15.03
                Add:fnameNETENGINE-8000E-M6-AC(225356),  -- Quidway fnameNETENGINE-8000E-M6-AC FRAME for V8R24C00
                Add:fnameNETENGINE-8000E-M6-DC(225357),  -- Quidway fnameNETENGINE-8000E-M6-DC FRAME for V8R24C00
                Add:virent8090DEVCR8DCXP160C4(689140),   -- V8R24C00 for CR8DCXP160C4(SBOM) System Control,Cross-connect and Multi-protocol Process Unit (CXP-160-C)
                Add:virent8090DEVCR8DCXP160C5(689141),   -- V8R24C00 for CR8DCXP160C5(SBOM) System Control,Cross-connect and Multi-protocol Process Unit (CXPA-160-C)
                Add:virent8090DEVCR8DCXP160C8(689142),   -- V8R24C00 for CR8DCXP160C8(SBOM) System Control,Cross-connect and Multi-protocol Process Unit (CXPA-160-C),High anti-corrosion"

        REVISION "202404301530Z"
            DESCRIPTION "V15.02,
                Add: virent8090DEVCR5D00EEKBC0(562143),    -- V8R24C00 for CR5D00EEKBC0(SBOM) NetEngine5000E 20-Port 400GBase QSFP-DD Integrated Line Process Unit(NE5000E LPUI-8T)
                Modify: virent8090DEVCR5D00EEKBC1(562144),    -- V8R24C00 for CR5D00EEKBC1(SBOM) NetEngine5000E 20-Port 400GBase QSFP-DD Integrated Line Process Unit CM(NE5000E LPUI-8T-CM) (5 ports enable)
                Modify: virent8090DEVCR5D00EEKBC2(562145),    -- V8R24C00 for CR5D00EEKBC2(SBOM) NetEngine5000E 20-Port 400GBase QSFP-DD Integrated Line Process Unit Liquid Cooling(NE5000E LPUI-8T-L)"

        REVISION "202404292035Z"
            DESCRIPTION "V15.01,
                Add: virent8090DEVCR5D00EEKBC0(562144),    -- V8R24C00 for CR5D00EEKBC0(SBOM) NetEngine5000E 20-Port 400GBase QSFP-DD Integrated Line Process Unit(NE5000E LPUI-8T)
                Add: virent8090DEVCR5D00EEKBC1(562145),    -- V8R24C00 for CR5D00EEKBC1(SBOM) NetEngine5000E 20-Port 400GBase QSFP-DD Integrated Line Process Unit CM(NE5000E LPUI-8T-CM) (5 ports enable)
                Add: virent8090DEVCR5DSFUIT460(562146),    -- V8R24C00 for CR5DSFUIT460(SBOM) NE5000E-20 8T CLC Switch Fabric Unit for Single Chassis(SFU-8T-S)
                Add: virent8090DEVCR5DSFUIT461(562147),    -- V8R24C00 for CR5DSFUIT461(SBOM) NE5000E-20 8T CLC Switch Fabric Unit for Single Chassis Liquid Cooling(SFU-8T-S-L)
                Add: virent8090DEVCR5D00EMNBC0(562148),    -- V8R24C00 for CR5D00EMNBC0(SBOM) NetEngine5000E 48-Port 100GBase QSFP28 Integrated Line Process Unit(NE5000E LPUI-8T)
                Add: virent8090DEVCR5D00EMNBC1(562149),    -- V8R24C00 for CR5D00EMNBC1(SBOM) NetEngine5000E 48-Port 100GBase QSFP28 Integrated Line Process Unit CM(NE5000E LPUI-8T-CM)(12 ports enable)
                Add: virent8090DEVCR5D00EMNBC2(562150),    -- V8R24C00 for CR5D00EMNBC2(SBOM) NetEngine5000E 48-Port 100GBase QSFP28 Integrated Line Process Unit Liquid Cooling(NE5000E LPUI-8T-L)"

		REVISION "202404241200Z"
            DESCRIPTION "V15.00,
				Add: bnameH901HTED(148837),          -- 8*50GPON board of MA5800."
 
		REVISION "202404201501Z"
            DESCRIPTION "V14.99,
				Add: virent8090DEVANPM001AICT9(215895),   -- V8R24C00 for ANPM001AICT9(SBOM) ATN 905-L System,AC,4*GE/FE(o),4*GE/FE(e)(without SRv6 and IFIT)
                Add: fnameNETENGINE-8100-X8-12T8-DC(689564),   --Quidway fnameNETENGINE-8100-X8-12T8-DC for V8R24C00"
 
        REVISION "202404191045Z"
            DESCRIPTION "V14.98,
                Add: virent8090DEVCR5DLPUFM39D(172860),   -- V8R24C00 for CR5DLPUFM39D(SBOM) Flexible Card Line Processing Unit(LPUF-483D)"
                
        REVISION "202404181045Z"
            DESCRIPTION "V14.97,
                Add: virent8090DEVCR5D0MPUV1D0(567017),           -- V8R24C00 for NE5000E-20 Main Processing Unit V(MPUV)
                Add: virent8090DEVCR5D0MPUV1D1(567018),           -- V8R24C00 for NE5000E-20 Main Processing Unit V Liquid Cooling(MPUV-L)"

        REVISION    "202404180000Z"
        DESCRIPTION "V14.96,
           Add: fnameGM111MERGE(688314) .
           Add: bnameGM111MERGE(688649)."    

        REVISION    "202404170000Z"
        DESCRIPTION "V14.95,
                    Add: bnameHE01MCSA(148835),          -- control board of MA5800-X2.
                    Add: bnameHE01LXSG(148836),          -- 24*10GE board of MA5800.
					"
		 
		REVISION "202404071544Z"
            DESCRIPTION "V14.94,
                Add: subbnameCARDATN910CS60G(333120),         --ATN910C-S-60G virtual card,6*10GE(o), 2*10GE /GE/FE(o),4*GE/FE(e)
                Add: subbname8090DEV905-L(115928),            --CARD ATN 905-L
                Add: subbname8090DEVNetEngine-A816(115929),   --CARD NetEngine A816
                Add: subbname8090DEVNetEngine-A816-E(115930), --CARD NetEngine A816 E
                Add: subbname8090DEVANNDE1NBFM01(548799),      --1-Port 100GBase/50GBase-QSFP28 FlexE MACsec+8-Port 10GE(SFP+)/GE(SFP) MACsec Physical Interface Card(PIC)"

 
 REVISION "202403301600Z"
        DESCRIPTION "V7.56,
	    The object identifier of AirEngine5773-23HWP is renamed AirEngine5773-23WP,
            The object identifier of AirEngine5773-25HWP is renamed AirEngine5773-25HW,
	    The object identifier of AP160E is renamed AP162E,
	    The object identifier of AP265 is removed,
	    The object identifier of AP361E is renamed AP362E,
	    The object identifier of AirEngine6776-58T is renamed AirEngine 6776-58Ti,
	    "		 
		REVISION "202403292129Z"
            DESCRIPTION "V14.92,
                Add: virent8090DEVCR8B0BKP2CF1(165903),   -- V8R24C00 for CR8B0BKP2CF1(SBOM) Integrated Chassis Components(Port-side Intake)
                Add: virent8090DEVCR8B0BKP2CF2(165904),   -- V8R24C00 for CR8B0BKP2CF2(SBOM) Integrated Chassis Components(Port-side Exhaust)
                Add: virent8090DEVCR8B0BKP2CF7(165905),   -- V8R24C00 for CR8B0BKP2CF7(SBOM) Integrated Chassis Components(Port-side Intake)
                Add: virent8090DEVCR8B0BKP2CF8(165906),   -- V8R24C00 for CR8B0BKP2CF8(SBOM) Integrated Chassis Components(Port-side Exhaust)
                Add: virent8090DEVCR8B0BKP2CF3(165907),   -- V8R24C00 for CR8B0BKP2CF3(SBOM) Integrated Chassis Components(Port-side Intake)
                Add: virent8090DEVCR8B0BKP2CF4(165908),   -- V8R24C00 for CR8B0BKP2CF4(SBOM) Integrated Chassis Components(Port-side Exhaust)
                Add: fnameNETENGINE-8000-F2C(688889),     --Quidway fnameNETENGINE-8000-F2C  FRAME for V8R24C00
                Add: fnameNETENGINE-8000E-F2C(688909),    --Quidway fnameNETENGINE-8000E-F2C  FRAME for V8R24C00"
                
		
		REVISION "202403292129Z"
            DESCRIPTION "V14.91,
                Add: bnameH838XPUB(156106),   -- Master board of MA582xS-G01"
		
                REVISION "202403271743Z"
            DESCRIPTION "V14.90,
                Add: portnameDCDE01RJ4525GE(688149),     -- The port with 25G BASE-T type"
		
		REVISION "202403262140Z"
            DESCRIPTION "V14.88,
                Add: fnamePTN7900TPH1CHASSIS(229700),   --PTN 7900F-32 Integrated Chassis Components"
		
                REVISION "202403220944Z"
            DESCRIPTION "V14.88,
                Add: fnameNETENGINE-8000E-M14-4AC(688899),  -- NETENGINE-8000E-M14-4AC (fnameNETENGINE-8000E-M14-4AC)"
		
		REVISION "202403201100Z"
              DESCRIPTION "V14.87,
               Add: bnamePTN7900TPH1EG24(229811), --TPH1EG24, 24-Port GE/FE adaptive ethernet service processing board
			   "
		
		REVISION    "202403201000Z"
        DESCRIPTION "V14.86,
           Add: ARPDC240S12-CN(668202),     --Power Card, 240W DC"
        
		REVISION    "202403182000Z"
        DESCRIPTION "V14.85,
					Add: bnamePDC240S12-CN(16748993),   -- Assembling Components,subnamePDC240S12-CN ,
					MODIFY:bnamePAC80S12-CN(16748963),   -- Assembling Components,subnamePAC80S12-CN "
		     REVISION "202403181929Z"
            DESCRIPTION "V14.84,
                Add: bnameTNRM002FBXC3(564544),    --V8R23C10 PTN6900-M4 TNRM002FBXC3
                Add: bnameCR5M002FBXC3(564545),    --V8R23C10 NE40E-M14 CR5M002FBXC3
                Add: bnameCR8M002FBXC4(564546),    --V8R23C10 NE8000E M14 CR8M002FBXC4"

		REVISION    "202403181200Z"
        DESCRIPTION "V14.83,
					Add: subnamePAH3KS54-CF(16748978),   -- Assembling Components,subnamePAH3KS54-CF."
		REVISION    "202403141200Z"
        DESCRIPTION "V14.82,
					Add: bnameH901HTHD(148838),          -- 8*50GPON board of MA5800.
			        Add: bnameH901ATHD(148839),          -- 8*50GPON board of MA5800.
			        Add: bnameHA01CILA(148840),          -- GPIO board of MA5800T.
                    "

                REVISION "202403141100Z"
            DESCRIPTION "V14.81,
               Add: subbnameLCN5000IT51XCUAHPCL1PICROH,        (720896)
               Add :subbnameLCN5000IT51XCUBAIL1PICROH,            (720897)
               Add: subbnameLCN5000IT51XCUBAIL1PICHCCS,          (720898)
               Add: subbnameLCN500032CQ8DQPICROH,                    (720899)
               Add: subbnameLCN5000IT51XCLBL2PICROH,                (720900)
               Add: subbnameLCN5000IT51XCLBL2PICHCCS,              (720901)
               Add: subbnameLCN5000IT51XCUCL3PICROH,               (720902)
               Add: subbnameLCN5000IT51XCLBL4PICROH,                (720903)"

		REVISION "202403120900Z"
            DESCRIPTION "V14.80,
               Add: virent8090DEVANPM001AICT5(215891),   -- V8R24C00 for ANPM001AICT5(SBOM) Customer Premise Equipment,ATN 905-L System,AC,4*GE/FE(o),4*GE/FE(e)
               Add: virent8090DEVCP8PHST10A13(215892),   -- V8R24C00 for CP8PHST10A13(SBOM) Customer Premise Equipment,NetEngine A816 AC System (4*GE/FE(o)+4*GE/FE(e), includes advanced features and auxiliary materials)
               Add: virent8090DEVCP8PHST2EA53(215893),   -- V8R24C00 for CP8PHST2EA53(SBOM) NetEngine A816 E Basic Configuration(Includes A816 E Chassis(A),Fixed Interface, 4*GE/FE (o),4*GE/FE (e), no software or doc, with auxiliary materials)
               Add: virent8090DEVCP8PHST2EA54(215894),   -- V8R24C00 for CP8PHST2EA54(SBOM) NetEngine A816 E Basic Configuration(Includes A816 E Chassis,Fixed Interface,4*GE/FE (o),4*GE/FE (e), no software or doc, with auxiliary materials)
               Add: fnameNetEngineA816-E-AC(229701),     -- V8R24C00 for NetEngineA816-E-AC chassis
               Add: fnameATN905-L-AC(229711),            -- V8R24C00 for ATN905-L-AC chassis
               Add: fnameNetEngineA816-AC(229721),       -- V8R24C00 for NetEngineA816-AC chassis"
		
		REVISION "202403110900Z"
            DESCRIPTION "V14.79,
             Add: subbnamePDC400S12CF(688166),"

		 
		REVISION "202403071600Z"
            DESCRIPTION "V14.78,
             Add: fnameAR5710-S28T2S2XE4(668081),           --AR5710-S28T2S2XE4 FRAME       
             Add: fnameAR5710-S52T2XE4(668082),             --AR5710-S52T2XE4 FRAME 
             Add: bnameAR5710-S28T2S2XE4(668200),          --AR5710-S28T2S2XE4 Main Control Unit    
             Add: bnameAR5710-S52T2XE4(668201),            --AR5710-S52T2XE4 Main Control Unit"

		REVISION "202403071000Z"
            DESCRIPTION "V14.77,
                Add: bnameCESFU16GH2(688637) to bnameCEX8L48CQJ2(688648).
                Del: subbnameCE98D8DQX(688162) and subbnameCE98D32CQX(688163).
                Modify: bnameCEL12DQJ(688625) -> bnameCEL18DQJ(688625).
                Modify: bnameCEXL12DQJ(688627)-> bnameCEXL18DQJ(688627)."
				
        REVISION "202403061000Z"
            DESCRIPTION "V14.76,
                The object identifier of S5735I-S8T8P2S4XN-V2 is added.
                The object identifier of S5735I-S16T2S4XN-V2 is added."

         REVISION "202403020000Z"
           DESCRIPTION "V14.75,
             Add: fname8031S6750-S16X8YZ(537901),             --S6750-S16X8YZ        
             Add: fname8031S6750-S24T16X8Y2CZ(537902),        --S6750-S24T16X8Y2CZ   
             Add: fname8031S6750-S16X10Y2CZ(537903),           --S6750-S16X10Y2CZ      
             Add: fname8031S5755-H24HB2Y2CZ(537904),          --S5755-H24HB2Y2CZ     
             Add: fname8031S6730-H6FX4Y2CZ-V2(537905),        --S6730-H6FX4Y2CZ-V2   
             Add: fname8031S5735-L24T8J4XE-A-V2(537906),      --S5735-L24T8J4XE-A-V2 
             Add: fname8031S5735-S24T8J4XE-XA-V2(537907),     --S5735-S24T8J4XE-XA-V2
             Add: fname8031S5735-S24T4XEZ-V2(537908),         --S5735-S24T4XEZ-V2    
             Add: fname8031S5735-S24T8J4XEZ-V2(537909),       --S5735-S24T8J4XEZ-V2  
             Add: fname8031S5735-S24P4XEZ-V2(537910),         --S5735-S24P4XEZ-V2    
             Add: fname8031S5735-S24P8J4XEZ-V2(537911),       --S5735-S24P8J4XEZ-V2  
             Add: fname8031S5735-S48T4XE-XA-V2(537912),       --S5735-S48T4XE-XA-V2  
             Add: fname8031S5735-S48T4XEZ-V2(537913),         --S5735-S48T4XEZ-V2    
             Add: fname8031S5735-S48P4XEZ-V2(537914),         --S5735-S48P4XEZ-V2    
             Add: fname8031S5535-S48HS4XE-V2(537915),         --S5535-S48HS4XE-V2    
             Add: fname8031S5335-L24T4S-A-V2(537916),         --S5335-L24T4S-A-V2    
             Add: fname8031S5335-L24P4S-A-V2(537917),         --S5335-L24P4S-A-V2    
             Add: fname8031S5755-H48T4Y2CZ-B(537918),         --S5755-H48T4Y2CZ-B    
             Add: fname8031S5535-S48PN4XE-V2(537919),         --S5535-S48PN4XE-V2    
             Add: fname8031S5535-S24PN4XE-V2(537920),         --S5535-S24PN4XE-V2    
             Add: fname8031S6780-H4Z(537921),                 --S6780-H4Z            
             Add: fnameLE5BS9304XE0(659482),              --S9300XE-4 assembly chassis
             Add: fnameLE5BS9308XE0(659483),              --S9300XE-8 assembly chassis
             Add: bname8031S6750-S16X8YZ(538084),             --S6750-S16X8YZ        
             Add: bname8031S6750-S24T16X8Y2CZ(538085),        --S6750-S24T16X8Y2CZ   
             Add: bname8031S6750-S16X10Y2CZ(538086),           --S6750-S16X10Y2CZ
             Add: bname8031S5755-H24HB2Y2CZ(538087),          --S5755-H24HB2Y2CZ     
             Add: bname8031S6730-H6FX4Y2CZ-V2(538088),        --S6730-H6FX4Y2CZ-V2   
             Add: bname8031S5735-L24T8J4XE-A-V2(538089),      --S5735-L24T8J4XE-A-V2 
             Add: bname8031S5735-S24T8J4XE-XA-V2(538090),     --S5735-S24T8J4XE-XA-V2
             Add: bname8031S5735-S24T4XEZ-V2(538091),         --S5735-S24T4XEZ-V2    
             Add: bname8031S5735-S24T8J4XEZ-V2(538092),       --S5735-S24T8J4XEZ-V2  
             Add: bname8031S5735-S24P4XEZ-V2(538093),         --S5735-S24P4XEZ-V2    
             Add: bname8031S5735-S24P8J4XEZ-V2(538094),       --S5735-S24P8J4XEZ-V2  
             Add: bname8031S5735-S48T4XE-XA-V2(538095),       --S5735-S48T4XE-XA-V2  
             Add: bname8031S5735-S48T4XEZ-V2(538096),         --S5735-S48T4XEZ-V2    
             Add: bname8031S5735-S48P4XEZ-V2(538097),         --S5735-S48P4XEZ-V2    
             Add: bname8031S5535-S48HS4XE-V2(538098),         --S5535-S48HS4XE-V2    
             Add: bname8031S5335-L24T4S-A-V2(538099),         --S5335-L24T4S-A-V2    
             Add: bname8031S5335-L24P4S-A-V2(538100),         --S5335-L24P4S-A-V2    
             Add: bname8031S5755-H48T4Y2CZ-B(538101),         --S5755-H48T4Y2CZ-B    
             Add: bname8031S5535-S48PN4XE-V2(538102),         --S5535-S48PN4XE-V2    
             Add: bname8031S5535-S24PN4XE-V2(538103),         --S5535-S24PN4XE-V2    
             Add: bname8031S6780-H4Z(538104),                 --S6780-H4Z            
             Add: bnameLSG3C16QX1E0(659765), --16-port 40GBASE-X interface card(QSFP+) or 8-port 100GBASE-X interface card(QSFP28)
             Add: bnameLSG3X48SX2E0(659766), --48-port 100M/1G/10GBASE-X interface card (SFP+)                                    
             Add: bnameLSG3SRUFX500(659767), --S9300XE-8 main control unit F                                                      
             Add: bnameLSG3SRUEX500(659768), --S9300XE-4 main control unit E                                                      
             Add: bnameLSG3C16QX1E0(659769), --16-port 40GBASE-X interface card(QSFP+) or 8-port 100GBASE-X interface card(QSFP28)
             Add: bnameLSG3C04HX1E0(659770), --4-port 100GBASE-X interface card(QSFP28)                                           
             Add: bnameLSG3X72SX1E0(659771), --72-port 100M/1G/10GBASE-X interface card (SFP+)                                    
             Add: bnameLSG3X48SX2E0(659772), --48-port 100M/1G/10GBASE-X interface card (SFP+)                                    
             Add: bnameLSG3X24SX1E0(659773), --24-port 100M/1G/10GBASE-X interface card (SFP+)                                    
             Add: bnameLSG3G48SX1E0(659774), --48-port 100/1000BASE-X interface card (SFP)                                        
             Add: bnameLSG3G48TX1E0(659775), --48-port 10/100/1000BASE-T interface card (RJ45)                                    
             Add: bnameLSG7C08HX1E0(713517),   --8-port 100GBASE-X interface card(QSFP28)                                           
             Add: bnameLSG7C32QX1E0(713518),   --32-port 40GBASE-X interface card(QSFP+)                                            
             Add: bnameLSG7C16HX1E0(713516),   --16-port 100GBASE-X interface card(QSFP28)                                          
             Add: bnameLSG7C16QX1E0(713519),   --16-port 40GBASE-X interface card(QSFP+) or 8-port 100GBASE-X interface card(QSFP28)
             Add: bnameLSG7C16BX1E0(713521),   --8-port 100G/40GBASE-X and 8-port 40GBASE-X interface card(QSFP28/QSFP+)            
             Add: bnameLSG7X48SX2E0(713520),   --48-port 100M/1G/10GBASE-X interface card (SFP+)                                      
             Add: bnameLSH7SFUCX200(713740), --S16700-4 Switch Fabric Unit C (X2)                                                                                        
             Add: bnameLSH7SFUJX200(713741), --S16700-8 Switch Fabric Unit C (X2)                                                                                        
             Add: bnameLSH7Y52BX2E0(713742), --40-port 25G/10G/GE Ethernet Optics and 4-port 100G/40GE Ethernet Optics, or 48-port 25G/10G/GE Ethernet (X2E, SFP+/QSFP28)
             Add: bnameLSH7X52BX2E0(713743), --40-port 10GE/GE Ethernet optical and 4-port 40GE Ethernet optical, or 48-port 10GE/GE Ethernet optical (X2E, SFP+/QSFP28) 
             Add: bnameLSH7C24HX2E0(713744), --24-Port 100G Optical Interface Card (X2E, QSFP28)                                                                         
             Add: bnameLSH7C36HX2E0(713745), --36-Port 100G Optical Interface Card (X2E, QSFP28)                                                                         
             Add: bnameLSH7D18DX2E0(713746), --18-Port 400G Optical Interface Card (X2E, QSFP-DD)                                                                         
             Add: subnameHSIC-Y08S000(536834)      --HSIC-Y08S000 (8-port 25GE SFP28 interface card)                                                              
             Add: subnameHSIC-X08S000(536835)      --HSIC-X08S000 (8-port 25GE/10GE SFP28 interface card(1/2/3/4 support 25GE))                                   
             Add: subnameXSIC-M26B000(536836)      --XSIC-M26B000 (card with 24*GE/2.5G/5G/10GBase-T ports and 2*40GE/100GE QSFP28 ports)                         
             Add: subnameXSIC-X26B000(536837)      --XSIC-X26B000 (card with 24*10GE SFP+ ports and 2*100GE QSFP28 ports)                                         
             Add: subnameXSIC-Y26B000(536838)      --XSIC-Y26B000 (card with 24*25GE SFP28 ports and 2*100GE QSFP28 ports)                                        
             Add: subnameXSIC-C10H000(536839)      --XSIC-C10H000 (card with 10*100GE QSFP28 ports)                                                               
             Add: subnameXSIC-L16Q000(536840)      --XSIC-L16Q000 (card with 16*40GE QSFP+ ports)                                                                 
             Add: subnameXSIC-C16H000(536841)      --XSIC-C16H000 (card with 16*100GE QSFP28 ports)                                                               
             Add: subnameXSIC-D12B000(536842)      --XSIC-D12B000 (card with 8*25GE SFP28 ports and 4*400GE QSFP-DD ports)                                        
             Add: subnamePDC400S12-CB(536843)      --Function Module,DC PSU,PDC400S12-CB,400W DC Power Module(Rear Front Air Passage, Power Panel Side Air Outlet)
             Add: subnamePDC240S12-CN(536844)      --Function Module,DC PSU,PDC240S12-CN,240W DC Power Module"
         REVISION "202403011929Z"
              DESCRIPTION "V14.74,
                Add: bnameCR8M002FBXC3(564543),    --V8R23C10 NetEngine-8000-M14 CR8M002FBXC3, M14
                "
         REVISION "202403011729Z"
              DESCRIPTION "V14.73,
               Add: virent8090DEVCR8DLPUFT6E4(165894),   -- V8R24C00 for CR8DLPUFT6E4(SBOM) Flexible Card Line Processing Unit E(LPUF-6T4-E)
               Add: virent8090DEVCR8DLPUFT6T4(165895),   -- V8R24C00 for CR8DLPUFT6T4(SBOM) Flexible Card Line Processing Unit (LPUF-6T4)
               Add: virent8090DEVCR8DLPUFT6L4(165896),   -- V8R24C00 for CR8DLPUFT6L4(SBOM) Flexible Card Line Processing Unit L(LPUF-6T4-L)
               Add: virent8090DEVCR8DLPUFT6EA(165897),   -- V8R24C00 for CR8DLPUFT6EA(SBOM) Flexible Card Line Processing Unit E(LPUF-6T4A-E)
               Add: virent8090DEVCR8DLPUFT6TA(165898),   -- V8R24C00 for CR8DLPUFT6TA(SBOM) Flexible Card Line Processing Unit(LPUF-6T4A)
               Add: virent8090DEVCR8DLPUFT6LA(165899),   -- V8R24C00 for CR8DLPUFT6LA(SBOM) Flexible Card Line Processing Unit L(LPUF-6T4A-L)
               Add: virent8090DEVCR8D8LPF6TE0(165900),   -- V8R24C00 for CR8D8LPF6TE0(SBOM) Flexible Card Line Processing Unit E(LPUF-6T4-E)
               Add: virent8090DEVCR8D8LPF6TC0(165901),   -- V8R24C00 for CR8D8LPF6TC0(SBOM) Flexible Card Line Processing Unit (LPUF-6T4)
               Add: virent8090DEVCR8D8LPF6TL0(165902),   -- V8R24C00 for CR8D8LPF6TL0(SBOM) Flexible Card Line Processing Unit L(LPUF-6T4-L)
			         "
        REVISION "202402271729Z"
              DESCRIPTION "V14.72,
               Add: bnamePTN7900TPH1FH8(229803), --TPH1FH8, 8-port 100 Gigabit Ethernet Switching Processing Board
			   Add: bnamePTN7900TPH1EX24S(229804), --TPH1EX24S, 24-port 10 Gigabit Ethernet Switching Processing Board
			   Add: bnamePTN7900TPH1FH2(229805), --TPH1FH2, 2-port 100 Gigabit Ethernet Switching Processing Board
			   Add: bnamePTN7900TPH1FH4(229806), --TPH1FH4, 4-port 100 Gigabit Ethernet Switching Processing Board
			   Add: bnamePTN7900TPH1FGU(229807), --TPH1FGU, Fine Granularity Unit Functional Board
			   Add: bnamePTN7900TPH1XCS(229808), --TPH1XCS, Switch Fabric Unit,1*1
			   Add: bnamePTN7900TPH1SCA(229809), --TPH1SCA,System Control, Communication and Auxiliary Processing Unit,1*1
			   Add: bnamePTN7900TPF1XCSD(229810),   --TPF1XCSD, Switch Fabric Unit,1*1
			   "

        REVISION "202402261400Z"
              DESCRIPTION "V14.71,
               Add: subbname AP371"

        REVISION    "202402231733Z"
        DESCRIPTION "V14.70,
                    Add: subbname8090DEVCR59LJXFD(709799),      -- 36-Port 10GBase LAN/WAN-SFP+ Fixed Daughter Card
                    "
        
        REVISION    "202402200000Z"
        DESCRIPTION "V14.69,
                    Add: subbnameHA01CKSA(148527),        -- CLock subboard of MA5800T.
                    "
					
            REVISION    "202402192020Z"
              DESCRIPTION "V14.68           
                add: bnameDP5U2K4APIU(564540),     --V8R23C10 NetEngine-8000-M DP5U2K4APIU
                add: bnameAPIU3000W(564541),     --V8R24C00 NetEngine-8000-F8 APIU3000W
                add: bnameF2CPIU(564542),     --V8R24C00 NetEngine-8000-F2 F2CPIU
            "
     
      REVISION "202402191500Z"
              DESCRIPTION "V14.67,
	   Add:virent8090DEVCR8DE6LEJKLP(849654),   -- V8R24C00 for CR8DE6LEJKLP(SBOM) 6-Port 800GBase-QSFP-DD + 36-Port 400GBase-QSFP-DD Integrated Line Processing Unit L CM(LPUI-19T2-L-CM,Enable 6*400GE + 36*100GE by default)
           Add:virent8090DEVCR8D8E6LJKLP(462881),   -- V8R24C00 for CR8D8E6LJKLP(SBOM) 6-Port 800GBase-QSFP-DD + 36-Port 400GBase-QSFP-DD Integrated Line Processing Unit L CM(LPUI-19T2-L-CM,Enable 6*400GE + 36*100GE by default)
           Add:virent8090DEVCR5DVSUIK092(314240),   -- V8R24C00 for CR5DVSUIK092(SBOM) Integrated Service Unit 400(VSUI-400A)
           Add:virent8090DEVCR5DVSUIK094(853637),   -- V8R24C00 for CR5DVSUIK094(SBOM) Integrated Service Unit 400(VSUI-400A-S)
           Add:virent8090DEVME0DVSUIK07H(285785),   -- V8R24C00 for ME0DVSUIK07H(SBOM) Integrated Service Unit 400(VSUI-400D)
           Add:virent8090DEVME0DVSUIK07I(224241),   -- V8R24C00 for ME0DVSUIK07I(SBOM) Integrated Service Unit 400(VSUI-400A)
           Add:virent8090DEVME0DVSUIK07J(434372),   -- V8R24C00 for ME0DVSUIK07J(SBOM) Integrated Service Unit 400(VSUI-400A-S)
           Add:virent8090DEVCR8DSFU19TA0(896523),   -- V8R24C00 for CR8DSFU19TA0(SBOM) Integrated Network Processing Unit (SFUI-19T2-A)
           Add:virent8090DEVCR8DSFU19TB0(896524),   -- V8R24C00 for CR8DSFU19TB0(SBOM) Integrated Network Processing Unit (SFUI-19T2-B)
           Add:virent8090DEVCR5DLPUFF39D(336598),   -- V8R24C00 for CR5DLPUFF39D(SBOM) Integrated Network Processing Unit (LPUF-246-E)
           Add:virent8090DEVCR5DLPUFF39F(336599),   -- V8R24C00 for CR5DLPUFF39F(SBOM) Integrated Network Processing Unit (LPUF-246A-E)
           Add:virent8090DEVCR5DLPUFF39E(336600),   -- V8R24C00 for CR5DLPUFF39E(SBOM) Integrated Network Processing Unit (LPUF-246-E)
           Add:virent8090DEVME0DBSUFM07Q(336601),   -- V8R24C00 for ME0DBSUFM07Q(SBOM) Integrated Network Processing Unit (BSUF-246)
           Add:virent8090DEVME0DBSUFM07R(336602),   -- V8R24C00 for ME0DBSUFM07R(SBOM) Integrated Network Processing Unit (BSUF-246A)
           Add:virent8090DEVME0DBSUFM07P(336603),   -- V8R24C00 for ME0DBSUFM07P(SBOM) Integrated Network Processing Unit (BSUF-246-E)"
              
	    REVISION "202402081500Z"
              DESCRIPTION "V14.65,
			   Add:bnamePTN7900TPD2PSU(229707), --TPD2PSU,Power Subboard
			   Add:bnamePTN7900TPD1SCAD(229708), --TPD1SCAD, System Control, Communication and Auxiliary Processing Unit,1*1
			   Add:bnamePTN7900TPF1CXPD(229709), --TPF1CXPD, System Control, Communication and Switch Fabric Process Unit,1*1
			   Add:virentPTN7900TPF1VXCSD(229710), --TPF1VXCSD,Switch Fabric Unit,1*1
			   Add:bnamePTN7900TPA1GY16(229711), --TPA1GY16, Fine Granularity Unit Functional Board, 16-Port-10GE/25GE/10G-FG Interface Card(SFP28/SFP+)"
			   
        REVISION "202402041400Z"
              DESCRIPTION "V14.65,
               Add: subbname AirEngine 6776I-X7TH,
               Add: subbname AP673,
               Add: subbname AirEngine 9701S-L"

       REVISION "202402011100Z"
              DESCRIPTION "V14.64,
                Add: subbname8090DEVCR8DPMUF00X1(513250),    -- V8R23C10 for CR8DPMUF00X1(SBOM) 16-Port 10GE(SFP+)/GE(SFP) + 16-Port 155M/16-Port 622M/8-Port 2.5G/2-Port 10GPOS Flexible Card CM(P1T-CM)
                Add: subbname8090DEVCR8DPMUF00XA(513251),    -- V8R23C10 for CR8DPMUF00XA(SBOM) 16-Port 10GE(SFP+)/GE(SFP) + 16-Port 155M/16-Port 622M/8-Port 2.5G/2-Port 10GPOS Flexible Card CM(P1T-CM)
                Add: subbname8090DEVCR8DPMUF00XB(513252),    -- V8R23C10 for CR8DPMUF00XB(SBOM) 16-Port 10GE(SFP+)/GE(SFP) + 16-Port 155M/16-Port 622M/8-Port 2.5G/2-Port 10GPOS Flexible Card CM(P1T-CM)
                Add: subbname8090DEVCR8DPMUF00XC(513253),    -- V8R23C10 for CR8DPMUF00XC(SBOM) 16-Port 10GE(SFP+)/GE(SFP) + 16-Port 155M/16-Port 622M/8-Port 2.5G/2-Port 10GPOS Flexible Card CM(P1T-CM)
                Add: subbname8090DEVCR8D8MUF00L1(513254),    -- V8R23C10 for CR8D8MUF00L1(SBOM) 16-Port 10GE(SFP+)/GE(SFP) + 16-Port 155M/16-Port 622M/8-Port 2.5G/2-Port 10GPOS Flexible Card L CM (P1T-L-CM)
                Add: subbname8090DEVCR8D8MUF00X1(513255),    -- V8R23C10 for CR8D8MUF00X1(SBOM) 16-Port 10GE(SFP+)/GE(SFP) + 16-Port 155M/16-Port 622M/8-Port 2.5G/2-Port 10GPOS Flexible Card (P1T-CM)
                Add: subbname8090DEVCR8DPMUF00X1-(513256),    -- V8R23C10 for CR8DPMUF00X1(SBOM) 16-Port 10GE(SFP+)/GE(SFP) + 16-Port 155M/16-Port 622M/8-Port 2.5G/2-Port 10GPOS Flexible Card CM(P1T-CM)
                Add: subbname8090DEVCR8DPMUF00XA-(513257),    -- V8R23C10 for CR8DPMUF00XA(SBOM) 16-Port 10GE(SFP+)/GE(SFP) + 16-Port 155M/16-Port 622M/8-Port 2.5G/2-Port 10GPOS Flexible Card CM(P1T-CM)
                Add: subbname8090DEVCR8DPMUF00XB-(513258),    -- V8R23C10 for CR8DPMUF00XB(SBOM) 16-Port 10GE(SFP+)/GE(SFP) + 16-Port 155M/16-Port 622M/8-Port 2.5G/2-Port 10GPOS Flexible Card CM(P1T-CM)
                Add: subbname8090DEVCR8DPMUF00XC-(513259),    -- V8R23C10 for CR8DPMUF00XC(SBOM) 16-Port 10GE(SFP+)/GE(SFP) + 16-Port 155M/16-Port 622M/8-Port 2.5G/2-Port 10GPOS Flexible Card CM(P1T-CM)
                Add: subbname8090DEVCR8D8MUF00L1-(513260),    -- V8R23C10 for CR8D8MUF00L1(SBOM) 16-Port 10GE(SFP+)/GE(SFP) + 16-Port 155M/16-Port 622M/8-Port 2.5G/2-Port 10GPOS Flexible Card L CM (P1T-L-CM)
                Add: subbname8090DEVCR8D8MUF00X1-(513261),    -- V8R23C10 for CR8D8MUF00X1(SBOM) 16-Port 10GE(SFP+)/GE(SFP) + 16-Port 155M/16-Port 622M/8-Port 2.5G/2-Port 10GPOS Flexible Card (P1T-CM)
                Add: subbname8090DEVCR8DE2NB00M1(548699),   -- 2-Port 100GBase/50GBase-QSFP28 Interface Card(PIC)"

	REVISION "202401271600Z"
     DESCRIPTION "V14.63,
           Add: virent8090DEVCR9DE8KE8N8Y(300368),   -- V8R23C10 for CR9DE8KE8N8Y(SBOM) 8-Port 400GE-QSFP-DD + 8-Port 100GE-QSFP28 Integrated Line Process Unit CM(LPUI-4T-CM, 8*100G RTU Enabled by default)"

	REVISION "202401261600Z"
	 DESCRIPTION "V14.62,
			Add: fnameMA5801FL04H1(148542),     	 --  Backplane of the MA5801-FL04-H1.
			Add: bnameV921MPCG(148831),        		 --  control board of MA5801-FL04-H1.
            Add: bnameV921FLHC(148832),        		 --  4*flex-PON board of MA5800-FL04-H1.
            Add: bnameV921NXLC(148833),        		 --  4*10GE and 2*2.5GE/GE electric port board of MA5801-FL04-H1.
			"
	
	REVISION "202401151900Z"		 
     DESCRIPTION "V14.61,
			Add: virent8090DEVHGFM0HOSTB02(229568),           -- V8R23C10 for HGFM0HOSTB02(SBOM) HG-FM CPE-02 AC Power,with 6*GE/FE(o),8*GE/FE(e),
			Add: virent8090DEVHGFM0HOSTA02(229567),           -- V8R23C10 for HGFM0HOSTA02(SBOM) HG-FM CPE-01 AC Power,with 5G module ,4*GE/FE(o),2*GE(o),8*GE/FE(e),
	 "

	REVISION "202401101400Z"
     DESCRIPTION "V14.60,
               Add: subbname AirEngine 6776I-X6TH,
               Add: subbname AirEngine 5773-25HWP,
               Add: subbname AirEngine 5773-23HWP,
               Add: subbname AirEngine 5576-26,
               Add: subbname AirEngine 6576-57T,
               Add: subbname AirEngine 6776-58T,
               Add: subbname AirEngine 5573-21,
               Add: subbname AirEngine 3573-21,
               Add: subbname AirEngine 6576-56TP,
               Add: subbname AP361E,
               Add: subbname AP265,
               Add: subbname AP265E,
               Add: subbname AP266,
               Add: subbname AP160E,
               Add: subbname AirEngine5763-11W,
               Add: subbname AirEngine 9503-S,
               Add: subbname AirEngine AC650-512,
			   Add: subbname AirEngine 5573-23H,
               Add: subbname AirEngine 5573-23HW"
			   
	REVISION "202401091100Z"		 
     DESCRIPTION "V14.58,
			Add: subbnameCE98D32CQF(688164),
			Add: subbnameCE98D8DQF(688165),
	 "
	REVISION "202401091100Z"
     DESCRIPTION "V14.58,
			Add: bnameUSG6000F-S30       (16748967),    --00FF9207
			Add: bnameUSG6000F-S50       (16748968),    --00FF9208
			Add: bnameUSG6000F-S150       (16748969),    --00FF920A
			Add: bnameUSG6000F-S160       (16748970),    --00FF920B
			Add: bnameUSG6000F-S180       (16748971),    --00FF920C
			Add: bnameUSG6000F-S200       (16748972),    --00FF920D
			Add: bnameUSG6000F-S230       (16748973),    --00FF920E
			Add: bnameUSG6000F-S260       (16748974),    --00FF920F
			Add: bnameIPS6000F-S110       (16748975),    --00FF9210
			Add: bnameIPS6000F-S120       (16748976),    --00FF9211
			Add: bnameXH6655         (16748977),    --00FF9212
			Add: fnameUSG6000F-S30   (16716181),    --00FF1195
			Add: fnameUSG6000F-S50   (16716182),    --00FF1196
			Add: fnameUSG6000F-S150   (16716183),    --00FF1197
			Add: fnameUSG6000F-S160   (16716184),    --00FF1198
			Add: fnameUSG6000F-S180   (16716185),    --00FF1199
			Add: fnameUSG6000F-S200   (16716186),    --00FF119A
			Add: fnameUSG6000F-S230   (16716187),    --00FF119B
			Add: fnameUSG6000F-S260   (16716188),    --00FF119C
			Add: fnameIPS6000F-S110   (16716189),    --00FF119D
			Add: fnameIPS6000F-S120   (16716190),    --00FF119E
			Add: fnameIPS6000F-S120   (16716190),    --00FF119E
			Add: fnameXH6655         (16716191),    --00FF119F
			delete bnameUSG6305F-C    (16748837),    --00FF9125
			delete bnameUSG6307F-D    (16748846),    --00FF912E
			delete bnameUSG6311F-D    (16748847),    --00FF912F
			delete bnameUSG6331F-D    (16748848),    --00FF9130
			delete bnameUSG6306F    (16748854),    --00FF9136
			delete bnameUSG6308F    (16748855),    --00FF9137
			delete bnameUSG6315F    (16748856),    --00FF9138
			delete bnameUSG6302F-C    (16748873),    --00FF9149
			delete bnameUSG6303F    (16748908),    --00FF916C
			delete bnameUSG6325F        (16748934),    --00FF9186
			delete bnameUSG6355F        (16748935),    --00FF9187
			delete bnameUSG6335F        (16748953),    --00FF9199
			delete bnameUSG6365F        (16748954),    --00FF919A
			delete bnameUSG6385F        (16748955),    --00FF919B
			delete bnameUSG6391F        (16748956),    --00FF919C
			delete bnameIPS6309F        (16748957),    --00FF919D
			delete bnameIPS6315F        (16748958),    --00FF919E 
			delete fnameUSG6305F-C        (16716066),    --00FF1122
			delete fnameUSG6307F-D        (16716075),    --00FF112B
			delete fnameUSG6311F-D        (16716076),    --00FF112C
			delete fnameUSG6331F-D        (16716077),    --00FF112D
			delete fnameUSG6306F        (16716083),    --00FF1133
			delete fnameUSG6308F        (16716084),    --00FF1134
			delete fnameUSG6315F        (16716085),    --00FF1135
			delete fnameUSG6302F-C        (16716102),    --00FF1146
			delete fnameUSG6303F        (16716115),    --00FF1153
			delete fnameUSG6325F        (16716144),    --00FF1170
			delete fnameUSG6355F        (16716145),    --00FF1171
			delete fnameUSG6335F        (16716159),    --00FF117F
			delete fnameUSG6365F        (16716160),    --00FF1180
			delete fnameUSG6385F        (16716161),    --00FF1181
			delete fnameUSG6391F        (16716162),    --00FF1182
			delete fnameIPS6309F        (16716163),    --00FF1183
			delete fnameIPS6315F        (16716164),    --00FF1184
		" 
    REVISION "202401031100Z"
     DESCRIPTION "V14.57,
               Add: subbname8090DEVCR8DE1KB00M3(548683),   -- 1-Port 400GBase-QSFP-DD Single-layer Physical Interface Card(PIC)
               Add: subbname8090DEVCR8DE1KB00M1(548685),   -- 1-Port 400GBase-QSFP-DD Single-layer Physical Interface Card(PIC)
               Add: subbname8090DEVCR8DE1KB00M4(548686),   -- 1-Port 400GBase-QSFP-DD Single-layer Physical Interface Card CM(Enable 1*100G)(PIC)
               Add: subbname8090DEVCR8DE1KB00M2(548687),   -- 1-Port 400GBase-QSFP-DD Single-layer Physical Interface Card CM(Enable 1*100G)(PIC)
               Add: subbname8090DEVCR8DE4NB00M3(548693),    -- 4-Port 100GBase/50GBase-QSFP28 Physical Interface Card(PIC)
               Add: subbname8090DEVCR8DE4NB00M1(548694),    -- 4-Port 100GBase/50GBase-QSFP28 Physical Interface Card(PIC)
               Add: subbname8090DEVCR8DE4NB00M2(548695),    -- 4-Port 100GBase/50GBase-QSFP28 Physical Interface Card CM(Enable 2*100GE by default)(PIC)"

	REVISION "202401020000Z"
     DESCRIPTION "V14.56,
			   Add: fnameCE9855U32DQ(688311),
			   Add: fnameCE9855T32DQ(688312),
			   Add: fnameCE9855M32DQ(688313),
			   Add: bnameCE9855U32DQ(688634),
			   Add: bnameCE9855T32DQ(688635),
			   Add: bnameCE9855M32DQ(688636),
			   Add: subbnameCE98D8DQX(688162),
			   Add: subbnameCE98D32CQX(688163),
			   MODIFY: bnameXHL36DQJ2(688626)->bnameXHL40DQJ2(688626),
			   MODIFY: bnameCEXL36DQJ2(688628)->bnameCEXL40DQJ2(688628),
			   Delete: fnameXH9120DX32BQ16DQ(688301),
			   Delete: fnameCE8875DX44BQ8DQ(688302),
			   Delete: bnameXH9120DX32BQ16DQ(688619),
			   Delete: bnameCE8875DX44BQ8DQ(688620),
		" 
		
		REVISION "202312271200Z"
			DESCRIPTION "V14.55,
			   Add: virent8090DEVCR8D0IPU3TM1(834277),   -- V8R23C10 for CR8D0IPU3TM1(SBOM) Integrated Network Processing Unit (IPU-3T6-A)
			   Add: virent8090DEVCR8D0IPU3TM2(803803),   -- V8R23C10 for CR8D0IPU3TM2(SBOM) Integrated Network Processing Unit (IPU-3T6-E-B)
			   Add: virent8090DEVCR8DUIPU2TM1(803804),   -- V8R23C10 for CR8DUIPU2TM1(SBOM) Integrated Network Processing Unit (IPU-2T-AU)
                           Add: virent8090DEVCR8DUIPU2TM2(803805),   -- V8R23C10 for CR8DUIPU2TM2(SBOM) Integrated Network Processing Unit (IPU-2T-E-BU)
                           Add: virent8090DEVTNRD0IPU3T91(803806),   -- V8R23C10 for TNRD0IPU3T91(SBOM) Integrated Network Processing Unit (IPU-3T6-A)
                           Add: virent8090DEVTNRD0IPU3T92(803807),   -- V8R23C10 for TNRD0IPU3T92(SBOM) Integrated Network Processing Unit (IPU-3T6-E-B)
                           Add: virent8090DEVTNRDUIPU2T91(803808),   -- V8R23C10 for TNRDUIPU2T91(SBOM) Integrated Network Processing Unit (IPU-2T-AU)
                           Add: virent8090DEVTNRDUIPU2T92(803809),   -- V8R23C10 for TNRDUIPU2T92(SBOM) Integrated Network Processing Unit (IPU-2T-E-BU)
                           Add: virent8090DEVCR5D0IPU3TM1(803810),   -- V8R23C10 for CR5D0IPU3TM1(SBOM) Integrated Network Processing Unit (IPU-3T6-A)
                           Add: virent8090DEVCR5D0IPU3TM2(803811),   -- V8R23C10 for CR5D0IPU3TM2(SBOM) Integrated Network Processing Unit (IPU-3T6-E-B)
                           Add: virent8090DEVCR5DUIPU2TM1(803812),   -- V8R23C10 for CR5DUIPU2TM1(SBOM) Integrated Network Processing Unit (IPU-2T-AU)
                           Add: virent8090DEVCR5DUIPU2TM2(803813),   -- V8R23C10 for CR5DUIPU2TM2(SBOM) Integrated Network Processing Unit (IPU-2T-E-BU)
                           Add: virent8090DEVCR8D0IPU3TM3(803814),   -- V8R23C10 for CR8D0IPU3TM3(SBOM) Integrated Network Processing Unit (IPUA-3T6-A)
                           Add: virent8090DEVCR8DUIPU2TM3(803815),   -- V8R23C10 for CR8DUIPU2TM3(SBOM) Integrated Network Processing Unit (IPUA-2T-AU)
                           Add: virent8090DEVCR8D0IPU3TM5(803816),   -- V8R23C10 for CR8D0IPU3TM5(SBOM) Integrated Network Processing Unit (IPUA-3T6-A)
                           Add: virent8090DEVCR8DUIPU2TM5(803817),   -- V8R23C10 for CR8DUIPU2TM5(SBOM) Integrated Network Processing Unit (IPUA-2T-AU)"
		
       REVISION    "202312080000Z"
        DESCRIPTION "V14.54,
           Add: subbnameCE88SAND16CQH(688160),
           Add: subbnameCE88SAND26FH(688161),
        "
		REVISION    "202312060000Z"
        DESCRIPTION "V14.53,
			delete:	bnameUSG6325Fold    (16748857),    --00FF9139
			delete:	bnameUSG6335Fold    (16748858),    --00FF913A
			delete:	bnameUSG6355Fold    (16748859),    --00FF913B
			delete:	bnameUSG6365Fold    (16748860),    --00FF913C
			delete:	bnameUSG6385Fold    (16748861),    --00FF913D
			delete:	bnameIPS6309Fold    (16748862),    --00FF913E
			delete:	bnameIPS6315Fold    (16748863),    --00FF913F
			delete:	fnameUSG6325Fold        (16716086),    --00FF1136
			delete:	fnameUSG6335Fold        (16716087),    --00FF1137
			delete:	fnameUSG6355Fold        (16716088),    --00FF1138
			delete:	fnameUSG6365Fold        (16716089),    --00FF1139
			delete:	fnameUSG6385Fold        (16716090),    --00FF113A
			delete:	fnameIPS6309Fold        (16716091),    --00FF113B
			delete:	fnameIPS6315Fold        (16716092),    --00FF113C
			Add: bnameEudemon1000E-M55(16748893),    --FW bnameEudemon1000E-M55,
			Add: bnameEudemon1000E-M10(16748894),    --FW bnameEudemon1000E-M10,
			Add: bnameEudemon1000E-S10(16748895),    --FW bnameEudemon1000E-S10,
			Add: bnameEudemon1000E-C10(16748896),    --FW bnameEudemon1000E-C10,
			Add: bnameMPUA-H6-T(16748922),   -- Assembling Components,bnameMPUA-H6-T"
		REVISION    "202312040000Z"
        DESCRIPTION "V14.52,
			Add: fnameEudemon1000E-C1A(16716116),   -- Assembling Components,fnameEudemon1000E-C1A,
			Add: fnameEudemon1000E-M1A(16716119),   -- Assembling Components,fnameEudemon1000E-M1A,
			Add: fnameEudemon1000E-M2A(16716120),   -- Assembling Components,fnameEudemon1000E-M2A,
			Add: fnameEudemon1000E-S1A(16716123),   -- Assembling Components,fnameEudemon1000E-S1A,
			Add: fnameEudemon1000E-T1A(16716126),   -- Assembling Components,fnameEudemon1000E-T1A,
			Add: fnameProbe1001F(16716130),   -- Assembling Components,fnameProbe1001F,
			Add: fnameEudemon1000E-F01(16716131),   -- Assembling Components,fnameEudemon1000E-F01,
			Add: fnameEudemon1000E-F05(16716132),   -- Assembling Components,fnameEudemon1000E-F05,
			Add: fnameUSG6680E-ACC(16716133),   -- Assembling Components,fnameUSG6680E-ACC,
			Add: fnameEudemon1000E-M55(16716139),   -- Assembling Components,fnameEudemon1000E-M55,
			Add: fnameEudemon1000E-M10(16716140),   -- Assembling Components,fnameEudemon1000E-M10,
			Add: fnameEudemon1000E-S10(16716141),   -- Assembling Components,fnameEudemon1000E-S10,
			Add: fnameEudemon1000E-C10(16716142),   -- Assembling Components,fnameEudemon1000E-C10,
			Add: fnameUSG6585F-B(16716143),   -- Assembling Components,fnameUSG6585F-B,
			Add: fnameUSG6325F(16716144),   -- Assembling Components,fnameUSG6325F,
			Add: fnameUSG6355F(16716145),   -- Assembling Components,fnameUSG6355F,
			Add: fnameEudemon1000E-C5A(16716146),   -- Assembling Components,fnameEudemon1000E-C5A,
			Add: fnameEudemon1000E-C8A(16716147),   -- Assembling Components,fnameEudemon1000E-C8A,
			Add: fnameEudemon1000E-M3A(16716148),   -- Assembling Components,fnameEudemon1000E-M3A,
			Add: fnameEudemon1000E-M5A(16716149),   -- Assembling Components,fnameEudemon1000E-M5A,
			Add: fnameEudemon1000E-S5A(16716150),   -- Assembling Components,fnameEudemon1000E-S5A,
			Add: fnameEudemon1000E-S8A(16716151),   -- Assembling Components,fnameEudemon1000E-S8A,
			Add: fnameEudemon1000E-T3A(16716152),   -- Assembling Components,fnameEudemon1000E-T3A,
			Add: fnameEudemon1000E-T5A(16716153),   -- Assembling Components,fnameEudemon1000E-T5A,
			Add: fnameEudemon1000E-C10A(16716154),   -- Assembling Components,fnameEudemon1000E-C10A,
			Add: fnameEudemon1000E-S10A(16716155),   -- Assembling Components,fnameEudemon1000E-S10A,
			Add: fnameEudemon1000E-M10A(16716156),   -- Assembling Components,fnameEudemon1000E-M10A,
			Add: fnameEudemon1000E-T10A(16716157),   -- Assembling Components,fnameEudemon1000E-T10A,
			Add: fnameEudemon9000E-H(16716158),   -- Assembling Components,fnameEudemon9000E-H,
			Add: fnameUSG6335F(16716159),   -- Assembling Components,fnameUSG6335F,
			Add: fnameUSG6365F(16716160),   -- Assembling Components,fnameUSG6365F,
			Add: fnameUSG6385F(16716161),   -- Assembling Components,fnameUSG6385F,
			Add: fnameUSG6391F(16716162),   -- Assembling Components,fnameUSG6391F,
			Add: fnameIPS6309F(16716163),   -- Assembling Components,fnameIPS6309F,
			Add: fnameIPS6309F(16716164),   -- Assembling Components,fnameIPS6309F,
			Add: fnameEudemon1000E-C1A-PL(16716165),   -- Assembling Components,fnameEudemon1000E-C1A-PL,
			Add: fnameEudemon1000E-M1A-PL(16716166),   -- Assembling Components,fnameEudemon1000E-M1A-PL,
			Add: fnameEudemon1000E-S1A-PL(16716167),   -- Assembling Components,fnameEudemon1000E-S1A-PL,
			Add: fnameEudemon1000E-T1A-PL(16716168),   -- Assembling Components,fnameEudemon1000E-T1A-PL,
			Add: Eudemon1000E-F10(16716169),   -- Assembling Components,Eudemon1000E-F10,
			Add: Eudemon1000E-F03-D-AC(16716170),   -- Assembling Components,Eudemon1000E-F03-D-AC,
			Add: Eudemon1000E-F03-DL-AC(16716171),   -- Assembling Components,Eudemon1000E-F03-DL-AC,
			Add: bnameEudemon1000E-C1A(16748909),   -- Assembling Components,bnameEudemon1000E-C1A,
			Add: bnameEudemon1000E-M1A(16748912),   -- Assembling Components,bnameEudemon1000E-M1A,
			Add: bnameEudemon1000E-M2A(16748913),   -- Assembling Components,bnameEudemon1000E-M2A,
			Add: bnameEudemon1000E-S1A(16748916),   -- Assembling Components,bnameEudemon1000E-S1A,
			Add: bnameEudemon1000E-T1A(16748919),   -- Assembling Components,bnameEudemon1000E-T1A,
			Add: bnameProbe1001F(16748923),   -- Assembling Components,bnameProbe1001F,
			Add: bnameEudemon1000E-F01(16748924),   -- Assembling Components,bnameEudemon1000E-F01,
			Add: bnameEudemon1000E-F05(16748925),   -- Assembling Components,bnameEudemon1000E-F05,
			Add: bnameUSG6680E-ACC(16748926),   -- Assembling Components,bnameUSG6680E-ACC
			Add: bnameUSG6585F-B(16748933),   -- Assembling Components,bnameUSG6585F-B,
			Add: bnameUSG6325F(16748934),   -- Assembling Components,bnameUSG6325F,
			Add: bnameUSG6355F(16748935),   -- Assembling Components,bnameUSG6355F,
			Add: bnameEudemon1000E-C5A(16748936),   -- Assembling Components,bnameEudemon1000E-C5A,
			Add: bnameEudemon1000E-C8A(16748937),   -- Assembling Components,bnameEudemon1000E-C8A,
			Add: bnameEudemon1000E-M3A(16748938),   -- Assembling Components,bnameEudemon1000E-M3A,
			Add: bnameEudemon1000E-M5A(16748939),   -- Assembling Components,bnameEudemon1000E-M5A,
			Add: bnameEudemon1000E-S5A(16748940),   -- Assembling Components,bnameEudemon1000E-S5A,
			Add: bnameEudemon1000E-S8A(16748941),   -- Assembling Components,bnameEudemon1000E-S8A,
			Add: bnameEudemon1000E-T3A(16748942),   -- Assembling Components,bnameEudemon1000E-T3A,
			Add: bnameEudemon1000E-T5A(16748943),   -- Assembling Components,bnameEudemon1000E-T5A,
			Add: bnameEudemon1000E-C10A(16748944),   -- Assembling Components,bnameEudemon1000E-C10A,
			Add: bnameEudemon1000E-S10A(16748945),   -- Assembling Components,bnameEudemon1000E-S10A,
			Add: bnameEudemon1000E-M10A(16748946),   -- Assembling Components,bnameEudemon1000E-M10A,
			Add: bnameEudemon1000E-T10A(16748947),   -- Assembling Components,bnameEudemon1000E-T10A,
			Add: bnameLPUG-E-16CQ24XS(16748948),   -- Assembling Components,bnameLPUG-E-16CQ24XS,
			Add: bnameLPUG-E-8CQ24XS(16748949),   -- Assembling Components,bnameLPUG-E-8CQ24XS,
			Add: bnameSPUG-E9KE-03(16748950),   -- Assembling Components,bnameSPUG-E9KE-03,
			Add: bnameSPUG-E9KE-02(16748951),   -- Assembling Components,bnameSPUG-E9KE-02,
			Add: bnameMPUA-H6(16748952),   -- Assembling Components,bnameMPUA-H6,
			Add: bnameUSG6335F(16748953),   -- Assembling Components,bnameUSG6335F,
			Add: bnameUSG6365F(16748954),   -- Assembling Components,bnameUSG6365F,
			Add: bnameUSG6385F(16748955),   -- Assembling Components,bnameUSG6385F,
			Add: bnameUSG6391F(16748956),   -- Assembling Components,bnameUSG6391F,
			Add: bnameIPS6309F(16748957),   -- Assembling Components,bnameIPS6309F,
			Add: bnameIPS6315F(16748958),   -- Assembling Components,bnameIPS6315F,
			Add: bnameEudemon1000E-C1A-PL(16748959),   -- Assembling Components,bnameEudemon1000E-C1A-PL,
			Add: bnameEudemon1000E-M1A-PL(16748960),   -- Assembling Components,bnameEudemon1000E-M1A-PL,
			Add: bnameEudemon1000E-S1A-PL(16748961),   -- Assembling Components,bnameEudemon1000E-S1A-PL,
			Add: bnameEudemon1000E-T1A-PL(16748962),   -- Assembling Components,bnameEudemon1000E-T1A-PL,
			Add: subnamePAC80S12-CN(16748963),   -- Assembling Components,subnamePAC80S12-CN,
			Add: bnameEudemon1000E-F10(16748964),   -- Assembling Components,bnameEudemon1000E-F10,
			Add: bnameEudemon1000E-F03-D(16748965),   -- Assembling Components,bnameEudemon1000E-F03-D,
			Add: bnameEudemon1000E-F03-DL(16748966),   -- Assembling Components,bnameEudemon1000E-F03-DL,"
    REVISION    "202311300000Z"
        DESCRIPTION "V14.51,
           Add: bnameLSG700VSX1E0(713503),   --High-quality value-added service board
           Add: bnameLSG7SRUDX100(713504),   --S8700-4 main control unit, supporting 2*25GE+6*10GE+20*GE electrical+4*GE combo, or 4*25GE+8*10GE+12*GE electrical+4*GE combo 4*25GE/10GE+8*10GE, or 4*10GE+8*GE+12*GE electrical+4*GE combo service ports     
           Add: bnameLSG7SRUDX1H0(713505),   --S8700-4 main control unit, supporting 2*25GE+6*10GE+20*GE electrical+4*GE combo, or 4*25GE+8*10GE+12*GE electrical+4*GE combo 4*25GE/10GE+8*10GE, or 4*10GE+8*GE+12*GE electrical+4*GE combo service ports
           Add: bnameLSG7SRUEX100(713506),   --S8700-6 main control unit, supporting 2*25GE+6*10GE+20*GE electrical+4*GE combo, or 4*25GE+8*10GE+12*GE electrical+4*GE combo 4*25GE/10GE+8*10GE, or 4*10GE+8*GE+12*GE electrical+4*GE combo service ports     
           Add: bnameLSG7SRUEX1H0(713507),   --S8700-6 main control unit, supporting 2*25GE+6*10GE+20*GE electrical+4*GE combo, or 4*25GE+8*10GE+12*GE electrical+4*GE combo 4*25GE/10GE+8*10GE, or 4*10GE+8*GE+12*GE electrical+4*GE combo service ports
           Add: bnameLSG7SRUFX500(713508),   --S8700-10 main control unit, supporting 1*100GE+2*40GE+12*10GE, 1*100GE+8*25GE, or 3*100GE service ports                                                                                                        
           Add: bnameLSG7SRUFX5H0(713509),   --S8700-10 main control unit, supporting 1*100GE+2*40GE+12*10GE, 1*100GE+8*25GE, or 3*100GE service ports                                                                                                   
           Add: bnameLSG7SRUEX500(713510),   --S8700-6 main control unit, supporting 1*100GE+2*40GE+12*10GE, 1*100GE+8*25GE, or 3*100GE service ports                                                                                                         
           Add: bnameLSG7SRUEX5H0(713511),   --S8700-6 main control unit, supporting 1*100GE+2*40GE+12*10GE, 1*100GE+8*25GE, or 3*100GE service ports                                                                                                    
           Add: bnameLSG7SFUAX100(713512),   --S8700 SFU A (X1)                                                                                                                                                                                               
           Add: bnameLSG7C04HX1E1(713513),   --4-Port 100G Ethernet Optical Interface Card (QSFP28)                                                                                                                                                           
           Add: bnameLSG7X72SX1E0(713514),   --72-port 100M/1G/10G Ethernet optical interface card (SFP+)                                                                                                                                                     
           Add: bnamePAC1K5S54-PF(713515),   --Function Module,AC&240VDC PSU,PAC1K5S54-PF,1500W AC&240VDC Power Module (Front to Back, Power panel side intake)
           Add: bnameLSH7L36QX1E1(713739),   --36-Port 40GE Interface Card (X1E, QSFP+)"

		REVISION    "202311270000Z"
        DESCRIPTION "V14.50,
           Add: subbname8090DEVNetEngine-A822(115925),     -- CARD NetEngine A822
           Add: subbname8090DEVGPI6EQ36KQES0(513327),   -- 6-port 800GBase QSFPDD800-36-Port 400GBase QSFPDD Integrated Line Process Unit"
		
		REVISION    "202311200000Z"
        DESCRIPTION "V14.49,
					Add: bnameHA01UPLA(148821),           -- Ultra Processing board of MA5800T.
					Add: bnameH901HXEDE(148830),          -- 8-port 10GS-PON and 50GS-PON combo interface board of EA5800.
					Add: bnameH901FLVFE(148834),          -- 16*flex-PON board of EA5800.
					Add: xponOltPort(597),                -- XPON OLT port
                    "
					
		REVISION    "202311180000Z"
        DESCRIPTION "V14.48,
           Add: VIRTUAL-SRU-700S(668197),   --VIRTUAL SRU-700S SRU Control Unit
           Add: ARPAC300S12-CL(668198),     --Power Card, 300W AC
           Add: ARPDC260S12-CL(668199),     --Power Card, 260W DC"
        
		REVISION    "202311170000Z"
        DESCRIPTION "V14.47,
           Add: virent8090DEVANGMHSTS0120(689135),   -- V8R23C10 for ANGMHSTS0120(SBOM) ATN 910C-S, DC Power, Port Capacity 6*10GE/GE/FE(o)+2*GE/FE(o)+4*GE/FE(e), Default 2*10GE+10*GE
           Add: virent8090DEVANGMHSTS0220(689136),   -- V8R23C10 for ANGMHSTS0220(SBOM) ATN 910C-S, AC Power, Port Capacity 6*10GE/GE/FE(o)+2*GE/FE(o)+4*GE/FE(e), Default 2*10GE+10*GE"     
        
		REVISION    "202311150000Z"
        DESCRIPTION "V14.46,
           Add: fnameGM510MERGE(688307) to fnameGM110SDI(688310).
           Add: bnameGM510MERGE(688630), to bnameGM110SDI(688633)."        
		   
		REVISION    "202311140000Z"
        DESCRIPTION "V14.45,
           Add: subbname8090DEVNetEngine-8000-M1D-A(235929),  --CARD NetEngine 8000 M1D-A
           Add: subbname8090DEVCR8DE2NB00M0(548690),   -- 2-Port 100GBase/50GBase-QSFP28 Interface Card(PIC)
           Add: subbname8090DEVCR8DE2NBMSF0(548691),   -- 2-Port 100GBase/50GBase-QSFP28 Interface Card(PIC)
           Add: subbname8090DEVCR8DE2NBMSF1(548692),   -- 2-Port 100GBase/50GBase-QSFP28 Interface Card(PIC)"
		
        REVISION    "202311080000Z"
        DESCRIPTION "V14.44,
           Add: fnameXH168008(688292) to fnameCE9865T4C(688306).
           Add: bnameXH168008(688605) to bnameCEXL36DQJ2(688628)."
        
		REVISION    "202311030000Z"
        DESCRIPTION "V14.43,
           Add: fnameMA5800TX17HA01BPLA(148541),     -- Backplane of MA5800T-X17.
           Add: bnameHA01PDLA(148827),               -- Power board of MA5800T-X17.
           Add: bnameHA01PDLB(148828),               -- Power board of MA5800T-X17.
           "

        REVISION "202311021400Z"
        DESCRIPTION "V14.42,
           Add: virent8090DEVANHMHSTA0506(689129),   -- V8R23C10 for ANHMHSTA0506(SBOM) ATN 910D-B,DC Power,Port Capacity 2*50GE+2*25GE/10GE/GE+2*10GE/GE+10*GE(o)+4*GE(e),support 4*25GE mode,default enable all GE/FE
           Add: virent8090DEVANHMHSTA0606(689130),   -- V8R23C10 for ANHMHSTA0606(SBOM) ATN 910D-B,AC Power,Port Capacity 2*50GE+2*25GE/10GE/GE+2*10GE/GE+10*GE(o)+4*GE(e),support 4*25GE mode,default enable all GE/FE
           Add: virent8090DEVCR8PM1DBASDE(689131),   -- V8R23C10 for CR8PM1DBASDE(SBOM) NetEngine 8000 M1D, DC Power(A)(Port Capacity 4*100GE/50GE+16*25GE/10GE/GE/FE+8*10GE/GE/FE,exclude auxiliary materials)
           Add: virent8090DEVCR8PM1DBASAE(689132),   -- V8R23C10 for CR8PM1DBASAE(SBOM) NetEngine 8000 M1D, AC Power(A)(Port Capacity 4*100GE/50GE+16*25GE/10GE/GE/FE+8*10GE/GE/FE,exclude auxiliary materials)
           Add: virent8090DEVCR8PM1DBADM6(689133),   -- V8R23C10 for CR8PM1DBADM6(SBOM) NetEngine 8000 M1D, DC Power (Port Capacity 4*100GE/50GE+16*25GE/10GE/GE/FE+8*10GE/GE/FE,exclude auxiliary materials)
           Add: virent8090DEVCR8PM1DBAAM6(689134),   -- V8R23C10 for CR8PM1DBAAM6(SBOM) NetEngine 8000 M1D Basic Configuration, AC Power (Port Capacity 4*100GE/50GE+16*25GE/10GE/GE/FE+8*10GE/GE/FE,exclude auxiliary materials)
           "
  REVISION "202310311000Z"
        DESCRIPTION "V7.57,
            The object identifier of S5735-L-V2, S5735-S-V2,  S3710-H and S6750-H are add."
            
        REVISION    "202310281000Z"
        DESCRIPTION "V14.40,
                    Add: bnameH901DPWA(148829),                -- Dustproof board of MA5800T-X17.
                    "

        REVISION "202310231000Z"
        DESCRIPTION "V14.39,
            The object identifier of AirEngine 5561-12 is add,
			The object identifier of AirEngine 5561R-11E is add,
			The object identifier of AirEngine 5562-15HW is add,
			The object identifier of AirEngine 6561-21T is add,
			The object identifier of AirEngine 6776-56T is renamed AirEngine 6776-56TP,
            The object identifier of AirEngine 5773-22 is renamed AirEngine 5773-22P,
			The object identifier of AirEngine 9501-L is add,
			The object identifier of AirEngine 9500-L1P is add."
		   
        REVISION "202310181400Z"
        DESCRIPTION "V14.38,
           Add: virent8090DEVTPND02CXPB03(932125),   -- V8R23C10 for TPND02CXPB03(SBOM) OptiX PTN 980, TPN2CXPB2, System Control,Cross-connect and Multi-protocol Process Unit
           Add: virent8090DEVTPND02CXPB04(932126),   -- V8R23C10 for TPND02CXPB04(SBOM) OptiX PTN 980, TPN2CXPB3, System Control,Cross-connect and Multi-protocol Process Unit
           Add: virent8090DEVTPQD01CXPB03(967205),   -- V8R23C10 for TPQD01CXPB03(SBOM) OptiX PTN 990E, TPQ1CXPB3, System Control,Cross-connect and Multi-protocol Process Unit
           Add: virent8090DEVTPQD01CXPB04(967206),   -- V8R23C10 for TPQD01CXPB04(SBOM) OptiX PTN 990E, TPQ1CXPB4, System Control,Cross-connect and Multi-protocol Process Unit
           "

    REVISION "202310101600Z"
    DESCRIPTION "V14.37,
        Add:fname8031S6330-S48X6Q(537900), bname8031S6330-S48X6Q(538083)"

    REVISION "202309271632Z"
              DESCRIPTION "V14.36,
                Add virent8090DEVCR5D00NINB61(562140),    -- V8R23C10 for CR5D00NINB61(SBOM) 32-Port 100G OTN/ETH QSFP28 Integrated Line Process Unit(NE5000E LPUI-3T2-C)
                Add virent8090DEVCR5D00NINB62(562141),    -- V8R23C10 for CR5D00NINB62(SBOM) 32-Port 32-Port 100G OTN/ETH QSFP28 Integrated Line Process Unit(NE5000E LPUI-3T2-C-CM)(8 ports enable)"

		REVISION    "202309261000Z"
		  DESCRIPTION "V14.35
			Add:fnameAR6710-H4T4X2Y7(668073),         --AR6710-H4T4X2Y7 FRAME
			Add:fnameAR5710-S8T2XE-LTE4CN(668074),    --AR5710-S8T2XE-LTE4CN FRAME
			Add:fnameAR5510-H10T2XW1(668075),         --AR5510-H10T2XW1 FRAME
			Add:fnameAR5510-L5TW(668076),             --AR5510-L5TW FRAME
			Add:fnameAR5510-L5TWDS-LTE4EA(668077),    --AR5510-L5TWDS-LTE4EA FRAME
			Add:fnameAR5510-L5TWDS(668078),           --AR5510-L5TWDS FRAME
			Add:fnameAR5510-L5TW-LTE6EA(668079),      --AR5510-L5TW-LTE6EA FRAME
			Add:fnameAR651EW(668080),                 --AR651EW FRAME
			Add:bnameAR5710-S8T2XE-LTE4CN(668188),    --AR5710-S8T2XE-LTE4CN Main Control Unit
			Add:bnameAR5510-H10T2XW1(668189),         --AR5510-H10T2XW1 Main Control Unit
			Add:bnameAR5510-L5TW(668190),             --AR5510-L5TW Main Control Unit
			Add:bnameAR5510-L5TWDS-LTE4EA(668191),    --AR5510-L5TWDS-LTE4EA Main Control Unit
			Add:bnameAR5510-L5TWDS(668192),           --AR5510-L5TWDS Main Control Unit
			Add:bnameAR5510-L5TW-LTE6EA(668193),      --AR5510-L5TW-LTE6EA Main Control Unit
			Add:bnameSIC-4STM1-V2(668194),            --SIC-4STM1-V2 Lpu Control Unit
			Add:bnameSRU-700S(668195),                --SRU-700S SRU Control Unit
			Add:bnameAR651EW(668196),                 --AR651EW Main Control Unit
		"

        REVISION "202309251900Z"
        DESCRIPTION "V14.34,
           Add: fnameATN910D-H-AC(229687),           -- V8R23C10 for ATN-910D-H-AC chassis
           Add: fnameATN910D-H-DC(229688),           -- V8R23C10 for ATN-910D-H-DC chassis
           Add: fnameNETENGINE-A812-E-S-DC(229689), -- V8R23C10 for NetEngine-A812-E-S-DC chassis
           Add: fnameNETENGINE-A822-AC(229691),      -- V8R23C10 for NetEngine-A822-AC chassis
           Add: virent8090DEVANHMHSTA0110(689121),   -- V8R23C10 for ANHMHSTA0110(SBOM) ATN 910D-H DC Basic Configuration(Includes Fixed Enable Interface (8*10GE+10*GE/Dual Power/FAN/Chassis)
           Add: virent8090DEVANHMHSTA0210(689122),   -- V8R23C10 for ANHMHSTA0210(SBOM) ATN 910D-H AC Basic Configuration(Includes Fixed Enable Interface (8*10GE+10*GE/Dual Power/FAN/Chassis)
           Add: virent8090DEVCP8PHST2EA11(689123),   -- V8R23C10 for CP8PHST2EA11(SBOM) NetEngine A812 E-S DC Chassis(10*GE/FE(o)+4*GE/FE(e))
           Add: virent8090DEVISR801BASAX2(689124),   -- V8R23C10 for ISR801BASAX2(SBOM) Mining intrinsic safety GE router KJJ12(A), NetEngine A812 E-S(10*GE/FE(o)+4*GE/FE(e))
           Add: virent8090DEVANHMHSTA0111(689125),   -- V8R23C10 for ANHMHSTA0111(SBOM) ATN 910D-H DC Basic Configuration(Includes Fixed Enable Interface (8*10GE+10*GE/Dual Power/FAN/Chassis)
           Add: virent8090DEVANHMHSTA0211(689126),   -- V8R23C10 for ANHMHSTA0211(SBOM) ATN 910D-H AC Basic Configuration(Includes Fixed Enable Interface (8*10GE+10*GE/Dual Power/FAN/Chassis)
           Add: virent8090DEVCP8PHST20A10(689127),   -- V8R23C10 for CP8PHST20A10(SBOM) NetEngine A822 AC System (2*10GE/GE/FE(o)+4*GE/FE(o)+8*GE/FE(e), Default 6*GE/FE(o)+8*GE/FE(e))
           Add: virent8090DEVCP8PHST20A12(689128),   -- V8R23C10 for CP8PHST20A12(SBOM) NetEngine A822 AC System (2*10GE/GE/FE(o)+4*GE/FE(o)+8*GE/FE(e), Default 6*GE/FE(o)+8*GE/FE(e))
           "

        REVISION "202309201900Z"
        DESCRIPTION "V14.33,
           Add: subbname8090DEV910D-H(333118),                 --card ATN 910D-H
           Add: subbname8090DEVCR8D8E5NBCC0(513222),   -- 5-Port 100GBase-QSFP28 FlexE MACsec Flexible Card CM(P1T-CM)
           Add: subbname8090DEVCR8D8E5NBCL0(513223),   -- 5-Port 100GBase-QSFP28 FlexE MACsec Flexible Card L CM(P1T-L-CM)
           Add: subbname8090DEVCR8D8LJXXCC0(513224),   -- 36-Port 10GBase LAN/WAN-SFP+ MACsec Flexible Card CM(P1T-CM)
           Add: subbname8090DEVCR8D8LJXXCL0(513225),   -- 36-Port 10GBase LAN/WAN-SFP+ MACsec Flexible Card L CM(P1T-L-CM)
           Add: subbname8090DEVCR8D82KE2NC0(513226),   -- 2-Port 400GBase-QSFP-DD FlexE + 2-Port 100GBase-QSFP28 Flexible Card CM(P2T-CM)
           Add: subbname8090DEVCR8D82KE2NL0(513227),   -- 2-Port 400GBase-QSFP-DD FlexE + 2-Port 100GBase-QSFP28 Flexible Card L CM(P2T-L-CM)
           Add: subbname8090DEVCR8D8ANBFEC0(513228),   -- 10-Port 100GBase-QSFP28 FlexE MACsec Flexible Card CM(P2T-CM)
           Add: subbname8090DEVCR8D8ANBFEL0(513229),   -- 10-Port 100GBase-QSFP28 FlexE MACsec Flexible Card L CM(P2T-L-CM)
           Add: subbname8090DEVCR8D8E5NBCE0(513230),   -- 5-Port 100GBase-QSFP28 FlexE MACsec Flexible Card E CM(P1T-E-CM)
           Add: subbname8090DEVCR8D8LJXXCE0(513231),   -- 36-Port 10GBase LAN/WAN-SFP+ MACsec Flexible Card E CM(P1T-E-CM)
           "

		REVISION "202309191700Z"
        DESCRIPTION "V14.32,
           Add: virent8090DEVCR8D8SFU9TA0(523683),   -- V8R23C10 for CR8D8SFU9TA0(SBOM) NetEngine 8800 X4 9.6Tbps Switch Fabric Unit(SFUI-9T6-A)
           "
		   
        REVISION "202309131700Z"
        DESCRIPTION "V14.31,
           The object identifier of bnamePAC2KS12PB(688590) to bnameCEX9SFU16GH(688604) are add.
           The object identifier of subbnamePAC2KS12PB(688155) to subbnamePDC2K2S12PF(688159) are add."
	   	   
        REVISION "202309131400Z"
        DESCRIPTION "V14.31,
           The object identifier of S220 and S310 are add."

		
		REVISION "202309111400Z"                                                                                  
        DESCRIPTION "V14.19,                                                                                 
         The object identifier of AP160 is add
	     The object identifier of AP361 is add"
	 
		REVISION    "202309081400Z" 	 
        DESCRIPTION "V12.28,
                     Add: virent8090DEVCR8D8MPUA1C0(205715),   -- V8R23C10 for CR8D8MPUA1C0(SBOM) NetEngine 8800 Main Processing Unit A1(MPUA1)
				     Add: virent8090DEVCR8D8MPUA2C0(364027),   -- V8R23C10 for CR8D8MPUA2C0(SBOM) NetEngine 8800 Main Processing Unit A2(MPUA2)
				     Add: virent8090DEVCR8D8SFU19A0(437796),   -- V8R23C10 for CR8D8SFU19A0(SBOM) NetEngine 8800 X4 19.2Tbps Switch Fabric Unit(SFUI-19T2-A)
				     Add: virent8090DEVCR8D8SFU19B0(376684),   -- V8R23C10 for CR8D8SFU19B0(SBOM) NetEngine 8800 X8 19.2Tbps Switch Fabric Unit(SFUI-19T2-B)
				     Add: virent8090DEVCR8D8SFU9TB0(223885),   -- V8R23C10 for CR8D8SFU9TB0(SBOM) NetEngine 8800 X8 9.6Tbps Switch Fabric Unit(SFUI-9T6-B)
				     Add: virent8090DEVCR8D8SFU9TC0(288568),   -- V8R23C10 for CR8D8SFU9TC0(SBOM) NetEngine 8800 X16 9.6Tbps Switch Fabric Unit(SFUI-9T6-C)
				     Add: virent8090DEVCR8D8SFU2TA0(667626),   -- V8R23C10 for CR8D8SFU2TA0(SBOM) NetEngine 8800 X4 2Tbps Switch Fabric Unit(SFUI-2T-A)
				     Add: virent8090DEVCR8D8SFU2TB0(490941),   -- V8R23C10 for CR8D8SFU2TB0(SBOM) NetEngine 8800 X8 2Tbps Switch Fabric Unit(SFUI-2T-B)
				     Add: virent8090DEVCR8D8SFU2TC0(287246),   -- V8R23C10 for CR8D8SFU2TC0(SBOM) NetEngine 8800 X16 2Tbps Switch Fabric Unit(SFUI-2T-C)
				     Add: virent8090DEVCR8D8E6LJKXP(329295),   -- V8R23C10 for CR8D8E6LJKXP(SBOM) 6-Port 800GBase-QSFP-DD + 36-Port 400GBase-QSFP-DD Integrated Line Processing Unit CM(LPUI-19T2-CM,Enable 6*400GE + 36*100GE by default)
				     Add: virent8090DEVCR8D8LPF2TC0(689587),   -- V8R23C10 for CR8D8LPF2TC0(SBOM) Flexible Card Line Processing Unit (LPUF-2T)
				     Add: virent8090DEVCR8D8LPF2TL0(824667),   -- V8R23C10 for CR8D8LPF2TL0(SBOM) Flexible Card Line Processing Unit L(LPUF-2T-L)
				     Add: virent8090DEVCR8D8LPF1TE0(289558),   -- V8R23C10 for CR8D8LPF1TE0(SBOM) Flexible Card Line Processing Unit E(LPUF-1T-E)
				     Add: virent8090DEVCR8D8VSUK0C3(534152),   -- V8R23C10 for CR8D8VSUK0C3(SBOM) Integrated Service Unit 400(VSUI-400-E)
				     Add: virent8090DEVCR8D8LPF1TC0(299808),   -- V8R23C10 for CR8D8LPF1TC0(SBOM) Flexible Card Line Processing Unit (LPUF-1T)
				     Add: virent8090DEVCR8D8LPF1TL0(313604),   -- V8R23C10 for CR8D8LPF1TL0(SBOM) Flexible Card Line Processing Unit L(LPUF-1T-L)
					 Add: fnameNETENGINE-8800-X4-DC(688701),      --Quidway fnameNETENGINE-8800-X4-DC for V8R23C10
                     Add: fnameNETENGINE-8800-X8-DC(688702),      --Quidway fnameNETENGINE-8800-X8-DC for V8R23C10
                     Add: fnameNETENGINE-8800-X16-DC(688703),      --Quidway fnameNETENGINE-8800-X16-DC for V8R23C10
                     Add: fnameNETENGINE-8800-X4-HVDC(688704),      --Quidway fnameNETENGINE-8800-X4-HVDC for V8R23C10
                     Add: fnameNETENGINE-8800-X8-HVDC(688705),      --Quidway fnameNETENGINE-8800-X8-HVDC for V8R23C10
                     Add: fnameNETENGINE-8800-X16-HVDC(688706),      --Quidway fnameNETENGINE-8800-X16-HVDC for V8R23C10
					 
                     "
		
        REVISION    "202308301900Z" 	 
        DESCRIPTION "V12.27,
                     Add: bnameH901HXED(148822),                --  8*XGSPON and 50GSPON combo board of MA5800.
                     Add: bnameH901AEED(148823),                --  8*EPON, 10GEPON and 50GPON combo board of MA5800.
                     Add: bnameH901ATED(148824),                --  8*GPON, XGSPON and 50GPON combo board of MA5800.
                     Add: bnameH901NCEC(148825),                --  4*100G uplink interface board of MA5800.
                     Add: bnameH901FLVF(148826),                --  16*flex-PON board of MA5800.
                     "

    REVISION "202308301700Z"                                                                                  
            DESCRIPTION "V14.26,                                                                                 
               Modify: fnameNETENGINE-8000-F2A-8K36H(688643),            --Quidway fnameNETENGINE-8000-F2A-8K36H FRAME for V8R21C00
               Modify: fnameNETENGINE-8000-F2A-8K36H-AC(688644),         --Quidway fnameNETENGINE-8000-F2A-8K36H-AC FRAME for V8R21C00
               Modify: fnameNETENGINE-8000-F2A-8K36H-DC(688645),         --Quidway fnameNETENGINE-8000-F2A-8K36H-DC FRAME for V8R21C00
               Modify: fnameNETENGINE-8000-F8(688437),           -- Quidway fnameNETENGINE-8000-F8 FRAME for V8R22C00
               Modify: fnameNETENGINE-8000E-F8(688438),          -- Quidway fnameNETENGINE-8000E-F8 FRAME for V8R22C00
               Modify: fnameNETENGINE-8000E-F8-Z(688439),        -- Quidway fnameNETENGINE-8000E-F8-Z FRAME for V8R22C00
               Modify: fnameNETENGINE-A831-E-DC(229665),    -- V8R22C00 for CP8PHST2EA10(SBOM) NetEngine-A831-E-DC chassis
               Modify: fnamePTN910D-F-AC(229540),           -- V8R22C00 for PTN910D-F-AC chassis
               Modify: fnamePTN910D-F-DC(229542),           -- V8R22C00 for PTN910D-F-DC chassis
               Modify: fnameSPNA907-AC(229547), -- V8R22C10 for SPNA907-AC chassis
               Modify: fnameHG-FM-CPE-03-A-AC(229548), -- V8R23C00 for HG-FM-CPE-03-A chassis
               Modify: fnameATN910D-B-AC(229666),           -- V8R22C00 for ATN910D-B AC chassis
               Modify: fnameATN910D-B-DC(229667),           -- V8R22C00 for ATN910D-B DC chassis
               Modify: fnameNETENGINE-8000-M1D-B-AC(229668), -- V8R22C00 for NetEngine-8000-M1D-B-AC chassis
               Modify: fnameNETENGINE-8000-M1D-B-DC(229669), -- V8R22C00 for NetEngine-8000-M1D-B-DC chassis
               Modify: fnameNETENGINE-A815-T-AC(229680), -- V8R22C00 for NetEngine-A815-T-AC chassis
               Modify: fnameNETENGINE-A825-T-DC(229681), -- V8R22C00 for NetEngine-A825-T-DC chassis
               Modify: fnameNETENGINE-A825-T-AC(229682), -- V8R22C00 for NetEngine-A825-T-AC chassis
               Modify: fnameNETENGINE-A835-T-DC(229683), -- V8R22C00 for NetEngine-A835-T-DC chassis
               Modify: fnameNETENGINE-A835-T-AC(229684), -- V8R22C00 for NetEngine-A835-T-AC chassis"

	REVISION "202308281100Z"                                                                                  
            DESCRIPTION "V14.25,                                                                                 
               Add: virent8090DEVCR8DE6LEJKXP(441886),   -- V8R23C10 for CR8DE6LEJKXP(SBOM) 6-Port 800GBase-QSFP-DD + 36-Port 400GBase-QSFP-DD Integrated Line Processing Unit CM(LPUI-19T2-CM,Enable 6*400GE + 36*100GE by default)"
			   
    REVISION "202308251700Z"                                                                                  
            DESCRIPTION "V14.24,                                                                                 
               Add: subbname8090DEVCR59LJXFF(225644),             --36-Port 10GBase LAN/WAN SFP+ Fixed Card
               Add: subbnameCARDATN910CG(333115),                 --ATN910C-G virtual card,16*10GE(o), 12*GE /GE/FE(o),4*GE/FE(e)
               Add: subbnameCARDATN910CS(333113),                 --ATN910C-S virtual card,5*10GE(o), 3*10GE /GE/FE(o),4*GE/FE(e)
               Add: subbname8090DEVCR9D00EANB83(225719),          --10-Port 100GE-QSFP28 Flexible Card CM
               Add: subbnameCARDATN910CH(333114),                 --ATN910C-H virtual card,4*10GE(o), 4*10GE /GE/FE(o),4*GE/FE(e)
			   Add: subbname8090DEVNetEngine-A812E-S(115923),     --CARD NetEngine A812E-S
		       Add: subbname8090DEVGFL72GSFB1(548682),            -- 24-Port 10GE/GE LAN/WAN-SFP+ MACsec + 48-port GE(100/1000Base-X-SFP) MACsec Physical Interface Card(PIC)
			   Add: subbname8090DEVCR8PF8HALQX2(548780),          -- 24-Port 10GE/GE LAN/WAN-SFP+ MACsec + 48-port GE(100/1000Base-X-SFP) MACsec Combined Line Processing Unit(LPUC-300)
			   Add: subbname8090DEVCR8PF8HALQX3(548781),          -- 24-Port 10GE/GE LAN/WAN-SFP+ MACsec + 48-port GE(100/1000Base-X-SFP) MACsec Combined Line Processing Unit(LPUC-300)
			   Add: subbname8090DEVCR8DE2KB00F0(548782),          -- 2-Port 400GBase-QSFP-DD Combined Line Processing Unit
			   Add: subbname8090DEVGFL2KQG(548783),               -- 2-Port 400GBase-QSFP-DD Interface Card(PIC)"

	REVISION "202308231700Z"                                                                                  
            DESCRIPTION "V14.23,                                                                                 
               Add: bnamePTN7900TPE1CXPD(229694),   --TPE1CXPD, System Control, Communication and Switch Fabric Unit,1*1
               Add: virentPTN7900TPE1VXCSD(229695),   --TPE1VXCSD,Switch Fabric Unit,1*1
               Add: bnamePTN7900TPA2FGU(229696),    --TPA2FGU, Fine Granularity Unit Functional Board"

	REVISION "202308181100Z"                                                                                  
            DESCRIPTION "V14.22,                                                                                 
               Add: virent8090DEVCR8DSFUI9TA0(265072),   -- V8R23C10 for CR8DSFUI9TA0(SBOM) NetEngine 8000 X16 9.6Tbps Switch Fabric Unit(SFUI-9T6-A)
               Add: virent8090DEVCR8DSFUI9TA1(142655),   -- V8R23C10 for CR8DSFUI9TA1(SBOM) NetEngine 8000 X16 9.6Tbps Switch Fabric Unit(SFUIA-9T6-A)
               Add: virent8090DEVCR8DSFUI9TB0(678751),   -- V8R23C10 for CR8DSFUI9TB0(SBOM) NetEngine 8000 X8 9.6Tbps Switch Fabric Unit(SFUI-9T6-B)
               Add: virent8090DEVCR8DSFUI9TB1(569258),   -- V8R23C10 for CR8DSFUI9TB1(SBOM) NetEngine 8000 X8 9.6Tbps Switch Fabric Unit(SFUIA-9T6-B)
               Add: virent8090DEVCR8D0SFUT6D1(116502),   -- V8R23C10 for CR8D0SFUT6D1(SBOM) NetEngine 8000 F 6T4 Switch Routing Unit(SRU-6T4-B)
               Add: virent8090DEVCR8D0SFUT6D2(441885),   -- V8R23C10 for CR8D0SFUT6D2(SBOM) NetEngine 8000E F 6T4 Switch Routing Unit(SRUA-6T4-B)"	
	REVISION "202308151100Z"                                                                                  
            DESCRIPTION "V14.20,                                                                                 
                Add: subbname8090DEVGPR8CQ20YSC1(548684),    -- 8-Port 100GBase-QSFP28 + 20-Port 25GBase-Y-SFP+
	        Add: subbname8090DEVCR59E8NBH(709796),       -- 16-Port 100GBase QSFP28 Integrated Line Process Unit C(NE5000E LPUI-1T6-H)"	
    REVISION "202308091100Z"                                                                                  
            DESCRIPTION "V14.20,                                                                                 
                Add: fname8031S6730-S48X6Q(537891), bname8031S6730-S48X6Q(538074)
	        Add: bname8031S5732-H48XUM2CC(537583)"	
   REVISION "202308081400Z"                                                                                  
        DESCRIPTION "V14.19,                                                                                 
         The object identifier of AirEngine 5776-26 is add
	 The object identifier of AirEngine 5773-23H is add
	 The object identifier of AirEngine 5773-22 is add"
		 
	REVISION "202308051100Z"
            DESCRIPTION "V14.18,
                The object identifier of S7706S Chassis is added
                The object identifier of S7703S Chassis is added."
        REVISION "202308041700Z"
            DESCRIPTION "V14.17,
                The object identifier of S5735I-H24U8S4XE-QA-V2 is added
                The object identifier of S5735I-S24T8S4XE-QA-V2 is added
                The object identifier of S5735I-S16T8S4XE-QD-V2 is added."

		REVISION "202308041100Z"                                                                                  
            DESCRIPTION "V14.16, 
                Add: fnameNETENGINE-8000-F1A-C(688778),         --Quidway fnameNETENGINE-8000-F1A-C FRAME for V8R23C10
                Add: virent600DEVCR8B0BKP03E1(688685),     -- V8R23C10 NetEngine-8000-F1A CR8B0BKP03E1(SBOM), F1A-C
                Add: virent600DEVCR8B0BKP03E0(688686),     -- V8R23C10 NetEngine-8000-F1A CR8B0BKP03E0(SBOM), F1A-C"

		REVISION "202308011100Z"                                                                                  
            DESCRIPTION "V14.15,                                                                                 
                Add: fname8031eKitEngineS5735S-L48P4X-A1(537873), bname8031eKitEngineS5735S-L48P4X-A1(538056)
                Add: fname8031eKitEngineS5735S-L48P4S-A1(537874), bname8031eKitEngineS5735S-L48P4S-A1(538057)
                Add: fname8031eKitEngineS5735S-L48T4X-A1(537875), bname8031eKitEngineS5735S-L48T4X-A1(538058)
                Add: fname8031eKitEngineS5735S-L48T4S-A1(537876), bname8031eKitEngineS5735S-L48T4S-A2(538059)
                Add: fname8031S5735R-48T4S-A2(537867), bname8031S5735R-48T4S-A2(538050)
                Add: fname8031S5735R-8P4S-QA2(537868), bname8031S5735R-8P4S-QA2(538051)
                Add: fname8031S5735R-24T4X-QA2(537869), bname8031S5735R-24T4X-QA2(538052)
                Add: fname8031S5735R-24T4S-QA2(537870), bname8031S5735R-24T4S-QA2(538053)
                Add: fname8031S5735R-24P4X-A2(537871), bname8031S5735R-24P4X-A2(538054)
                Add: fname8031S5735R-24P4S-A2(537872), bname8031S5735R-24P4S-A2(538055)"

		REVISION "202307311100Z"                                                                                  
            DESCRIPTION "V14.14,                                                                                 
                Add: bnamePTN7900TPD3XCS(229693),   --TPD3XCS, Switch Fabric Unit,1*1"

                REVISION "202307261400Z"                                                                                  
        DESCRIPTION "V14.13,                                                                                 
	    virent600DEVCR8D0IPU2TM3(688345),    --V8R23C00 Integrated Network Processing Unit (IPUA-2T-E), M14
            virent600DEVCR8DIPU1T2M9(688349),    --V8R23C00 Integrated Network Processing Unit (IPUA-1T2-E), M14"
		 
		 REVISION "202307251400Z"                                                                                  
        DESCRIPTION "V14.12,                                                                                 
	    The object identifier of MAP3000C-CIh is add
            The object identifier of MAP3000P-CIh is add
            The object identifier of MAP3000P-CIs is add
            The object identifier of MAP6000P-CIh is add
            The object identifier of MAP6000P-CIa is add
            The object identifier of AP663 is renamed AP661
            The object identifier of AP762 is renamed AP761"
	 
		REVISION "202307171100Z"                                                                                  
            DESCRIPTION "V14.11,                                                                                 
                Add: bnamePTN7900TPD1XCSD(229692),   --TPD1XCSD, Switch Fabric Unit,1*1"

            REVISION "202307131100Z"                                                                                  
            DESCRIPTION "V14.10,                                                                                 
                 Add: bnameCEXSFU04GL(688580),
                 Add: bnameCEXSFU08GL(688581),
                 Add: bnameCEXSFU16GL(688582),
                 Add: bnameCEXL18EQJ2(688583),
"
		 
		REVISION "202307111100Z"                                                                                  
            DESCRIPTION "V14.09,                                                                                 
                 Add: subbname8090DEVCR59EDNBE(709794),         -- 16-Port 100GBase QSFP28
                 Add: subbname8090DEVCR59E4KBC(709795),         -- 4-Port 400GBase QSFP-DD"
		
        REVISION "202307101100Z"                                                                                  
            DESCRIPTION "V14.08,                                                                                 
                 Change: subnamePAC70S12-CN(536833) ->subnamePAC80S12-CN(536833)."

		REVISION "202307061425Z"
        DESCRIPTION "V14.07,
                Add  virent8090DEVCR5D00E8KB63(562192),    -- V8R23C00 for CR5D00E8KB63(SBOM) 8-Port 400GBase QSFP-DD Integrated Line Process Unit(NE5000E LPUI-3T2-C)
                Add  virent8090DEVCR5D00EINB63(562193),    -- V8R23C00 for CR5D00EINB63(SBOM) 32-Port 100GBase QSFP28 Integrated Line Process Unit(NE5000E LPUI-3T2-C)
                Add  virent8090DEVCR5D00E8KB64(562194),    -- V8R23C00 for CR5D00E8KB64(SBOM) 8-Port 400GBase QSFP-DD Integrated Line Process Unit CM(NE5000E LPUI-3T2-C-CM)(2 ports enable)
                Add  virent8090DEVCR5D00EINB64(562195),    -- V8R23C00 for CR5D00EINB64(SBOM) 32-Port 100GBase QSFP28 Integrated Line Process Unit CM(NE5000E LPUI-3T2-C-CM)(8 ports enable)"
	 
		REVISION "202307031200Z"
        DESCRIPTION "V14.06,
			Change: bnameCEXL36DQ2YSJ2(688544) ->bnameCEXL36DQ2CQJ2(688544)
			del: bnameCESFU04GH(688513)
			Add: bnameCESFU08GH(688536)
			Add: bnameCESFU16GH(688537)
			Add: bnameCEL48CQJ2(688547)"		 
		REVISION "202306261200Z"
        DESCRIPTION "V14.05,
			Change: bnameCEMPUDFULL2C(688486) ->bnameCEMPUDCFULL2C(688486)
			Change: bnameCEMPUDHALF2C(688487)->bnameCEMPUDCHALF2C(688487)
			Add: fnameCE885132CQ4BQ(688284)
			Add: fnameCE6863E48S8CQ(688285)
			Add: bnameCE885132CQ4BQ(688578)
			Add: bnameCE6863E48S8CQ(688579)"
				
	REVISION "202306211200Z"
        DESCRIPTION "V14.04,
			Add: bnameEudemon1000E-M55(16748893),    --FW bnameEudemon1000E-M55,
			Add: bnameEudemon1000E-M10(16748894),    --FW bnameEudemon1000E-M10,
			Add: bnameEudemon1000E-S10(16748895),    --FW bnameEudemon1000E-S10,
			Add: bnameEudemon1000E-C10(16748896),    --FW bnameEudemon1000E-C10,
			Add: fnameEudemon1000E-M55(16716139),    --FW fnameEudemon1000E-M55,
			Add: fnameEudemon1000E-M10(16716140),    --FW fnameEudemon1000E-M10,
			Add: fnameEudemon1000E-S10(16716141),    --FW fnameEudemon1000E-S10,
			Add: fnameEudemon1000E-C10(16716142),    --FW fnameEudemon1000E-C10,
			The object identifier of USG6305F       is delete,
			The object identifier of USG6309F       is delete,
			Change: bnameUSG6520F-K(16748868),    --FW bnameUSG6520F-K,
			Change: bnameUSG6560F-K(16748869),    --FW bnameUSG6560F-K,
			Change: bnameUSG6590F-K(16748870),    --FW bnameUSG6590F-K,
			Add:  --FW Antiddos1905-N,
			Add: subbnameSPCB-E9KE-02-L       (16728152),
			Add: subbnameSPCC-E9KE-01         (16728155),
			The object identifier of IPS6620F-K-AC is changed,
			The object identifier of Eudemon1000E-F205-AC is changed,
			The object identifier of fnameUSG6305F-C is add,
			The object identifier of USG6510F-DLP is changed,
			The object identifier of USG6530F-DLP is changed."
    REVISION "202306191500Z"
        DESCRIPTION "V14.03,
            The object identifier of AirEngine 9703-H is add	
            The object identifier of AirEngine 9703-S is add
            The object identifier of AirEngine 9703-H-T is add	
            The object identifier of AirEngine 9703-S-T is add
            The object identifier of AP663 is add
            The object identifier of AP762 is add
            The object identifier of AirEngine 9500-LP is add
            The object identifier of AirEngine 5773-23HW is add
            The object identifier of AirEngine 5773-21 is add
            The object identifier of AirEngine 6776-56T is add
            The object identifier of AirEngine 6776-57 is add."
			
    REVISION "202306091000Z"
        DESCRIPTION "V14.02,
                Add:bnameAR5710S-S8T2X(668186),             --AR5710S-S8T2X Main Control Unit
                Add:bnameAR5710S-S10T1X2(668187),           --AR5710S-S10T1X2 Main Control Unit
                Add:fnameAR5710S-S8T2X(668071),             --AR5710S-S8T2X FRAME
                Add:fnameAR5710S-S10T1X2(668072),           --AR5710S-S10T1X2 FRAME"

    REVISION "202306061500Z"
        DESCRIPTION "V14.01,
            The object identifier of S5735I-H8T4S2XN is added."

   REVISION "202305191100Z"                                                                                  
        DESCRIPTION "V14.00,                                                                                 
        The object identifier of S5755-H24UTM4X4Y2C-T     is add.
            The object identifier of S5755-H48UTM4X4Y2C-T     is add.
            The object identifier of S5735-L14P2S-TQA-V2      is add.
            The object identifier of S5535-L16LP2UM2X-QA-V2   is add.
            The object identifier of S5535-L24ST4XE-A-V2      is add.
            The object identifier of S5535-S24HS4XE-V2        is add.
            The object identifier of S5335-L8T4X-QA-V2        is add.
            The object identifier of S5335-L8T4S-A-V2         is add.
            The object identifier of S5335-L8P4X-QA-V2        is add.
            The object identifier of S5335-L24T4X-QA-V2       is add.
            The object identifier of S5335-L24T4XE-A-V2       is add.
            The object identifier of S5735-L48S4X-A-V2        is add.
            The object identifier of PAC70S12-CN              is add."

			REVISION    "202305180000Z"
              DESCRIPTION "V13.99,
               Add: virent8090DEVTPVM0HOSTA04(689209),  -- V8R23C00 for TPVM0HOSTA04(SBOM) PTN 917-F,TPVM0HOSTA04,PTN 917-F - AC Power,with 2*10GE Fine Granularity Unit(o),6*GE/FE(o),4*GE/FE(e)
			   Add: virent8090DEVCR8DVSUPA0F0(679991),    -- V8R23C00 for CR8DVSUPA0F0(SBOM) Integrated Service Card 100(VSUP-100)
               Add: virent8090DEVCR8DVSUPA0F1(679992),    -- V8R23C00 for CR8DVSUPA0F1(SBOM) Integrated Service Card 100(VSUPA-100)
			   Add: virent8090DEVCR8DGSUPA0C0(679796),    -- V8R23C00 for CR8DGSUPA0C0(SBOM) Multi-function Integrated Service Card(VSUP-100)
               Add: virent8090DEVCR8DGSUPA0C1(679797),    -- V8R23C00 for CR8DGSUPA0C1(SBOM) Multi-function Integrated Service Card(VSUPA-100)
			   Add: virent8090DEVCR8DVSUIK0C3(676828),    -- V8R23C00 for CR8DVSUIK0C3(SBOM) Integrated Service Unit 400(VSUI-400-E)
               Add: virent8090DEVCR8DVSUIK0C4(676829),    -- V8R23C00 for CR8DVSUIK0C4(SBOM) Integrated Service Unit 400(VSUI-400A-E)
			   Add: virent8090DEVCR8DLPUFT171(689369),   -- V8R23C00 for CR8DLPUFT171(SBOM) Flexible Card Line Processing Unit(LPUF-1T)
               Add: virent8090DEVCR8DLPUFT072(689370),   -- V8R23C00 for CR8DLPUFT072(SBOM) Flexible Card Line Processing Unit (LPUF-1TA)
               Add: virent8090DEVCR81LPUFT072(689371),   -- V8R23C00 for CR81LPUFT072(SBOM) Flexible Card Line Processing Unit (LPUF-1TA)
               Add: virent8090DEVCR8DLPUFT172(689372),   -- V8R23C00 for CR8DLPUFT172(SBOM) Flexible Card Line Processing Unit (LPUF-1TA)
               Add: virent8090DEVCR8DLPUFT0D1(689373),   -- V8R23C00 for CR8DLPUFT0D1(SBOM) Flexible Card Line Processing Unit(LPUF-2T)
               Add: virent8090DEVCR8DLPUFT0D2(689374),   -- V8R23C00 for CR8DLPUFT0D2(SBOM) Flexible Card Line Processing Unit(LPUF-2TA)
               Add: virent8090DEVCR8DLPUFT182(689376),   -- V8R23C00 for CR8DLPUFT182(SBOM) Flexible Card Line Processing Unit (LPUF-1TA-E)
               Add: virent8090DEVCR8DLPUFT181(689375),   -- V8R23C00 for CR8DLPUFT181(SBOM) Flexible Card Line Processing Unit (LPUF-1T-E)
			   Add: virent8090DEVANHMHSTA0700(229698),   -- V8R23C00 for ANHMHSTA0700(SBOM) ATN 910D-C, DC Power, Port Capacity 2*400G/100G+2*100GE+16*25G/10G/GE+8*25G/10G/GE, default all the GE/FE ports is enabled
               Add: virent8090DEVANHMHSTA0800(229699),   -- V8R23C00 for ANHMHSTA0800(SBOM) ATN 910D-C, AC Power, Port Capacity 2*400G/100G+2*100GE+16*25G/10G/GE+8*25G/10G/GE, default all the GE/FE ports is enabled
            "
        
            REVISION    "202305120000Z"
              DESCRIPTION "V13.98,
               Add: virent8090DEVANND02CXPAE1(228005),  -- V8R23C00 ATN 980C,ANN3CXPA20,System Control,Cross-connect and Multi-protocol Process Unit with 800G
            "

            REVISION    "202305060000Z"
              DESCRIPTION "V13.97,
                Add: subbname8090DEVCR8DE1N8XFM0(548680),   -- 1-Port 100GBase-QSFP28 FlexE MACsec + 8-Port 10GBase-SPF+ MACsec Physical Interface Card(PIC)
                Add: subbname8090DEVCR5DE1N8XFM0(548681),   -- 1-Port 100GBase/50GBase-QSFP28 FlexE MACsec or 8-port 10GE(SFP+)/GE(SFP) MACsec Physical Interface Card(PIC)
            "

			REVISION    "202304230000Z"
              DESCRIPTION "V13.96,
				Add: bnameUSG6305F-C(16748837),    --FW bnameUSG6305F-C,
				Add: bnameUSG6505F-C(16748838),    --FW bnameUSG6505F-C,
				Add: bnameUSG6606F-C(16748839),    --FW bnameUSG6606F-C,
				Add: bnameIPS6525F(16748840),    --FW bnameIPS6525F,
				Add: bnameIPS6525FD(16748841),    --FW bnameIPS6525FD,
				Add: bnameIPS6585FD(16748842),    --FW bnameIPS6585FD,
				Add: bnameIPS6615FD(16748843),    --FW bnameIPS6615FD,
				Add: bnameIPS6625FD(16748844),    --FW bnameIPS6625FD,
				Add: bnameUSG6307F-D(16748846),    --FW bnameUSG6307F-D,
				Add: bnameUSG6311F-D(16748847),    --FW bnameUSG6311F-D,
				Add: bnameUSG6331F-D(16748848),    --FW bnameUSG6331F-D,
				Add: bnameUSG6510F-D(16748849),    --FW bnameUSG6510F-D,
				Add: bnameUSG6530F-D(16748850),    --FW bnameUSG6530F-D,
				Add: bnameUSG6510F-DK(16748851),    --FW bnameUSG6510F-DK,
				Add: bnameUSG6510F-DL(16748852),    --FW bnameUSG6510F-DL,
				Add: bnameUSG6530F-DL(16748853),    --FW bnameUSG6530F-DL,
				Add: bnameUSG6306F(16748854),    --FW bnameUSG6306F,
				Add: bnameUSG6308F(16748855),    --FW bnameUSG6308F,
				Add: bnameUSG6315F(16748856),    --FW bnameUSG6315F,
				Add: bnameUSG6325F(16748857),    --FW bnameUSG6325F,
				Add: bnameUSG6335F(16748858),    --FW bnameUSG6335F,
				Add: bnameUSG6355F(16748859),    --FW bnameUSG6355F,
				Add: bnameUSG6365F(16748860),    --FW bnameUSG6365F,
				Add: bnameUSG6385F(16748861),    --FW bnameUSG6385F,
				Add: bnameIPS6309F(16748862),    --FW bnameIPS6309F,
				Add: bnameIPS6315F(16748863),    --FW bnameIPS6315F,
				Add: bnameUSG6525F(16748864),    --FW bnameUSG6525F,
				Add: bnameUSG6555F(16748865),    --FW bnameUSG6555F,
				Add: bnameUSG6565F(16748866),    --FW bnameUSG6565F,
				Add: bnameUSG6585F(16748867),    --FW bnameUSG6585F,
				Add: bnameUSG6560F-K(16748868),    --FW bnameUSG6560F-K,
				Add: bnameUSG6590F-K(16748869),    --FW bnameUSG6590F-K,
				Add: bnameUSG6520F-K(16748870),    --FW bnameUSG6520F-K,
				Add: bnameIPS6520F-K(16748871),    --FW bnameIPS6520F-K,
				Add: bnameEudemon1000E-F08(16748872),    --FW bnameEudemon1000E-F08,
				Add: bnameUSG6302F-C(16748873),    --FW bnameUSG6302F-C,
				Add: bnameUSG6502F-C(16748874),    --FW bnameUSG6502F-C,
				Add: bnameUSG6303E(16748877),    --FW bnameUSG6303E,
				Add: bnameLPUA-12CQ24XS(16748878),    --FW bnameLPUA-12CQ24XS,
				Add: bnameLPUA-E-12CQ24XS(16748879),    --FW bnameLPUA-E-12CQ24XS,
				Add: bnameSFUA-USG12008(16748880),    --FW bnameSFUA-USG12008-v2(USG V600R022C10),
				Add: bnameSFUA-E9KE-X8(16748881),    --FW bnameSFUA-E9KE-X8-v2(USG V600R022C10),
				Add: bnameSFUA-IPS12008(16748882),    --FW bnameSFUA-IPS12008-v2(USG V600R022C10),
				Add: bnameMPUD-E9KE-X16(16748883),    --FW bnameMPUD-E9KE-X16,
				Add: bnameMPUD-E9KE-X16-T(16748884),    --FW bnameMPUD-E9KE-X16-T,
				Add: bnameMPUD-ADS-X16(16748885),    --FW bnameMPUD-ADS-X16,
				Add: bnameMPUD-ADS-X16-T(16748886),    --FW bnameMPUD-ADS-X16-T,
				Add: bnameSFUA-USG12016(16748887),    --FW bnameSFUA-USG12016,
				Add: bnameSFUA-E9KE-X16(16748888),    --FW bnameSFUA-E9KE-X16,
				Add: bnameSPUC-E9KE-02(16748892),    --FW bnameSPUC-E9KE-02,
				Add: bnameEudemon1000E-T1(16748902),    --FW bnameEudemon1000E-T1,
				Add: bnameUSG6621F-O(16748903),    --FW bnameUSG6621F-O,
				Add: bnameUSG6620F-O(16748904),    --FW bnameUSG6620F-O,
				Add: bnameSIC-4GE-BC(16748905),    --FW bnameSIC-4GE-BC,
				Add: bnameUSG6510F-DPL(16748906),    --FW bnameUSG6510F-DPL,
				Add: bnameUSG6530F-DPL(16748907),    --FW bnameUSG6530F-DPL,
				Add: bnameUSG6303F(16748908),    --FW bnameUSG6303F,
				Add: bnameEudemon1000E-C1A(16748909),    --FW bnameEudemon1000E-C1A,
				Add: bnameEudemon1000E-C5A(16748910),    --FW bnameEudemon1000E-C5A,
				Add: bnameEudemon1000E-C8A(16748911),    --FW bnameEudemon1000E-C8A,
				Add: bnameEudemon1000E-M1A(16748912),    --FW bnameEudemon1000E-M1A,
				Add: bnameEudemon1000E-M2A(16748913),    --FW bnameEudemon1000E-M2A,
				Add: bnameEudemon1000E-M3A(16748914),    --FW bnameEudemon1000E-M3A,
				Add: bnameEudemon1000E-M5A(16748915),    --FW bnameEudemon1000E-M5A,
				Add: bnameEudemon1000E-S1A(16748916),    --FW bnameEudemon1000E-S1A,
				Add: bnameEudemon1000E-S5A(16748917),    --FW bnameEudemon1000E-S5A,
				Add: bnameEudemon1000E-S8A(16748918),    --FW bnameEudemon1000E-S8A,
				Add: bnameEudemon1000E-T1A(16748919),    --FW bnameEudemon1000E-T1A,
				Add: bnameEudemon1000E-T3A(16748920),    --FW bnameEudemon1000E-T3A,
				Add: bnameEudemon1000E-T5A(16748921),    --FW bnameEudemon1000E-T5A,
				Add: bnameUSG6305F(16748922),    --FW bnameUSG6305F,
				Add: bnameProbe1001(16748923),    --FW bnameProbe1001,
				Add: bnameEudemon1000E-F01(16748924),    --FW bnameEudemon1000E-F01,
				Add: bnameEudemon1000E-F05(16748925),    --FW bnameEudemon1000E-F05,
				Add: bnameUSG6680E-ACC(16748926),    --FW bnameUSG6680E-ACC,
				Add: bnameUSG6309F(16748927),    --FW bnameUSG6309F,
				Add: bnameSGA1POE-D-1*1(16748928),    --FW bnameSGA1POE-D-1*1,
				Add: bnameEudemon1000E-C10A(16748929),    --FW bnameEudemon1000E-C10A,
				Add: bnameEudemon1000E-S10A(16748930),    --FW bnameEudemon1000E-S10A,
				Add: bnameEudemon1000E-M10A(16748931),    --FW bnameEudemon1000E-M10A,
				Add: bnameEudemon1000E-T10A(16748932),    --FW bnameEudemon1000E-T10A,
				Add: fnameUSG6505F-C(16716067),   -- Assembling Components,fnameUSG6505F-C,
				Add: fnameUSG6606F-C(16716068),   -- Assembling Components,fnameUSG6606F-C,
				Add: fnameIPS6525F(16716069),   -- Assembling Components,fnameIPS6525F,
				Add: fnameIPS6525FD(16716070),   -- Assembling Components,fnameIPS6525FD,
				Add: fnameIPS6585FD(16716071),   -- Assembling Components,fnameIPS6585FD,
				Add: fnameIPS6615FD(16716072),   -- Assembling Components,fnameIPS6615FD,
				Add: fnameIPS6625FD(16716073),   -- Assembling Components,fnameIPS6625FD,
				Add: fnameUSG6307F-D(16716075),   -- Assembling Components,fnameUSG6307F-D,
				Add: fnameUSG6311F-D(16716076),   -- Assembling Components,fnameUSG6311F-D,
				Add: fnameUSG6331F-D(16716077),   -- Assembling Components,fnameUSG6331F-D,
				Add: fnameUSG6510F-D(16716078),   -- Assembling Components,fnameUSG6510F-D,
				Add: fnameUSG6530F-D(16716079),   -- Assembling Components,fnameUSG6530F-D,
				Add: fnameUSG6510F-DK(16716080),   -- Assembling Components,fnameUSG6510F-DK,
				Add: fnameUSG6510F-DL(16716081),   -- Assembling Components,fnameUSG6510F-DL,
				Add: fnameUSG6530F-DL(16716082),   -- Assembling Components,fnameUSG6530F-DL,
				Add: fnameUSG6306F(16716083),   -- Assembling Components,fnameUSG6306F,
				Add: fnameUSG6308F(16716084),   -- Assembling Components,fnameUSG6308F,
				Add: fnameUSG6315F(16716085),   -- Assembling Components,fnameUSG6315F,
				Add: fnameUSG6325F(16716086),   -- Assembling Components,fnameUSG6325F,
				Add: fnameUSG6335F(16716087),   -- Assembling Components,fnameUSG6335F,
				Add: fnameUSG6355F(16716088),   -- Assembling Components,fnameUSG6355F,
				Add: fnameUSG6365F(16716089),   -- Assembling Components,fnameUSG6365F,
				Add: fnameUSG6385F(16716090),   -- Assembling Components,fnameUSG6385F,
				Add: fnameIPS6309F(16716091),   -- Assembling Components,fnameIPS6309F,
				Add: fnameIPS6315F(16716092),   -- Assembling Components,fnameIPS6315F,
				Add: fnameUSG6525F(16716093),   -- Assembling Components,fnameUSG6525F,
				Add: fnameUSG6555F(16716094),   -- Assembling Components,fnameUSG6555F,
				Add: fnameUSG6565F(16716095),   -- Assembling Components,fnameUSG6565F,
				Add: fnameUSG6585F(16716096),   -- Assembling Components,fnameUSG6585F,
				Add: fnameUSG6520F-K(16716097),   -- Assembling Components,fnameUSG6520F-K,
				Add: fnameUSG6560F-K(16716098),   -- Assembling Components,fnameUSG6560F-K,
				Add: fnameUSG6590F-K(16716099),   -- Assembling Components,fnameUSG6590F-K,
				Add: fnameIPS6520F-K(16716100),   -- Assembling Components,fnameIPS6520F-K,
				Add: fnameEudemon1000E-F08(16716101),   -- Assembling Components,fnameEudemon1000E-F08,
				Add: fnameUSG6302F-C(16716102),   -- Assembling Components,fnameUSG6302F-C,
				Add: fnameUSG6502F-C(16716103),   -- Assembling Components,fnameUSG6502F-C,
				Add: fnameUSG6303E(16716106),   -- Assembling Components,fnameUSG6303E,
				Add: fnameEudemon9000E-X16(16716107),   -- Assembling Components,fnameEudemon9000E-X16,
				Add: fnameUSG12016(16716108),   -- Assembling Components,fnameUSG12016,
				Add: fnameAntiDDoS12016(16716109),   -- Assembling Components,fnameAntiDDoS12016,
				Add: fnameEudemon1000E-T1(16716110),   -- Assembling Components,fnameEudemon1000E-T1,
				Add: fnameUSG6621F-O(16716111),   -- Assembling Components,fnameUSG6621F-O,
				Add: fnameUSG6620F-O(16716112),   -- Assembling Components,fnameUSG6620F-O,
				Add: fnameUSG6510F-DPL(16716113),   -- Assembling Components,fnameUSG6510F-DPL,
				Add: fnameUSG6510F-DPL(16716113),   -- Assembling Components,fnameUSG6510F-DPL,
				Add: fnameUSG6530F-DPL(16716114),   -- Assembling Components,fnameUSG6530F-DPL,
				Add: fnameUSG6530F-DPL(16716114),   -- Assembling Components,fnameUSG6530F-DPL,
				Add: fnameUSG6303F(16716115),   -- Assembling Components,fnameUSG6303F,
				Add: fnameEudemon1000E-C1A(16716116),   -- Assembling Components,fnameEudemon1000E-C1A,
				Add: fnameEudemon1000E-C5A(16716117),   -- Assembling Components,fnameEudemon1000E-C5A,
				Add: fnameEudemon1000E-C8A(16716118),   -- Assembling Components,fnameEudemon1000E-C8A,
				Add: fnameEudemon1000E-M1A(16716119),   -- Assembling Components,fnameEudemon1000E-M1A,
				Add: fnameEudemon1000E-M2A(16716120),   -- Assembling Components,fnameEudemon1000E-M2A,
				Add: fnameEudemon1000E-M3A(16716121),   -- Assembling Components,fnameEudemon1000E-M3A,
				Add: fnameEudemon1000E-M5A(16716122),   -- Assembling Components,fnameEudemon1000E-M5A,
				Add: fnameEudemon1000E-S1A(16716123),   -- Assembling Components,fnameEudemon1000E-S1A,
				Add: fnameEudemon1000E-S5A(16716124),   -- Assembling Components,fnameEudemon1000E-S5A,
				Add: fnameEudemon1000E-S8A(16716125),   -- Assembling Components,fnameEudemon1000E-S8A,
				Add: fnameEudemon1000E-T1A(16716126),   -- Assembling Components,fnameEudemon1000E-T1A,
				Add: fnameEudemon1000E-T3A(16716127),   -- Assembling Components,fnameEudemon1000E-T3A,
				Add: fnameEudemon1000E-T5A(16716128),   -- Assembling Components,fnameEudemon1000E-T5A,
				Add: fnameUSG6305F(16716129),   -- Assembling Components,fnameUSG6305F,
				Add: fnameProbe1001(16716130),   -- Assembling Components,fnameProbe1001,
				Add: fnameEudemon1000E-F01(16716131),   -- Assembling Components,fnameEudemon1000E-F01,
				Add: fnameEudemon1000E-F05(16716132),   -- Assembling Components,fnameEudemon1000E-F05,
				Add: fnameUSG6680E-ACC(16716133),   -- Assembling Components,fnameUSG6680E-ACC,
				Add: fnameUSG6309F(16716134),   -- Assembling Components,fnameUSG6309F,
				Add: fnameEudemon1000E-C10A(16716135),   -- Assembling Components,fnameEudemon1000E-C10A,
				Add: fnameEudemon1000E-S10A(16716136),   -- Assembling Components,fnameEudemon1000E-S10A,
				Add: fnameEudemon1000E-M10A(16716137),   -- Assembling Components,fnameEudemon1000E-M10A,
				Add: fnameEudemon1000E-T10A(16716138),   -- Assembling Components,fnameEudemon1000E-T10A,
            "
	
			REVISION    "202304210000Z"
              DESCRIPTION "V13.95,
                Add: bnameCESFU04GH2(688513), 
				Add: bnameCEXSFU04GH(688533) to bnameCE6855M48XS8CQ(688577),  
				Add: fnameCE6885H48YS8CQ(688265) to fnameCE16880X16(688283),  
				Add: subbnameCE88D8YS4DQH(688150) to subbnameCE88D24T2CQH(688154),  
            "
			   
			REVISION    "202304180000Z"
              DESCRIPTION "V13.94,
                Changed the name of AirEngine 9700-S-T to AirEngine 9701-L-T AirEngine 9700-S to AirEngine 9701-L
            "
			

            REVISION    "202304170000Z"
              DESCRIPTION "V13.93,
                Add: subbname8090DEVCR8DE1KB00F0(548778),   -- 1-Port 400GBase-QSFP-DD Combined Line Processing Unit CM Basic Setup Bundle(Including LPUC-400-CM, default enable 100G)
                Add: subbname8090DEVCR8DE8NB00F0(548779),   -- 8-Port 100GBase-QSFP28 Combined Line Processing Unit(LPUC-800-CM)
                Add: subbname8090DEVGFL1KQG(548679),        -- 1-Port 400GBase-QSFP-DD Interface Card(PIC)
                Add: subbname8090DEVGFL8CQG(548678),        -- 8-Port 100GBase-QSFP28 Interface Card(PIC)
            "
			
			REVISION    "202304130000Z"
              DESCRIPTION "V13.92,
                Add: virent8090DEVCR8B0BKP03CA(689207),  -- V8R23C00 for CR8B0BKP03CA(SBOM) NetEngine 8000 F1A-8H20Q Integrated Chassis Components(Port-side Intake)
                Add: virent8090DEVCR8B0BKP03CB(689208),  -- V8R23C00 for CR8B0BKP03CB(SBOM) NetEngine 8000 F1A-8H20Q Integrated Chassis Components(Port-side Exhaust)
            "

            REVISION    "202304110000Z"
              DESCRIPTION "V13.91,
                Add: bnameH906CSHF(148812),                --  16*XGS combo board of MA5800.
                Add: bnameH901HXHD(148813),                --  8*50GPON board of MA5800.
                Add: bnameH906FLHF(148814),                --  16*XGS combo board of MA5800.
                Add: bnameH902FLSF(148815),                --  16*XGS combo board of MA5800.
                Add: bnameH906FLHFE(148816),               --  16*XGS combo board of EA5800.
                Add: bnameH906CSHFE(148817),               --  16*XGS combo board of EA5800.
                Add: bnameH901FLHH(148818)                 --  32*flex-PON board of MA5800.
                Add: bnameH901FLPF(148819),                --  16*flex-PON board of MA5800.
                Add: bnameH901MPSH(148820)                 --  control board of MA5800-X2.
            "

                REVISION    "202304100000Z"	
        DESCRIPTION "V13.90
                Add:fnameHG-FM-CPE-03-A-AC(229548), -- V8R23C00 for HG-FM-CPE-03-A chassis
                Add:virent8090DEVHGFM0HOSTD00(229539),           -- V8R23C00 for HGFM0HOSTD00(SBOM) HG-FM CPE-03-A AC Power,with 2*10GE Fine Granularity Unit(o),6*GE/FE(o),4*GE/FE(e)
            "

                REVISION    "202304060000Z"	
        DESCRIPTION "V13.86
                Add:virent8090DEVANHMHSTA0504(689119),  -- V8R23C00 for ANHMHSTA0602(SBOM) ATN910D-B,DCPower,PortCapacity4*25GE/10GE/GE+6*10GE/GE+10*GE(o)+4*GE(e),default4*25GEandallGE/FEports
                Add:virent8090DEVANHMHSTA0604(689120),  -- V8R23C00 for ANHMHSTA0602(SBOM) ATN910D-B,ACPower,PortCapacity4*25GE/10GE/GE+6*10GE/GE+10*GE(o)+4*GE(e),default4*25GEandallGE/FEports
            "

          REVISION "202304031100Z"
        DESCRIPTION "V13.88,
                add: fnameCE685548XS8CQ(688251), 
                add: fnameCE6885LL56F(688252), 
                add: fnameCE688548YS8CQ(688253), 
                add: fnameCE688548YS8CQT(688254), 
                add: fnameCE6885SAN56F(688256), 
                add: fnameCE885532CQ4BQ(688257), 
                add: fnameCE16800X4(688258), 
                add: fnameCE16800X8(688259), 
                add: fnameCE16800X16(688260), 
                add: fnameCE585548T4XS(688262), 
                add: fnameCE5855SH48T4XS(688263), 
                add: fnameCE5855SL48T4XS(688264), 
                add: bnameCE685548XS8CQ(688496), 
                add: bnameCE6885LL56F(688497), 
                add: bnameCE688548YS8CQ(688498), 
                add: bnameCE688548YS8CQT(688499), 
                add: bnameCE6885SAN56F(688501), 
                add: bnameCE885532CQ4BQ(688502), 
                add: bnameCE585548T4XS(688527), 
                add: bnameCE5855SH48T4XS(688528), 
                add: bnameCE5855SL48T4XS(688529), 
                add: bnameCEXL48YSJ(688516), 
                add: bnameCEXL48YSAJ(688517), 
                add: bnameCEXL24CQJ(688518), 
                add: bnameCEXL36LQJ(688519), 
                add: bnameCEXL36CQJ(688520), 
                add: bnameCEXSFU04G(688506), 
                add: bnameCEXSFU08G(688507), 
                add: bnameCEXSFU16G(688508), 
                add: bnameCEXMPUDH(688523), 
                add: bnameCEXMPUDF(688524), 
                add: bnameCEXMPUEH(688525), 
                add: bnameCEXMPUEF(688526), 
                add: bnameCEL48YSJ(688504), 
                add: bnameCEL48YSAJ(688505), 
                add: bnameCEL24CQJ(688510), 
                add: bnameCEL36LQJ(688509), 
                add: bnameCEL36CQJ(688503), 
                add: bnameCESFU08GL2(688511), 
                add: bnameCESFU04GL2(688512), 
                add: bnameCESFU16GL2(688514), 
                add: bnamePAC600S12PF(688530), 
                add: bnamePAC1K2S12PF(688531), 
                add: bnamePDC1K2S12PB(688532), 
                add: subbnamePAC600S12P(688149), 
                add: subbnamePAC1K2S12PF(688147), 
                add: subbnamePDC1K2S12PB(688148),
				"

          REVISION    "202304011000Z"
             DESCRIPTION "V13.87,
               The object identifier of 5755-H48T4Y2CZ is added.
               The object identifier of 5755-H48P4Y2CZ is added.
               The object identifier of 5755-H48U4Y2CZ is added.
               The object identifier of 5755-H24T4Y2CZ is added.
               The object identifier of 5755-H24P4Y2CZ is added.
               The object identifier of 5755-H24U4Y2CZ is added.
               The object identifier of 5755-H24UTM4X4Y2C is added.
               The object identifier of 5755-H48UTM4X4Y2C is added.
               The object identifier of 5755-H24N4Y-A is added.
               The object identifier of 5355-H24N4Y-A is added.
               The object identifier of 5755-H48N4Y-A is added.
               The object identifier of 5355-H48N4Y-A is added.
               The object identifier of 5755-H24UN4Y2CZ is added.
               The object identifier of 5755-H48UN4Y2CZ is added.
               The object identifier of 5735-L24ST4XE-A-V2 is added.
               The object identifier of 5735-L48S4XE-A-V2 is added.
               The object identifier of 5331-S32ST4X-A-V1 is added.
               The object identifier of 5335-L48S4X-A-V2 is added.
               The object identifier of 5735-S48S4XE-V2 is added.
               The object identifier of 5735-S48S4X-V2 is added.
               The object identifier of 5331-S48S4X-V1 is added.
               The object identifier of 5735-L14P2S-QA-V2 is added.
               The object identifier of 5735-L16LP2X-QA-V2 is added.
               The object identifier of 5735-L16P2UM2X-QA-V2 is added.
               The object identifier of 5735-L16LP2UM2X-QA-V2 is added.
               The object identifier of 5335-L16LP2UM2X-QA-V2 is added.
               The object identifier of 5335-L24ST4XE-A-V2 is added.
               The object identifier of 5735-S24HS4XE-V2 is added.
               The object identifier of 5735-S24ST4XE-V2 is added.
               The object identifier of 5335-S24ST4XE-V2 is added.
               The object identifier of 5735-S48HS4XE-V2 is added.
               The object identifier of LSG7C04HX1E0 is added.
               The object identifier of LSG700VSX1E0 is added."

            REVISION    "202303310000Z"
              DESCRIPTION "V13.86
                add: bnameGPFANCBE(564539),  --V8R23C00 NetEngine-8000-X GPFANCBE
            "
		    REVISION    "202303280000Z"
              DESCRIPTION "V13.85
                add: subbname8090DEVCR8DEKNBXFF0(548775),   -- 4-Port 100GBase-QSFP28 + 40-port 10GE/GE LAN/WAN-SFP+ Combined Line Processing Unit(LPUC-800-CM)
                add: subbname8090DEVGFL4CQ40XSG(548677),   -- 4-Port 100GBase-QSFP28 + 40-port 10GE/GE LAN/WAN-SFP+ Interface Card(PIC)
            "
		 
            REVISION    "202303270000Z"
              DESCRIPTION "V13.84
                add: fnameAR617VW-LTE4(668070),   --AR617VW-LTE4 FRAME
                add: bnameAR617VW-LTE4(668185),   --AR617VW-LTE4 Main Control Unit
            "
            REVISION    "202303240000Z"
              DESCRIPTION "V13.83
                Add:virent8090DEVCR8D0SFUT6D0(800108),    -- V8R23C00 CR8D0SFUT6D0(SBOM) NetEngine 8000 F 6T4 Switch Routing Unit(SRU-6T4-A)
            "
            REVISION    "202303210000Z"
              DESCRIPTION "V13.82
                Add:bnameAR5710-S10T1X2(668055),         --AR5710-S10T1X2 Main Control Unit
                Add:bnameAR5710-S8P2X(668056),           --AR5710-S8P2X Main Control Unit
                Add:bnameAR5710-S8P2X-LTE4CN(668057),    --AR5710-S8P2X-LTE4CN Main Control Unit
                Add:bnameAR5710-S8T2X(668058),           --AR5710-S8T2X Main Control Unit
                Add:bnameAR5710-S8T2X-LTE4EA(668059),    --AR5710-S8T2X-LTE4EA Main Control Unit
                Add:bnameAR5710-S8T2XE(668060),          --AR5710-S8T2XE Main Control Unit
                Add:bnameAR5710-S8T2XE-LTE4EA-T(668061), --AR5710-S8T2XE-LTE4EA-T Main Control Unit
                Add:bnameAR5710-S8T2XE-NRCN(668062),     --AR5710-S8T2XE-NRCN Main Control Unit
                Add:bnameAR6710-L14T2X4(668063),         --AR6710-L14T2X4 Main Control Unit
                Add:bnameAR5510-S10T1X2(668064),         --AR5510-S10T1X2 Main Control Unit
                Add:bnameAR5510-S8P2X(668065),           --AR5510-S8P2X Main Control Unit
                Add:bnameAR5510-S8P2X-LTE4CN(668066),    --AR5510-S8P2X-LTE4CN Main Control Unit
                Add:bnameAR5510-S8T2X(668067),           --AR5510-S8T2X Main Control Unit
                Add:bnameAR5510-S8T2X-LTE4EA(668068),    --AR5510-S8T2X-LTE4EA Main Control Unit
                Add:bnameAR5510-S8T2XE-NRCN(668069),     --AR5510-S8T2XE-NRCN Main Control Unit
                Add:bnameSIC-4GET-V2(668184),            --SIC-4GET-V2 Lpu Control Unit
                Add:fnameAR5710-S10T1X2(668169),         --AR5710-S10T1X2 FRAME
                Add:fnameAR5710-S8P2X(668170),           --AR5710-S8P2X FRAME
                Add:fnameAR5710-S8P2X-LTE4CN(668171),    --AR5710-S8P2X-LTE4CN FRAME
                Add:fnameAR5710-S8T2X(668172),           --AR5710-S8T2X FRAME
                Add:fnameAR5710-S8T2X-LTE4EA(668173),    --AR5710-S8T2X-LTE4EA FRAME
                Add:fnameAR5710-S8T2XE(668174),          --AR5710-S8T2XE FRAME
                Add:fnameAR5710-S8T2XE-NRCN(668175),     --AR5710-S8T2XE-NRCN FRAME
                Add:fnameAR6710-L14T2X4(668176),         --AR6710-L14T2X4 FRAME
                Add:fnameAR5510-S10T1X2(668177),         --AR5510-S10T1X2 FRAME
                Add:fnameAR5510-S8P2X(668178),           --AR5510-S8P2X FRAME
                Add:fnameAR5510-S8P2X-LTE4CN(668179),    --AR5510-S8P2X-LTE4CN FRAME
                Add:fnameAR5510-S8T2X(668180),           --AR5510-S8T2X FRAME
                Add:fnameAR5510-S8T2X-LTE4EA(668181),    --AR5510-S8T2X-LTE4EA FRAME
                Add:fnameAR5510-S8T2XE-NRCN(668182),     --AR5510-S8T2XE-NRCN FRAME
            "
            REVISION    "202303200000Z"	
              DESCRIPTION "V13.81,	
               Add: subbnameAirEngine9700-S-T,          -- WLAN AirEngine9700-S-T
            "
            REVISION    "202303160000Z"	
              DESCRIPTION "V13.80,	
               Add: subbname8090DEV910D-C(225978),          -- CARD ATN 910D-C
            "
            REVISION    "202303150000Z"	
              DESCRIPTION "V13.79,	
               Add: bnameH901OSCL(157011),          -- OSU board of MA5800.
            "

            REVISION    "202303140000Z"
              DESCRIPTION "V13.78,
               Add:virent8090DEVCR8DIPU1T2ME(689203),  -- V8R22C10 for CR8DIPU1T2ME(SBOM) Integrated Network Processing Unit (IPUA-1T2-EN)
               Add:virent8090DEVCR8DIPU1T2MG(689204),  -- V8R22C10 for CR8DIPU1T2MG(SBOM) Integrated Network Processing Unit (IPUA-1T2-E)
               Add:virent8090DEVCR8DIPU480MH(689205),  -- V8R22C10 for CR8DIPU480MH(SBOM) Integrated Network Processing Unit (IPUA-480-E)
               Add:virent8090DEVCR8DIPU1T2MK(689206),  -- V8R22C10 for CR8DIPU1T2MK(SBOM) Integrated Network Processing Unit (IPUA-1T2-EN)
            "

            REVISION    "202303110000Z"
              DESCRIPTION "V13.77,
               Add:subbname8090DEVCR8D0LJXXCCP(513217),   -- 36-Port 10GBase LAN/WAN-SFP+ MACsec Flexible Card CM(P1T-CM)
               Add:subbname8090DEVCR8D0LJXX0CP(513214),   -- 36-Port 10GBase LAN/WAN-SFP Flexible Card CM(P1T-CM)
               Add:subbname8090DEVCR8D0LJXXCDP(513215),   -- 36-Port 10GBase LAN/WAN-SFP+ MACsec Flexible Card CM(P1T-E-CM)
               Add:subbname8090DEVCR8D0E5NBCCP(513218),   -- 5-Port 100GBase-QSFP28 FlexE MACsec Flexible Card CM(P1T-CM)
               Add:subbname8090DEVCR8D0E5NBCDP(513216),   -- 5-Port 100GBase-QSFP28 FlexE MACsec Flexible Card CM(P1T-E-CM)
               Add:subbname8090DEVCR8DEANBFECP(513220),   -- 10-Port 100GBase-QSFP28 FlexE MACsec Flexible Card CM(P2T-CM)
               Add:subbname8090DEVCR8DE2KE2NCP(513219),   -- 2-Port 400GBase-QSFP-DD + 2-Port 100GBase-QSFP28 FlexE MACsec Flexible Card CM(P2T-CM)
		       Add:subbname8090DEVCR5DE2NBFM77(513210),   -- 2-Port 100GBase-QSFP28 Flexible Card A(P486-A)
               Add:subbname8090DEVCR5DE2NBFM78(513211),   -- 2-Port 100GBase-QSFP28 Flexible Card A(P486-A)
               Add:subbname8090DEVCR5DE2NBFM79(513212),   -- 2-Port 100GBase-QSFP28 Flexible Card A(P486-A)
               Add:subbname8090DEVME0M0E2NFB7B(513213),   -- 2-Port 100GBase-QSFP28 Flexible Card A(BP486-A)
		       Add:subbname8090DEVGFL72XSGB(548676),      -- 72-port 10GE MACsec Physical Interface Card(PIC)
               Add:subbname8090DEVCR8DERXFMSF0(548776),   -- 72-port 10GE-SFP+ FlexE MACsec Combined Line Processing Unit(LPUC-800-CM)
			   Add:subbname8090DEVCR810LJXX0CP(513221),   -- 36-Port 10GBase LAN/WAN-SFP Flexible Card CM(P1T-CM)
            "
			
			REVISION    "202303080000Z"
              DESCRIPTION "V13.76,
               Add:virent8090DEVTNRPM4BASDC1(688029),  -- V8R22C10 for TNRPM4BASDC1(SBOM) PTN 6900-2-M4 Integrated DC Chassis Components(Including DC Power,Fan Box)
               Add:virent8090DEVTNRPM4BASAC1(688030),  -- V8R22C10 for TNRPM4BASAC1(SBOM) PTN 6900-2-M4 Integrated AC Chassis Components(Including AC Power,Fan Box)
               Add:virent8090DEVANND02CXPAC2(228001),  -- V8R22C10 ATN 980C,ANN3CXPA10,System Control,Cross-connect and Multi-protocol Process Unit with 360G
               Add:virent8090DEVCR5DIPU1T292(689118),  -- V8R22C10 for CR5DIPU1T292(SBOM) Integrated Network Processing Unit (IPU-1T2-E)
               Add:virent8090DEVCR8PM1DBASCX(689200),  -- V8R22C10 for CR8PM1DBASCX(SBOM) NetEngine 8000 M1D-B AC(A)(Port Capacity 2*50GE+2*25GE/10GE+2*10GE+14*GE,default 2*25GE&amp;all GE,no aux material)
               Add:virent8090DEVCR8DIPU1T2M5(689201),  -- V8R22C10 for CR8DIPU1T2M5(SBOM) Integrated Network Processing Unit (IPU-1T2-E)
               Add:virent8090DEVTNRDIPU1T293(689202)  -- V8R22C10 for TNRDIPU1T293(SBOM) Integrated Network Processing Unit (IPU-1T2-F)
            "
			
            REVISION    "202303020000Z"
              DESCRIPTION "V13.75,
                Add virent8090DEVCR5DSFUIT261(562191),    -- V8R23C00 for CR5DSFUIT261(SBOM) NE5000E-20 1.6T CLC Integrated Switch Fabric Unit for Multi-Chassis (SFUI-1T6-M2)
            "

			REVISION    "202303010000Z"
              DESCRIPTION "V13.74,
				add AirEngine3562-10(692417),    -- WLAN R22C10 New AP
				add AirEngine3562-10SW(692418),  -- WLAN R22C10 New AP
            "

                    REVISION    "202302270000Z"
              DESCRIPTION "V13.73,
                Add:virent8090DEVCR8PM1DBASCP(303625),  -- V8R22C10 for CR8PM1DBASCP(SBOM) NetEngine 8000 M1D-B DC(Port Capacity 2*50GE+2*25GE/10GE+2*10GE+14*GE,default 2*25GE&all GE,no aux material)
                Add:virent8090DEVCR5DLPUFME75(303626),   -- V8R23C00 for CR5DLPUFME75(SBOM) Flexible Card Line Processing Unit E(LPUF-486-E)
                Add:virent8090DEVCR5DLPUFME76(303627),   -- V8R23C00 for CR5DLPUFME76(SBOM) Flexible Card Line Processing Unit E(LPUF-486-E)
                Add:virent8090DEVCR5DLPUFME78(303628),   -- V8R23C00 for CR5DLPUFME78(SBOM) Flexible Card Line Processing Unit E(LPUF-486A-E)
                Add:virent8090DEVME0DBSUFM07A(303629),   -- V8R23C00 for ME0DBSUFM07A(SBOM) Flexible Card Broadband Service Unit(BSUF-486,2 sub-slots)
                Add:virent8090DEVME0DBSUFM079(303630),   -- V8R23C00 for ME0DBSUFM079(SBOM) Flexible Card Broadband Service Unit(BSUF-486-E,2 sub-slots)
                Add:virent8090DEVME0DBSUFM07D(303631),   -- V8R23C00 for ME0DBSUFM07D(SBOM) Flexible Card Broadband Service Unit(BSUF-486A,2 sub-slots)
                "

		    REVISION    "202302240000Z"
              DESCRIPTION "V13.72,
                Add:virent8090DEVCR5DLPUFT07J(558495),   -- V8R22C10 for CR5DLPUFT07J(SBOM) Flexible Card Line Processing Unit(LPUF-1T2-E)
                "
		   REVISION    "202302231000Z"
              DESCRIPTION "V13.71,
                Add:virent8090DEVCR81IPU1T2CG(228002),  --Integrated Network Processing Unit (IPUA-1T2)
                Add:virent8090DEVCR81IPU480AF(228003),  --Integrated Network Processing Unit (IPUA-480)
                Add:virent8090DEVCR81IPU2TA9(228004),  --Integrated Network Processing Unit (IPUA-2T)
                "      
                                   REVISION    "202302221000Z"
			   DESCRIPTION "V13.70,
			     add: fname8031S5531-H48HB4XZ(537845), bname8031S5531-H48HB4XZ(538028)
			     add: fname8031S5531-S32ST4X(537846), bname8031S5531-S32ST4X(538029)
			     add: fname8031S5735-L48P4X-A2(537836), bname8031S5735-L48P4X-A2(538020)
			     add: fname8031S5735-L48P4S-A2(537837), bname8031S5735-L48P4S-A2(538021)
			     add: fname8031S5735S-L48P4X-A2(537838), bname8031S5735S-L48P4X-A2(538022)
			     add: fname8031S5735S-L48P4S-A2(537839), bname8031S5735S-L48P4S-A2(538023)
			     add: fname8031S5735-L48T4X-A2(537840), bname8031S5735-L48T4X-A2(538024)
			     add: fname8031S5735-L48T4S-A2(537841), bname8031S5735-L48T4S-A2(538025)
			     add: fname8031S5735S-L48T4X-A2(537842), bname8031S5735S-L48T4X-A2(538026)
			     add: fname8031S5735S-L48T4S-A2(537843), bname8031S5735S-L48T4S-A2(538027)
			     "
		 
		     REVISION    "202302180000Z"
              DESCRIPTION "V13.69,
                virent8090DEVCR8DMPUF8AF4(115245),   -- V8R22C10 for CR8DMPUF8AF4(SBOM) NetEngine 8000E F Main Processing Unit B1A(MPUB1A)
               virent8090DEVCR8D00LRXFD6(693699),   -- V8R22C10 for CR8D00LRXFD6(SBOM) 72-Port 25GE(SFP28)/10GE(SFP+)/GE(SFP) Integrated Line Processing Unit CM(LPUI-2T-CM)
               virent8090DEVCR8D00EKNBD6(285562),   -- V8R22C10 for CR8D00EKNBD6(SBOM) 40-Port 100GBase-QSFP28 Integrated Line Processing Unit CM(LPUI-4T-CM)
               virent8090DEVCR8D00EENBD7(177236),   -- V8R22C10 for CR8D00EENBD7(SBOM) 20-Port 100GBase-QSFP28 Integrated Line Processing Unit CM(LPUI-2T-CM)
               virent8090DEVCR8DE4KEFND0(717476),   -- V8R22C10 for CR8DE4KEFND0(SBOM) 4-Port 400GBase-QSFP-DD + 24-Port 100GBase-QSFP28 Integrated Line Processing Unit CM (LPUI-4T-CM)
               virent8090DEVCR8DEANCJXDB(452016),   -- V8R22C10 for CR8DEANCJXDB(SBOM) 10-Port 100GBase-QSFP28 + 36-Port 25GE(SFP28)/10GE(SFP+)/GE(SFP) Integrated Line Processing Unit CM(LPUI-2T-CM)
               virent8090DEVCR8D00LRXFD8(722152),   -- V8R22C10 for CR8D00LRXFD8(SBOM) 72-Port 25GE(SFP28)/10GE(SFP+)/GE(SFP) Integrated Line Processing Unit L CM(LPUI-2T-L-CM)
               virent8090DEVCR8D00EKNBD8(679585),   -- V8R22C10 for CR8D00EKNBD8(SBOM) 40-Port 100GBase-QSFP28 Integrated Line Processing Unit L CM(LPUI-4T-L-CM)
               virent8090DEVCR8D00EENBD9(964479),   -- V8R22C10 for CR8D00EENBD9(SBOM) 20-Port 100GBase-QSFP28 Integrated Line Processing Unit L CM(LPUI-2T-L-CM)
               virent8090DEVCR8D00LRXFD7(422375),   -- V8R22C10 for CR8D00LRXFD7(SBOM) 72-Port 25GE(SFP28)/10GE(SFP+)/GE(SFP) Integrated Line Processing Unit CM(LPUI-2TA-CM)
               virent8090DEVCR8D00EKNBD7(855837),   -- V8R22C10 for CR8D00EKNBD7(SBOM) 40-Port 100GBase-QSFP28 Integrated Line Processing Unit CM(LPUI-4TA-CM)
               virent8090DEVCR8D00EENBDD(640421),   -- V8R22C10 for CR8D00EENBDD(SBOM) 20-Port 100GBase-QSFP28 Integrated Line Processing Unit CM(LPUI-2TA-CM)
               virent8090DEVCR8DE4KEFNF1(818326),   -- V8R22C10 for CR8DE4KEFNF1(SBOM) 4-Port 400GBase-QSFP-DD + 24-Port 100GBase-QSFP28 Integrated Line Processing Unit CM (LPUI-4TA-CM)
               virent8090DEVCR8DEANCJXDD(620583),   -- V8R22C10 for CR8DEANCJXDD(SBOM) 10-Port 100GBase-QSFP28 + 36-Port 25GE(SFP28)/10GE(SFP+)/GE(SFP) Integrated Line Processing Unit CM(LPUI-2TA-CM)
               virent8090DEVCR8D00LRXFD9(837511),   -- V8R22C10 for CR8D00LRXFD9(SBOM) 72-Port 25GE(SFP28)/10GE(SFP+)/GE(SFP) Integrated Line Processing Unit L(LPUI-2TA-L-CM)
               virent8090DEVCR8D00EKNBD9(336731),   -- V8R22C10 for CR8D00EKNBD9(SBOM) 40-Port 100GBase-QSFP28 Integrated Line Processing Unit L CM(LPUI-4TA-L-CM)
               virent8090DEVCR8D00EENBDA(288688),   -- V8R22C10 for CR8D00EENBDA(SBOM) 20-Port 100GBase-QSFP28 Integrated Line Processing Unit L CM(LPUI-2TA-L-CM)
               virent8090DEVCR8DE4KFBND1(716032),   -- V8R22C10 for CR8DE4KFBND1(SBOM) 4-Port 400GBase-QSFP-DD + 24-Port 100GBase-QSFP28 Integrated Line Processing Unit CM (LPUI-4TA-L-CM)
               virent8090DEVCR8DEANCJXDE(209467),   -- V8R22C10 for CR8DEANCJXDE(SBOM) 10-Port 100GBase-QSFP28 + 36-Port 25GE(SFP28)/10GE(SFP+)/GE(SFP) Integrated Line Processing Unit L CM(LPUI-2TA-L-CM)
               virent8090DEVCR8DEANCJXDC(520236),   -- V8R22C10 for CR8DEANCJXDC(SBOM) 10-Port 100GBase-QSFP28 + 36-Port 25GE(SFP28)/10GE(SFP+)/GE(SFP) Integrated Line Processing Unit L CM(LPUI-2T-L-CM)
               virent8090DEVCR8DE4KFBND2(109608),   -- V8R22C10 for CR8DE4KFBND2(SBOM) 4-Port 400GBase-QSFP-DD + 24-Port 100GBase-QSFP28 Integrated Line Processing Unit CM (LPUI-4T-L-CM)
            "
			
		    REVISION    "202302150000Z"
              DESCRIPTION "V13.68,
                Add:subbname8090DEVGPLI72XSE1(778134),        -- 72-Port 25GE(SFP28)/10GE(SFP+)/GE(SFP) Integrated Line Processing Unit
                Add:subbname8090DEVCR8DE4YBMSF0(998319),      --4-Port 25GE(SFP28)/10GE(SFP+) MACsec Physical Interface Card (PIC)
            "
		 
            REVISION    "202302140000Z"	
              DESCRIPTION "V13.67,	
               Modify:virent8090DEVCP8PHST20A06(226214),  --NetEngine A821 AC System (2*10GE/GE/FE+8*GE/FE(o)+8*GE/FE(e))
               Add:virent8090DEVCR5DVSUIK07K(226183),  --Integrated Service Unit 400(VSUI-400)
               Add:virent8090DEVCR5DVSUIK07Z(226184),  --Integrated Service Unit 400(VSUI-400B)
               Add:virent8090DEVCR5DVSUIK07P(226185),  --Integrated Service Unit 400(VSUI-400A)
               Add:virent8090DEVCR5DVSUIK07L(226186),  --Integrated Service Unit 400(VSUI-400)
               Add:virent8090DEVCR5DVSUIK07O(226187),  --Integrated Service Unit 400(VSUI-400-S)
               Add:virent8090DEVME0DVSUIK07G(226188),  --Integrated Service Unit 400(VSUI-400)
               Add:virent8090DEVME0DVSUIK07P(226189),  --Integrated Service Unit 400(VSUI-400A)
               Add:virent8090DEVCR5DVSUIK07J(226190),  --Integrated Service Unit 400(VSUI-400A-E)
               Add:virent8090DEVCR5DVSUIK07V(226191),  --Enhanced Multi-Function Integrated Service Unit 400(VSUI-400-E)
               Add:virent8090DEVCR5DVSUIK07R(226192),  --Enhanced Multi-Function Integrated Service Unit 400(VSUI-400-E)
               Add:virent8090DEVCR5DVSUIK07W(226193),  --Enhanced Multi-Function Integrated Service Unit 400(VSUI-400A-E)
               Add:virent8090DEVCR5DVSUIK07S(226194),  --Enhanced Multi-Function Integrated Service Unit 400(VSUI-400A-E)
               Add:virent8090DEVME0DVSUIK07R(226195),  --Integrated Service Unit 400(VSUI-400-E)
               Add:virent8090DEVME0DVSUIK07S(226196),  --Integrated Service Unit 400(VSUI-400A-E)
               Add:virent8090DEVCR5DVSUIK07I(226198),  --Integrated Service Unit 400(VSUI-400A-S)
               Add:virent8090DEVCR5DVSUIK07X(226226),  --Multi-Function Integrated Service Unit 400(VSUI-400-S)
               Add:virent8090DEVCR5DVSUIK07T(226227),  --Multi-Function Integrated Service Unit 400(VSUI-400-S)
               Add:virent8090DEVCR5DVSUIK07Y(226228),  --Multi-Function Integrated Service Unit 400(VSUI-400A-S)
               Add:virent8090DEVCR5DVSUIK07U(226229),  --Multi-Function Integrated Service Unit 400(VSUI-400A-S)
               Add:virent8090DEVCR5DJYSUK074(226230),  --Public Security Service Unit(PSSU-A)
               Add:virent8090DEVCR5DJYSUK076(226231),  --Public Security Service Unit(PSSU-S)
               Add:virent8090DEVME0DVSUIK07T(226232),  --Integrated Service Unit 400(VSUI-400-S)
               Add:virent8090DEVME0DVSUIK07U(226233),  --Integrated Service Unit 400(VSUI-400-S)
               Add:virent8090DEVME0DVSUIK07V(226234),  --Integrated Service Unit 400(VSUI-400A-S)
               Add:virent8090DEVME0DJYSUK072(226235),  --Public Security Service Unit(PSSU-A)
               Add:virent8090DEVME0DJYSUK074(226236),  --Public Security Service Unit(PSSU-S)
               Add:virent8090DEVCR5D00EENB7T(892500),   -- V8R22C10 for CR5D00EENB7T(SBOM) 20-Port 100GBase-QSFP28 FlexE/MACsec Integrated Line Processing Unit CM(LPUI-2T-E-CM)
               Add:virent8090DEVCR5DLPUF537P(948166),   -- V8R22C10 for CR5DLPUF537P(SBOM) Flexible Card Line Processing Unit(LPUF-53D)
               Add:virent8090DEVCR5DLPUFF395(250006),   -- V8R22C10 for CR5DLPUFF395(SBOM) Flexible Card Line Processing Unit(LPUF-243D)
               Add:virent8090DEVCR5DLPUFM398(778602),   -- V8R22C10 for CR5DLPUFM398(SBOM) Flexible Card Line Processing Unit(LPUF-483D)
               Add:virent8090DEVCR5DLPUF5378(471965),   -- V8R22C10 for CR5DLPUF5378(SBOM) Flexible Card Line Processing Unit(LPUF-53)
               Add:virent8090DEVCR5DLPUF5379(422392),   -- V8R22C10 for CR5DLPUF5379(SBOM) Flexible Card Line Processing Unit(LPUF-53A)
               Add:virent8090DEVCR5DLPUF537Q(773447),   -- V8R22C10 for CR5DLPUF537Q(SBOM) Flexible Card Line Processing Unit(LPUF-53A)
               Add:virent8090DEVCR5DLPUFF37J(417466),   -- V8R22C10 for CR5DLPUFF37J(SBOM) Flexible Card Line Processing Unit(LPUF-243)
               Add:virent8090DEVCR5DLPUFF37U(824233),   -- V8R22C10 for CR5DLPUFF37U(SBOM) Flexible Card Line Processing Unit(LPUF-243A)
               Add:virent8090DEVCR5DLPUFF37Q(625934),   -- V8R22C10 for CR5DLPUFF37Q(SBOM) 8-Port GE-SFP/10GE-SFP+ and 16-Port GE-SFP Flexible Card Line Processing Unit(LPUI-243A-CM, 4*10GE+20*GE by default, one sub-slot for flexible card)
               Add:virent8090DEVCR5DLPUFF37V(820969),   -- V8R22C10 for CR5DLPUFF37V(SBOM) 8-Port GE-SFP/10GE-SFP+ and 16-Port GE-SFP Flexible Card Line Processing Unit(LPUI-243A-CM, 4*10GE+20*GE by default, one sub-slot for flexible card)
               Add:virent8090DEVCR5DLPUFF37R(547778),   -- V8R22C10 for CR5DLPUFF37R(SBOM) 8-Port GE-SFP/10GE-SFP+ and 16-Port GE-SFP Flexible Card Line Processing Unit(LPUI-243-CM, 4*10GE+20*GE by default, one sub-slot for flexible card)
               Add:virent8090DEVCR5DLPUFF37S(269662),   -- V8R22C10 for CR5DLPUFF37S(SBOM) 8-Port GE-SFP/10GE-SFP+ and 16-Port GE-SFP Flexible Card Line Processing Unit(LPUI-243-CM, 4*10GE+20*GE by default, one sub-slot for flexible card)
               Add:virent8090DEVCR5DVSUIK07Q(793681),   -- V8R22C10 for CR5DVSUIK07Q(SBOM) Integrated Service Unit 400(VSUI-400A)
               Add:virent8090DEVME0DVSUIK07Q(204391),   -- V8R22C10 for ME0DVSUIK07Q(SBOM) Integrated Service Unit 400(VSUI-400A)
               Add:virent8090DEVCR5DLPUF537A(998152),   -- V8R22C10 for CR5DLPUF537A(SBOM) Flexible Card Line Processing Unit(LPUF-53)
               Add:virent8090DEVCR5DLPUF537C(840258),   -- V8R22C10 for CR5DLPUF537C(SBOM) Flexible Card Line Processing Unit(LPUF-53A)
               Add:virent8090DEVCR5DLPUFF39C(705910),   -- V8R22C10 for CR5DLPUFF39C(SBOM) Flexible Card Line Processing Unit(LPUF-243)
               Add:virent8090DEVCR5DLPUFF398(609281),   -- V8R22C10 for CR5DLPUFF398(SBOM) Flexible Card Line Processing Unit(LPUF-243A)
               Add:virent8090DEVCR5DLPUFF399(242316),   -- V8R22C10 for CR5DLPUFF399(SBOM) 8-Port GE-SFP/10GE-SFP+ and 16-Port GE-SFP Flexible Card Line Processing Unit(LPUI-243A-CM, 4*10GE+20*GE by default, one sub-slot for flexible card)
               Add:virent8090DEVCR5DLPUFF39B(823300),   -- V8R22C10 for CR5DLPUFF39B(SBOM) 8-Port GE-SFP/10GE-SFP+ and 16-Port GE-SFP Flexible Card Line Processing Unit(LPUI-243-CM, 4*10GE+20*GE by default, one sub-slot for flexible card)
               Add:virent8090DEVCR5DLPUFM37A(322248),   -- V8R22C10 for CR5DLPUFM37A(SBOM) Flexible Card Line Processing Unit(LPUF-483)
               Add:virent8090DEVCR5DLPUFM37B(468309),   -- V8R22C10 for CR5DLPUFM37B(SBOM) Flexible Card Line Processing Unit(LPUF-483A)
               Add:virent8090DEVCR5DLPUFM37D(520268),   -- V8R22C10 for CR5DLPUFM37D(SBOM) Flexible Card Line Processing Unit(LPUF-483A)
               Add:virent8090DEVCR5DLPUFM37E(472413),   -- V8R22C10 for CR5DLPUFM37E(SBOM) Flexible Card Line Processing Unit(LPUF-483-CM, enable slot 0 by default)
               Add:virent8090DEVCR5DLPUFM37F(950192),   -- V8R22C10 for CR5DLPUFM37F(SBOM) Flexible Card Line Processing Unit(LPUF-483-E-CM, enable slot 0 by default)
               Add:virent8090DEVCR5DLPUFM37N(665079),   -- V8R22C10 for CR5DLPUFM37N(SBOM) 24-Port GE-SFP/10GE-SFP+ Flexible Card Line Processing Unit(LPUI-483A-CM, Enable 12*10GE+12*GE by default, Supporting one sub-slot for flexible card)
               Add:virent8090DEVCR5DLPUFM37L(670588),   -- V8R22C10 for CR5DLPUFM37L(SBOM) 24-Port GE-SFP/10GE-SFP+ Flexible Card Line Processing Unit(LPUI-483-CM, Enable 12*10GE+12*GE by default, Supporting one sub-slot for flexible card)
               Add:virent8090DEVCR5DLPUFM39A(307470),   -- V8R22C10 for CR5DLPUFM39A(SBOM) Flexible Card Line Processing Unit(LPUF-483A, Supportting DIP)
               Add:virent8090DEVCR5DLPUFM39B(418653),   -- V8R22C10 for CR5DLPUFM39B(SBOM) Flexible Card Line Processing Unit(LPUF-483, Supportting DIP)
               Add:virent8090DEVCR5D00EENB7A(384144),   -- V8R22C10 for CR5D00EENB7A(SBOM) 20-Port 100GBase-QSFP28 Integrated Line Processing Unit (LPUI-2TA)
               Add:virent8090DEVCR5D00EENB7D(660183),   -- V8R22C10 for CR5D00EENB7D(SBOM) 20-Port 100GBase-QSFP28 FlexE/MACsec Integrated Line Processing Unit CM(LPUI-2T-CM)
               Add:virent8090DEVME0DBSUFM07C(585779),   -- V8R22C10 for ME0DBSUFM07C(SBOM) Flexible Card Broadband Service Unit(BSUF-243-E,2 sub-slots)
               Add:virent8090DEVME0DBSUFM07J(639282),   -- V8R22C10 for ME0DBSUFM07J(SBOM) Flexible Card Broadband Service Unit(BSUF-483-E,2 sub-slots)
               Add:virent8090DEVIG2D00EENB03(482016),   -- V8R22C10 for IG2D00EENB03(SBOM) 20-Port 100GBase-QSFP28 Integrated Line Processing Unit (LPUI-2TA)
               Add:virent8090DEVCR5DLPUF5377(995282),   -- V8R22C10 for CR5DLPUF5377(SBOM) Flexible Card Line Processing Unit(LPUF-53)
               Add:virent8090DEVCR5DLPUF537B(486588),   -- V8R22C10 for CR5DLPUF537B(SBOM) Flexible Card Line Processing Unit(LPUF-53)
               Add:virent8090DEVCR5DLPUFF37M(940300),   -- V8R22C10 for CR5DLPUFF37M(SBOM) Flexible Card Line Processing Unit(LPUF-243)
               Add:virent8090DEVCR5DLPUFF37N(714849),   -- V8R22C10 for CR5DLPUFF37N(SBOM) Flexible Card Line Processing Unit(LPUF-243)
               Add:virent8090DEVCR5DLPUFF37P(335140),   -- V8R22C10 for CR5DLPUFF37P(SBOM) Flexible Card Line Processing Unit(LPUF-243A)
               Add:virent8090DEVCR5DLPUFF37T(933293),   -- V8R22C10 for CR5DLPUFF37T(SBOM) 8-Port GE-SFP/10GE-SFP+ and 16-Port GE-SFP Flexible Card Line Processing Unit(LPUI-243-CM, 4*10GE+20*GE by default, one sub-slot for flexible card)
               Add:virent8090DEVCR5DLPUFM37P(733811),   -- V8R22C10 for CR5DLPUFM37P(SBOM) Flexible Card Line Processing Unit(LPUF-483)
               Add:virent8090DEVCR5DLPUFM37R(778558),   -- V8R22C10 for CR5DLPUFM37R(SBOM) Flexible Card Line Processing Unit(LPUF-483-CM, enable slot 0 by default)
               Add:virent8090DEVCR5DLPUFM37T(541057),   -- V8R22C10 for CR5DLPUFM37T(SBOM) Flexible Card Line Processing Unit(LPUF-483-E-CM, enable slot 0 by default)
               Add:virent8090DEVCR5DLPUFM37V(488097),   -- V8R22C10 for CR5DLPUFM37V(SBOM) 24-Port GE-SFP/10GE-SFP+ Flexible Card Line Processing Unit(LPUI-483-CM, Enable 12*10GE+12*GE by default, Supporting one sub-slot for flexible card)
               Add:virent8090DEVCR5DLPUFM399(175781),   -- V8R22C10 for CR5DLPUFM399(SBOM) Flexible Card Line Processing Unit(LPUF-483, Supportting DIP)
               Add:virent8090DEVCR5D00EENB7F(811462),   -- V8R22C10 for CR5D00EENB7F(SBOM) 20-Port 100GBase-QSFP28 Integrated Line Processing Unit (LPUI-2TA-E)
               Add:virent8090DEVME0DBSUFM07H(546995),   -- V8R22C10 for ME0DBSUFM07H(SBOM) Flexible Card Broadband Service Unit(BSUF-483-E,2 sub-slots)
               Add:virent8090DEVME0DBSUFM07F(303620),   -- V8R22C10 for ME0DBSUFM07F(SBOM) Flexible Card Broadband Service Unit(BSUF-243-E,2 sub-slots)
               Add:virent8090DEVCR5D00EENB7U(303621),   -- V8R22C10 for CR5D00EENB7U(SBOM) 20-Port 100GBase-QSFP28 Integrated Line Processing Unit L(LPUI-2T-L)
               Add:virent8090DEVCR5DVSUIK091(303622),   -- V8R22C10 for CR5DVSUIK091(SBOM) Integrated Service Unit 400(VSUI-400-E)
               Add:virent8090DEVCR5DVSUIK093(303623),   -- V8R22C10 for CR5DVSUIK093(SBOM) Integrated Service Unit 400(VSUI-400-S)
               Add:virent8090DEVME0DVSUIK07W(303624),   -- V8R22C10 for ME0DVSUIK07W(SBOM) Integrated Service Unit 400(VSUI-400)
              "

            REVISION    "202302100000Z"	
              DESCRIPTION "V13.66,	
              Add: bnameH901MPSF(148809),              -- control board of MA5800-X2.
              "

            REVISION    "202302090000Z"
              DESCRIPTION "V13.65
               Add:virent8090DEVCR8DMPUF8BF3(820122),   -- V8R22C10 for CR8DMPUF8BF3(SBOM) NetEngine 8000 F Main Processing Unit B1(MPUB1)
               Add:virent8090DEVCR8DMPUF8BF2(560449),   -- V8R22C10 for CR8DMPUF8BF2(SBOM) NetEngine 8000 F Main Processing Unit B2(MPUB2)
               Add:virent8090DEVCR8DMPUF8AZ2(333932),   -- V8R22C10 for CR8DMPUF8AZ2(SBOM) NetEngine 8000E F Main Processing Unit B1Z(MPUB1Z)
               Add:virent8090DEVCR8DSFUIK0D0(278498),   -- V8R22C10 for CR8DSFUIK0D0(SBOM) NetEngine 8000 F 2T Switch Routing Unit(SRU-2T-A)
               Add:virent8090DEVCR8DSFUIK0D1(333202),   -- V8R22C10 for CR8DSFUIK0D1(SBOM) NetEngine 8000E F 2T Switch Routing Unit(SRUA-2T-A)
               Add:virent8090DEVCR8D00EKNIC0(437814),   -- V8R22C10 for CR8D00EKNIC0(SBOM) 40-Port 100GBase-QSFP28 Integrated Line Processing Unit(LPUIA-4T)
               Add:virent8090DEVCR8D00EINBC2(142863),   -- V8R22C10 for CR8D00EINBC2(SBOM) 32-Port 100GBase-QSFP28 Integrated Line Processing Unit CM(LPUI-3T2A-CM)
               Add:virent8090DEVCR8D00LRXIC0(544919),   -- V8R22C10 for CR8D00LRXIC0(SBOM) 72-Port 10GE(SFP+)/GE(SFP) Integrated Line Processing Unit(LPUIA-2T)
               Add:virent8090DEVCR8D00EENBCY(218591),   -- V8R22C10 for CR8D00EENBCY(SBOM) 20-Port 100GBase-QSFP28 Integrated Line Processing Unit CM(LPUI-2TA-CM)
               Add:virent8090DEVCR8D00LRXFCY(142985),   -- V8R22C10 for CR8D00LRXFCY(SBOM) 72-Port 10GE-SFP+ Integrated Line Processing Unit(LPUI-1TA-CM)
               Add:virent8090DEVIG2DLPUFT003(200560),   -- V8R22C10 for IG2DLPUFT003(SBOM) Flexible Card Line Processing Unit(LPUF-1T2A)
               Add:virent8090DEVIG2DLPUFM306(641528),   -- V8R22C10 for IG2DLPUFM306(SBOM) Flexible Card Line Processing Unit(LPUF-483A)
               Add:virent8090DEVCR5DEDVE8N7C(492102),   -- V8R22C10 for CR5DEDVE8N7C(SBOM) 16-Port 50G/8-Port 100GBase-QSFP28 FlexE Integrated Line Processing Unit L(LPUI-1T2-L)
               Add:virent8090DEVCR5DEDVE8N7D(956150),   -- V8R22C10 for CR5DEDVE8N7D(SBOM) 16-Port 50G/8-Port 100GBase-QSFP28 FlexE/MACsec Integrated Line Processing Unit CM(LPUI-1T2-CM)
               Add:virent8090DEVCR5DLPUFT07H(135161),   -- V8R22C10 for CR5DLPUFT07H(SBOM) Flexible Card Line Processing Unit(LPUF-1T2)
               Add:virent8090DEVCR5DLPUF537G(163641),   -- V8R22C10 for CR5DLPUF537G(SBOM) Flexible Card Line Processing Unit(LPUF-53)
               Add:virent8090DEVCR5DLPUFF397(540645),   -- V8R22C10 for CR5DLPUFF397(SBOM) Flexible Card Line Processing Unit(LPUF-243)
               Add:virent8090DEVCR5DLPUFF37I(981704),   -- V8R22C10 for CR5DLPUFF37I(SBOM) 8-Port GE-SFP/10GE-SFP+ and 16-Port GE-SFP Flexible Card Line Processing Unit(LPUI-243-CM, 4*10GE+20*GE by default, one sub-slot for flexible card)
               Add:virent8090DEVCR5DLPUFM37G(441838),   -- V8R22C10 for CR5DLPUFM37G(SBOM) Flexible Card Line Processing Unit(LPUF-483)
               Add:virent8090DEVCR5DLPUFM37J(576508),   -- V8R22C10 for CR5DLPUFM37J(SBOM) Flexible Card Line Processing Unit(LPUF-483-CM, enable slot 0 by default)
               Add:virent8090DEVCR5DLPUFM37I(505713),   -- V8R22C10 for CR5DLPUFM37I(SBOM) Flexible Card Line Processing Unit(LPUF-483-E-CM, enable slot 0 by default)
               Add:virent8090DEVCR5DLPUFM37M(848667),   -- V8R22C10 for CR5DLPUFM37M(SBOM) 24-Port GE-SFP/10GE-SFP+ Flexible Card Line Processing Unit(LPUI-483-CM, Enable 12*10GE+12*GE by default, Supporting one sub-slot for flexible card)
               Add:virent8090DEVCR5DLPUF537D(776113),   -- V8R22C10 for CR5DLPUF537D(SBOM) Flexible Card Line Processing Unit(LPUF-53)
               Add:virent8090DEVCR5DLPUFF37X(900536),   -- V8R22C10 for CR5DLPUFF37X(SBOM) Flexible Card Line Processing Unit(LPUF-243)
               Add:virent8090DEVCR5DLPUFF37W(620808),   -- V8R22C10 for CR5DLPUFF37W(SBOM) 8-Port GE-SFP/10GE-SFP+ and 16-Port GE-SFP Flexible Card Line Processing Unit(LPUI-243-CM, 4*10GE+20*GE by default, one sub-slot for flexible card)
               Add:virent8090DEVCR5DLPUFM37Y(575487),   -- V8R22C10 for CR5DLPUFM37Y(SBOM) Flexible Card Line Processing Unit(LPUF-483)
               Add:virent8090DEVCR5DLPUFM37Q(560576),   -- V8R22C10 for CR5DLPUFM37Q(SBOM) Flexible Card Line Processing Unit(LPUF-483-CM, enable slot 0 by default)
               Add:virent8090DEVCR5DLPUFM37S(924968),   -- V8R22C10 for CR5DLPUFM37S(SBOM) Flexible Card Line Processing Unit(LPUF-483-E-CM, enable slot 0 by default)
               Add:virent8090DEVCR5DLPUFM37U(822545),   -- V8R22C10 for CR5DLPUFM37U(SBOM) 24-Port GE-SFP/10GE-SFP+ Flexible Card Line Processing Unit(LPUI-483-CM, Enable 12*10GE+12*GE by default, Supporting one sub-slot for flexible card)
               Add:virent8090DEVCR5DLPUFT07G(157738),   -- V8R22C10 for CR5DLPUFT07G(SBOM) Flexible Card Line Processing Unit(LPUF-1T2A)
               Add:virent8090DEVCR5D00E8NB7T(477667),   -- V8R22C10 for CR5D00E8NB7T(SBOM) 16-Port 50G/8-Port 100GBase-QSFP28 FlexE/MACsec Integrated Line Processing Unit CM(LPUI-1T2A-CM)
               Add:virent8090DEVCR5DLPUFT07K(558494),   -- V8R22C10 for CR5DLPUFT07K(SBOM) Flexible Card Line Processing Unit(LPUF-1T2A-E)
               Add:virent8090DEVCR5DLPUF537H(248937),   -- V8R22C10 for CR5DLPUF537H(SBOM) Flexible Card Line Processing Unit(LPUF-53A)
               Add:virent8090DEVCR5DLPUFF396(632083),   -- V8R22C10 for CR5DLPUFF396(SBOM) Flexible Card Line Processing Unit(LPUF-243A)
               Add:virent8090DEVCR5DLPUFF39A(827356),   -- V8R22C10 for CR5DLPUFF39A(SBOM) 8-Port GE-SFP/10GE-SFP+ and 16-Port GE-SFP Flexible Card Line Processing Unit(LPUI-243A-CM, 4*10GE+20*GE by default, one sub-slot for flexible card)
               Add:virent8090DEVCR5DLPUFM37H(530429),   -- V8R22C10 for CR5DLPUFM37H(SBOM) Flexible Card Line Processing Unit(LPUF-483A)
               Add:virent8090DEVCR5DLPUFM37W(495978),   -- V8R22C10 for CR5DLPUFM37W(SBOM) Flexible Card Line Processing Unit(LPUF-483A)
               Add:virent8090DEVCR5DLPUFM37K(715222),   -- V8R22C10 for CR5DLPUFM37K(SBOM) 24-Port GE-SFP/10GE-SFP+ Flexible Card Line Processing Unit(LPUI-483A-CM, Enable 12*10GE+12*GE by default, Supporting one sub-slot for flexible card)
               Add:virent8090DEVME0DMSUFT07G(706119),   -- V8R22C10 for ME0DMSUFT07G(SBOM) Flexible Card Multi Service Unit(MSUF-1T2,2 sub-slots)
               Add:virent8090DEVME0DBSUFT07F(165590),   -- V8R22C10 for ME0DBSUFT07F(SBOM) Flexible Card Broadband Service Unit(BSUF-1T2A,2 sub-slots)
               Add:virent8090DEVME0DBSUFT07M(768000),   -- V8R22C10 for ME0DBSUFT07M(SBOM) Flexible Card Broadband Service Unit(BSUF-1T2-E,2 sub-slots)
               Add:virent8090DEVME0DMSUFT07M(315631),   -- V8R22C10 for ME0DMSUFT07M(SBOM) Flexible Card Multi Service Unit(MSUF-1T2-E,2 sub-slots)
               Add:virent8090DEVME0DBSUFT07N(995118),   -- V8R22C10 for ME0DBSUFT07N(SBOM) Flexible Card Broadband Service Unit(BSUF-1T2A-E,2 sub-slots)
               Add:virent8090DEVME0DMSUFT07N(834245),   -- V8R22C10 for ME0DMSUFT07N(SBOM) Flexible Card Multi Service Unit(MSUF-1T2A-E,2 sub-slots)
               Add:virent8090DEVME0DBSUFM07B(466368),   -- V8R22C10 for ME0DBSUFM07B(SBOM) Flexible Card Broadband Service Unit(BSUF-243-E,2 sub-slots)
               Add:virent8090DEVME0DBSUFM07K(458457),   -- V8R22C10 for ME0DBSUFM07K(SBOM) Flexible Card Broadband Service Unit(BSUF-483-E,2 sub-slots)
               Add:virent8090DEVME0DBSUFM07E(919145),   -- V8R22C10 for ME0DBSUFM07E(SBOM) Flexible Card Broadband Service Unit(BSUF-243-E,2 sub-slots)
               Add:virent8090DEVME0DBSUFM07G(333879),   -- V8R22C10 for ME0DBSUFM07G(SBOM) Flexible Card Broadband Service Unit(BSUF-483-E,2 sub-slots)
               Add:virent8090DEVCX6DISUFT014(390887),   -- V8R22C10 for CX6DISUFT014(SBOM) Flexible Card Integrated Service Unit(ISUF-1TA)
               Add:virent8090DEVCX6DISUFT016(392871),   -- V8R22C10 for CX6DISUFT016(SBOM) Flexible Card Integrated Service Unit(ISUF-1T)
               Add:virent8090DEVCX6DISUFM312(440866),   -- V8R22C10 for CX6DISUFM312(SBOM) Flexible Card Line Processing Unit(ISUF-483A)
			   Add:virent8090DEVCR8PM1DBADM1(226170),  --NetEngine 8000 M1D, DC Power (Port Capacity 4*100GE/50GE+16*25GE/10GE/GE/FE+8*10GE/GE/FE,exclude auxiliary materials)
               Add:virent8090DEVCR8PM1DBADM0(226171),  --NetEngine 8000 M1D, DC Power (Port Capacity 4*100GE/50GE+16*25GE/10GE/GE/FE+8*10GE/GE/FE,exclude auxiliary materials)
               Add:virent8090DEVCR8PM1DBAAM1(226172),  --NetEngine 8000 M1D, AC Power (Port Capacity 4*100GE/50GE+16*25GE/10GE/GE/FE+8*10GE/GE/FE,exclude auxiliary materials)
               Add:virent8090DEVCR8PM1DBAAM0(226173),  --NetEngine 8000 M1D, AC Power (Port Capacity 4*100GE/50GE+16*25GE/10GE/GE/FE+8*10GE/GE/FE,exclude auxiliary materials)
               Add:virent8090DEVCR8PM1DBADM5(226174),  --NetEngine 8000 M1D, DC Power (Port Capacity 4*100GE/50GE+16*25GE/10GE/GE/FE+8*10GE/GE/FE,exclude auxiliary materials)
               Add:virent8090DEVCR8PM1DBAAM5(226175),  --NetEngine 8000 M1D, AC Power (Port Capacity 4*100GE/50GE+16*25GE/10GE/GE/FE+8*10GE/GE/FE,exclude auxiliary materials)
               Add:virent8090DEVANRD00CXPB02(226159),  --System Control, Cross-connect and Multi-protocol Process Unit with 160G
               Add:virent8090DEVCR8PM1CBASC7(226199),  --NetEngine 8000 M1C, 2*AC Power, Port Capacity 16*10GE+8*GE(o)+4*GE(e), None of the ports are available by default
               Add:virent8090DEVCR8PM1CBASA6(226200),  --NetEngine 8000 M1C(A), 2*DC Power, Port Capacity 16*10GE+8*GE(o)+4*GE(e), None of the ports are available by default
               Add:virent8090DEVCR8PM1CBASA7(226201),  --NetEngine 8000 M1C(A), 2*AC Power, Port Capacity 16*10GE+8*GE(o)+4*GE(e), None of the ports are available by default
               Add:virent8090DEVANGMHSTH0100(226206),  --ATN 910C-H DC Basic Configuration(Includes Fixed Enable Interface (4*10GE/GE/FE(o)+4*GE/FE(o)+4*GE/FE(e))/Dual Power/FAN/Chassis)
               Add:virent8090DEVANGMHSTH0200(226208),  --ATN 910C-H AC Basic Configuration(Includes Fixed Enable Interface (4*10GE/GE/FE(o)+4*GE/FE(o)+4*GE/FE(e))/Power/FAN/Chassis)
               Add:virent8090DEVANGMHSTS0200(226209),  --ATN 910C-S AC Basic Configuration(Includes Fixed Enable Interface (4*10GE/GE/FE(o)+4*GE/FE(o)+4*GE/FE(e))/Power/FAN/Chassis)
               Add:virent8090DEVCP8PHST20A06(226214),  --NetEngine A821 AC System (2*10GE/GE/FE+8*GE/FE(o)+8*GE/FE(e))
               Add:virent8090DEVCP8PHST20A08(226215),  --NetEngine A821 AC System (2*10GE/GE/FE+8*GE/FE(o)+8*GE/FE(e))
               Add:virent8090DEVCP8PHST10A10(226216),  --NetEngine A813 AC System (6*GE/FE(o)+8*GE/FE(e))
               Add:virent8090DEVCP8PHSB2EA04(226217),  --NetEngine A821 E AC Chassis(A) (6*10GE/GE/FE(o)+4*GE/FE(o)+8*GE/FE(e), Default 2*10GE/GE/FE(o)+8*GE/FE(o)+8*GE/FE(e))
               Add:virent8090DEVCP8PHSB2EA05(226218),  --NetEngine A821 E AC Chassis (6*10GE/GE/FE(o)+4*GE/FE(o)+8*GE/FE(e), Default 2*10GE/GE/FE(o)+8*GE/FE(o)+8*GE/FE(e))
               Add:virent8090DEVCP8PHST2EA29(226219),  --NetEngine A822 E AC Chassis(A)(2*10GE/GE/FE(o)+4*GE/FE(o)+8*GE/FE(e))
               Add:virent8090DEVCP8PHST2EA28(226220),  --NetEngine A822 E AC Chassis (2*10GE/GE/FE(o)+4*GE/FE(o)+8*GE/FE(e))
               Add:virent8090DEVCP8PHST1EA0A(226223),  --NetEngine A813 E AC Chassis (A)(6*GE/FE(o)+8*GE/FE(e))
               Add:virent8090DEVCP8PHST1EAAB(226224),  --NetEngine A813 E AC Chassis (6*GE/FE(o)+8*GE/FE(e))
               Add:virent8090DEVANPM01HOST7(226225),  --ATN 905-S System,AC,4*GE/FE(o),4*GE/FE(e)
               Add:virent8090DEVCR5D0SRUAI7A(226160),  --Switch and Route Processing Unit A21A(SRUA-1TA-H, 32G Memory)
               Add:virent8090DEVCR5D0SRUAI7B(226161),  --Switch and Route Processing Unit A21(SRUA-1T-H, 32G Memory)
               Add:virent8090DEVCX6D0SRUAI7A(226162),  --Switch and Route Processing Unit A21(SRUA-1T-H, 32G Memory)
               Add:virent8090DEVCX6D0SRUAI1B(226163),  --Switch and Route Processing Unit A21(SRUA-1T-H, 32G Memory)
               Add:virent8090DEVTNRD0SRUAI7A(226164),  --Switch and Route Processing Unit A21(SRUA-1T-H, 32G Memory)
               Add:virent8090DEVME0D0SRUAI7B(226165),  --Switch and Route Processing Unit A21A(SRUA-1TA-H, 32G Memory)
               Add:virent8090DEVME0D0SRUAI7C(226166),  --Switch and Route Processing Unit A21(SRUA-1T-H, 32G Memory)
               Add:virent8090DEVIG2D0SRUAI7A(226167),  --Switch and Route Processing Unit A21A(SRUA-1TA-H, 32G Memory)
               Add:virent8090DEVCR5D0SRUAH7C(226168),  --Switch and Route Processing Unit A20A(SRUA-480A-I, 32G Memory)
               Add:virent8090DEVCR5D0SRUAH7D(226169),  --Switch and Route Processing Unit A20(SRUA-480-I, 32G Memory)
               Add:virent8090DEVCX6D0SRUAH7B(226176),  --Switch and Route Processing Unit A20(SRUA-480-I, 32G Memory)
               Add:virent8090DEVCX6D0SRUAH1A(226177),  --Switch and Route Processing Unit A20(SRUA-480-I, 32G Memory)
               Add:virent8090DEVTNRD0SRUAH7B(226178),  --Switch and Route Processing Unit A20(SRUA-480-I, 32G Memory)
               Add:virent8090DEVME0D0SRUAH7D(226179),  --Switch and Route Processing Unit A20A(SRUA-480A-I, 32G Memory)
               Add:virent8090DEVME0D0SRUAH7E(226180),  --Switch and Route Processing Unit A20(SRUA-480-I, 32G Memory)
               Add:virent8090DEVME0D0SRUAH7A(226181),  --Switch and Route Processing Unit A22A(SRUA-480A-J, 32G Memory)
               Add:virent8090DEVME0D0SRUAH7P(226182),  --Switch and Route Processing Unit A22(SRUA-480-J, 32G Memory)
            "
                    REVISION    "202302081134Z"
              DESCRIPTION "V13.64
                Add virent8090DEVCR5D00E8KB61(562132),    -- V8R23C00 for CR5D00E8KB61(SBOM) 8-Port 400GBase QSFP-DD Integrated Line Process Unit(NE5000E LPUI-3T2-C) 
                Add virent8090DEVCR5D00E8KB62(562133),    -- V8R23C00 for CR5D00E8KB62(SBOM) 8-Port 400GBase QSFP-DD Integrated Line Process Unit CM(NE5000E LPUI-3T2-C-CM)(2 ports enable)
                Add virent8090DEVCR5D00EINB61(562134),    -- V8R23C00 for CR5D00EINB61(SBOM) 32-Port 100GBase QSFP28 Integrated Line Process Unit(NE5000E LPUI-3T2-C) 
                Add virent8090DEVCR5D00EINB62(562135),    -- V8R23C00 for CR5D00EINB62(SBOM) 32-Port 100GBase QSFP28 Integrated Line Process Unit CM(NE5000E LPUI-3T2-C-CM)(8 ports enable)
                Add virent8090DEVCR5D00EDNB68(562136),    -- V8R23C00 for CR5D00EDNB68(SBOM) 16-Port 100GBase QSFP28 Integrated Line Process Unit(NE5000E LPUI-1T6-G) 
                Add virent8090DEVCR5D00EDNB69(562137),    -- V8R23C00 for CR5D00EDNB69(SBOM) 16-Port 100GBase QSFP28 Integrated Line Process Unit CM(NE5000E LPUI-1T6-G-CM)(4 ports enable)
                Add virent8090DEVCR5D00LRXF65(562138),    -- V8R23C00 for CR5D00LRXF65(SBOM) 72-Port 10GBase LAN/WAN-SFP+ Integrated Line Process Unit(NE5000E LPUI-1T6-G)
                Add virent8090DEVCR5D00LRXF66(562139),    -- V8R23C00 for CR5D00LRXF66(SBOM) 72-Port 10GBase LAN/WAN-SFP+ Integrated Line Process Unit CM(NE5000E LPUI-1T6-G-CM)(24 ports enable)
            "

		    REVISION    "202302070001Z"
              DESCRIPTION "V13.63
				Add:subbname8090DEVGPR8CQ20YSD(650885),   -- 8-Port 100GBase-QSFP28 + 20-Port 25GBase-Y-SFP+
                Add:subbname8090DEVTNR1E4NBIYFS(258025),   -- 4-Port 100GBase-QSFP28 or 16-Port 25GBase-SFP28 Combo + 16-Port 25GBase-SFP28
                Add:subbname8090DEVCR81E4NBIYFS(258026),   -- 4-Port 100GBase-QSFP28 or 16-Port 25GBase-SFP28 Combo + 16-Port 25GBase-SFP28
                Add:subbname8090DEVCR81E4NBIYF(258027),    -- 4-Port 100GBase-QSFP28 or 16-Port 25GBase-SFP28 Combo + 16-Port 25GBase-SFP28
            "
		 
		    REVISION    "202302040001Z"
              DESCRIPTION "V13.62
                Add: virent8090DEVCR8DIPU1T214(658303),  -- V8R22C10 for CR8DIPU1T214(SBOM) Integrated Network Processing Unit (IPUA-1T2-F)
                Add: virent8090DEVCR8DE8KE8ND9(578779),  -- V8R22C10 for 8-Port 400GBase-QSFP-DD + 8-Port 100GBase-QSFP28 Integrated Line Processing Unit CM(LPUI-4T-E-CM,Enable 16*100GE by default)
                Add: virent8090DEVCR8DE4KEFND9(734940),  -- V8R22C10 for 4-Port 400GBase-QSFP-DD + 24-Port 100GBase-QSFP28 Integrated Line Processing Unit CM (LPUI-4T-E-CM)
                Add: virent8090DEVCR8DEKNBFED9(193229),  -- V8R22C10 for 40-Port 100GBase-QSFP28 Integrated Line Processing Unit CM(LPUI-4T-E-CM)
                Add: virent8090DEVCR8DEENBFED9(263591),  -- V8R22C10 for 20-Port 100GBase-QSFP28 Integrated Line Processing Unit CM(LPUI-2T-E-CM)
                Add: virent8090DEVCR8DERYBFED9(623955),  -- V8R22C10 for 72-Port 25GE(SFP28)/10GE(SFP+)/GE(SFP) Integrated Line Processing Unit CM(LPUI-2T-E-CM)
                Add: virent8090DEVCR8DEANEJYD9(245429),  -- V8R22C10 for 10-Port 100GBase-QSFP28 + 36-Port 25GE(SFP28)/10GE(SFP+)/GE(SFP) Integrated Line Processing Unit CM(LPUI-2T-E-CM)
                Add: virent8090DEVCR8DEANEJXDQ(818320),  -- V8R22C10 for 10-Port 100GBase-QSFP28 MACsec + 36-Port 10GE(SFP+)/GE(SFP) MACsec Integrated Line Processing Unit CM(LPUI-1T-CM)
                Add: virent8090DEVCR8DEANEJXD9(236875),  -- V8R22C10 for 10-Port 100GBase-QSFP28 + 36-Port 10GE(SFP+)/GE(SFP) Integrated Line Processing Unit CM(LPUI-1T-CM)
                Add: virent8090DEVCR8DIPU480M3(115244),  -- V8R22C10 for CR8DIPU480M3(SBOM) Integrated Network Processing Unit (IPU-480-E)
            "
		 

            REVISION    "202302040000Z"
            DESCRIPTION "V13.61,
            Add:fnameCE688248S8CQ(688251) to fnameCE5811S48T4S(688264),
            Add:bnameCE688248S8CQ(688496) to bnameCE5811S48T4S(688529),
            "
            REVISION    "202302030000Z"
              DESCRIPTION "V13.60
                Add bnameTNRMM42FBXC1(564538),    --V8R22C10 PTN 6900-2-M4 TNRMM42FBXC1
                Add virent8090DEVCR5DSFUIT27V(465407),   --  for CR5DSFUIT27V(SBOM) Finished Board Unit,NetEngine40E,CR57SFU2TES01,2Tbps Switch Fabric Unit I(SFUI-2T-I)
                Add virent8090DEVCR5DSFUIT27W(606864),   --  for CR5DSFUIT27W(SBOM) Finished Board Unit,NetEngine40E,CR57SFU2TEA01,2Tbps Switch Fabric Unit I(SFUI-2TA-I)
                Add virent8090DEVCX6DSFUIT27U(440925),   --  for CX6DSFUIT27U(SBOM) Finished Board Unit,CX600,CX61SFU2TES00,2Tbps Switch Fabric Unit I(SFUI-2T-I)
                Add virent8090DEVTNRDSFUIT27U(978034),   --  for TNRDSFUIT27U(SBOM) Finished Board Unit,PTN6900,TNR1SFU2TES00,2Tbps Switch Fabric Unit I(SFUI-2T-I)
                Add virent8090DEVIG2DSFUIT214(310202),   --  for IG2DSFUIT214(SBOM) Finished Board Unit,SIG9800,IG21SFU2TE03,2Tbps Switch Fabric Unit E1(SFUI-2TA-I)
                Add virent8090DEVCR5DSFUIT27T(721887),   --  for CR5DSFUIT27T(SBOM) Finished Board Unit,NetEngine40E,CR57SFU2TFS1,2Tbps Switch Fabric Unit J(SFUI-2T-J)
                Add virent8090DEVCR5DSFUIT27U(413155),   --  for CR5DSFUIT27U(SBOM) Finished Board Unit,NetEngine40E,CR57SFU2TFA1,2Tbps Switch Fabric Unit J(SFUI-2TA-J)
                Add virent8090DEVCX6DSFUIT27T(471946),   --  for CX6DSFUIT27T(SBOM) Finished Board Unit,CX600,CX61SFU2TFS1,2Tbps Switch Fabric Unit J(SFUI-2T-J)
                Add virent8090DEVTNRDSFUIT27T(448824),   --  for TNRDSFUIT27T(SBOM) Finished Board Unit,PTN6900,CR57SFU2TFS1,2Tbps Switch Fabric Unit J(SFUI-2T-J)
                Add virent8090DEVIG2DSFUIT213(137349),   --  for IG2DSFUIT213(SBOM) Finished Board Unit,SIG9800,IG21SFU2TFA1,2Tbps Switch Fabric Unit F1(SFUI-2TA-J)
            "

			REVISION    "202302010000Z"
              DESCRIPTION "V13.59,
				add AirEngine8771-X1T(692411),   -- WLAN R23C00 New AP
                add AirEngine5562-17W(692412),   -- WLAN R22C10 New AP
				add AirEngine5562-10(692413),    -- WLAN R22C10 New AP
				add AirEngine5562-10SW(692414),  -- WLAN R22C10 New AP
				add AC650-128AP(692415),         -- WLAN R22C10 New AC
				add AC650-256AP(692416),         -- WLAN R22C10 New AC
            "
            REVISION    "202301310000Z"
              DESCRIPTION "V13.58,
                modify: virent8090DEVCR5DSFUIT365(562189),    -- V8R21C10 for CR5DSFUIT365(SBOM) NE5000E-20 3.2T CLC Integrated Switch Fabric Unit for Multi-Chassis (SFUI-3T2-M2)
                modify: virent8090DEVCR5DSFUIT364(562190),    -- V8R21C10 for CR5DSFUIT364(SBOM) NE5000E-20 3.2T CLC Switch Fabric Unit for Single Chassis (SFU-3T2-S2)
            "
             
            REVISION "202301301000Z"
              DESCRIPTION "V13.57,
                add: virent8090DEVCR8D0MPUAXC0(688760),    -- V8R23C00 for CR8D0MPUAXC0(SBOM) NetEngine 8000 Main Processing Unit A10(MPUA10)
                add: virent8090DEVCR8D0MPUAXC2(688761),    -- V8R23C00 for CR8D0MPUAXC2(SBOM) NetEngine 8000 Main Processing Unit A10B(MPUA10B)
                add: virent8090DEVCR8D0MPUAXCA(688762),    -- V8R23C00 for CR8D0MPUAXCA(SBOM) NetEngine 8000 Main Processing Unit A10A(MPUA10A)
                add: virent8090DEVCR8D0MPUA8C6(688763),    -- V8R23C00 for CR8D0MPUA8C6(SBOM) NetEngine 8000 Main Processing Unit A9A(MPUA9A)
                add: virent8090DEVCR8D0MPUAXC1(688764),    -- V8R23C00 for CR8D0MPUAXC1(SBOM) NetEngine 8000 Main Processing Unit A11(MPUA11)
                add: virent8090DEVCR8D0MPUAXC3(688765),    -- V8R23C00 for CR8D0MPUAXC3(SBOM) NetEngine 8000 Main Processing Unit A11B(MPUA11B)
            "

            REVISION    "202301291000Z"	
              DESCRIPTION "V13.56,	
                add: fnameAR6510-L11T1X2(668048),   --AR6510-L11T1X2 FRAME
                add: fnameAR6510-L5T4S4(668049),   --AR6510-L5T4S4 FRAME
                add: fnameAR5510-H8P2TW1(668050),   --AR5510-H8P2TW1 FRAME
                add: fnameAR5510-H10T1(668051),   --AR5510-H10T1 FRAME
                add: fnameAR5510-L5T-LTE4EA(668052),   --AR5510-L5T-LTE4EA FRAME
                add: fnameAR5510-L5T(668053),   --AR5510-L5T FRAME
                add: fnameAR6500-10(668054),   --AR6500-10 FRAME

                add: bnameAR6510-L11T1X2(668163),   --AR6510-L11T1X2 Main Control Unit
                add: bnameAR6510-L5T4S4(668164),   --AR6510-L5T4S4 Main Control Unit
                add: bnameAR5510-H8P2TW1(668165),   --AR5510-H8P2TW1 Main Control Unit
                add: bnameAR5510-H10T1(668166),   --AR5510-H10T1 Main Control Unit
                add: bnameAR5510-L5T-LTE4EA(668167),   --AR5510-L5T-LTE4EA Main Control Unit
                add: bnameAR5510-L5T(668168),   --AR5510-L5T Main Control Unit

            "

		    REVISION    "202301290000Z"
              DESCRIPTION "V13.55,
                add: fname8031S5331-H48HB4XZ(537806),   -- S5331-H48HB4XZ
                add: bname8031S5331-H48HB4XZ(537990),   -- S5331-H48HB4XZ
            "

            REVISION "202301191000Z"
              DESCRIPTION "V13.54,
                add: fname8031S3710-H24T4S-A(537794),    -- S3710-H24T4S-A
                add: fname8031S3710-H24P4S-A(537795),    -- S3710-H24P4S-A
                add: fname8031S3710-H48T4S-A(537796),    -- S3710-H48T4S-A
                add: fname8031S3710-H48LP4S-A(537797),   -- S3710-H48LP4S-A
                add: fname8031S5331-S24T4X-A-V1(537798), -- S5331-S24T4X-A-V1
                add: fname8031S5331-H24P4XC-V1(537799),  -- S5331-H24P4XC-V1
                add: fname8031S5331-H48T4XC-V1(537800),  -- S5331-H48T4XC-V1
                add: fname8031S310-24P4S(537801),        -- S310-24P4S
                add: fname8031S310-24T4S(537802),        -- S310-24T4S
                add: fname8031S310-48T4S(537803),        -- S310-48T4S
                add: bname8031S3710-H24T4S-A(537978),    -- S3710-H24T4S-A
                add: bname8031S3710-H24P4S-A(537979),    -- S3710-H24P4S-A
                add: bname8031S3710-H48T4S-A(537980),    -- S3710-H48T4S-A
                add: bname8031S3710-H48LP4S-A(537981),   -- S3710-H48LP4S-A
                add: bname8031S5331-S24T4X-A-V1(537982), -- S5331-S24T4X-A-V1
                add: bname8031S5331-H24P4XC-V1(537983),  -- S5331-H24P4XC-V1
                add: bname8031S5331-H48T4XC-V1(537984),  -- S5331-H48T4XC-V1
                add: bname8031S310-24P4S(537985),        -- S310-24P4S
                add: bname8031S310-24T4S(537986),        -- S310-24T4S
                add: bname8031S310-48T4S(537987),        -- S310-48T4S"

			REVISION    "202301181000Z"	
              DESCRIPTION "V13.53,	
                add: fname8031S5331-S24S8T4X-A(537804),   -- S5331-S24S8T4X-A
                add: fname8031S5331-S24S8T4X-D(537805),   -- S5331-S24S8T4X-D
                add: bname8031S5331-S24S8T4X-A(537988),   -- S5331-S24S8T4X-A
                add: bname8031S5331-S24S8T4X-D(537989),   -- S5331-S24S8T4X-D
            "

			REVISION    "202301141000Z"	
              DESCRIPTION "V13.36,	
                Add:virent8090DEVCR8B0BKP03D4(689110),  --NetEngine 8000 F1A-8H20Q Intergrated Chassis Components(Port-side Intake)
                Add:virent8090DEVCR8B0BKP03D5(689111),  --NetEngine 8000 F1A-8H20Q Intergrated Chassis Components(Port-side Exhaust)
                Add:virent8090DEVCR8B0BKP03D0(689112),  --NetEngine 8000 F1A-8H20Q Intergrated Chassis Components(Port-side Intake)
                Add:virent8090DEVCR8B0BKP03D2(689113),  --NetEngine 8000 F1A-8H20Q Intergrated Chassis Components(Port-side Exhaust)
                Add:virent8090DEVCR8B0BKP03D6(689114),  --NetEngine 8000 F1A-8H20Q Intergrated Chassis Components(Port-side Intake)
                Add:virent8090DEVCR8B0BKP03D7(689115),  --NetEngine 8000 F1A-8H20Q Intergrated Chassis Components(Port-side Exhaust)
                Add:virent8090DEVCR8B0BKP03D1(689116),  --NetEngine 8000 F1A-8H20Q Intergrated Chassis Components(Port-side Intake)
                Add:virent8090DEVCR8B0BKP03D3(689117),  --NetEngine 8000 F1A-8H20Q Intergrated Chassis Components(Port-side Exhaust)
            "
			
			REVISION    "202301130000Z"
              DESCRIPTION "V13.51,
               		add: virent8090DEVCR5DVSUIK07M(894575),   -- V8R22C10 for CR5DVSUIK07M(SBOM) Integrated Service Unit 400(VSUI-400B)
               		add: virent8090DEVIG2D00SPUG0F(829027),   -- V8R22C10 for IG2D00SPUG0F(SBOM) High Performance X8A&X16A Service Processing Unit-SPUGA,with HW Service Inspection Gateway Software
               		add: virent8090DEVIG2D00SPUG0E(836270),   -- V8R22C10 for IG2D00SPUG0E(SBOM) High Performance X8A&X16A Enhanced Service Processing Unit-SPUGEA,with HW Service Inspection Gateway Software
               		add: virent8090DEVCR8DSFUI2TC1(676895),   -- V8R23C00 for CR8DSFUI2TC1(SBOM) NetEngine 8000 X16 14.4Tbps Switch Fabric Unit(SFUI-2T-C)
               		add: virent8090DEVCR8DSFUI2TC2(676896),   -- V8R23C00 for CR8DSFUI2TC2(SBOM) NetEngine 8000 X16 2Tbps Switch Fabric Unit(SFUIA-2T-C)
              		add: virent8090DEVCR5D0SRUAK72(183685),   --  for CR5D0SRUAK72(SBOM) Switch and Route Processing Unit A113(SRUA-2T-G, 32G Memory)
              		add: virent8090DEVCR5D0SRUAK73(959601),   --  for CR5D0SRUAK73(SBOM) Switch and Route Processing Unit A113A(SRUA-2TA-G, 32G Memory)
              		add: virent8090DEVCX6D0SRUAK72(125962),   --  for CX6D0SRUAK72(SBOM) Switch and Route Processing Unit A113(SRUA-2T-G, 32G Memory)
              		add: virent8090DEVTNRD0SRUAK72(300854),   --  for TNRD0SRUAK72(SBOM) Switch and Route Processing Unit A113(SRUA-2T-G, 32G Memory)
              		add: virent8090DEVIG2D0SRUAK72(135469),   --  for IG2D0SRUAK72(SBOM) Switch and Route Processing Unit A113A(SRUA-2TA-G, 32G Memory)
              "

			REVISION    "202301090000Z"
              DESCRIPTION "V13.50,
				add: fname8031S6330-H24X4Y(537793),   -- S6330-H24X4Y (24*10GE SFP+ ports, 4*25GE SFP28 ports, optional RTU upgrade to 4*100GE QSFP28, without power module)
              "
			REVISION    "202301090000Z"
              DESCRIPTION "V13.49,
				add: subbname8090DEVME0D00E1KB71(542988),   -- 1-Port 400GBase-QSFP-DD + 2-Port External OA Flexible Card(BP1T)
              "

			REVISION    "202212190000Z"
              DESCRIPTION "V13.48,
				add: subbnamePTN7900TPA7FH2E(229705),   -- PTN7900TPA7FH2E
                add: subbnamePTN7900TPA7FH4E(229706),   -- PTN7900TPA7FH4E
              "
			
		   REVISION    "202212160000Z"
              DESCRIPTION "V13.47,
				add: subbname8090DEVGPLI10CQ36XSES1(582393),   -- 36-Port 10GE(SFP+)/GE(SFP) 10-Port 100GBase QSFP28 Integrated Line Process Unit
                add: subbname8090DEVGPLI10CQ36XSE2(582394),   -- 36-Port 10GE(SFP+)/GE(SFP) 10-Port 100GBase QSFP28 Integrated Line Process Unit
                add: subbname8090DEVGFL72GSFB(548674),      -- 72-port GE MACsec Physical Interface Card(PIC)
				add: subbname8090DEVCR8DERGF00F1(548774),   -- NetEngine 8000 F 2T Switch Routing Unit(SRU-2T-A)
              "
			
           REVISION    "202212060000Z"
              DESCRIPTION "V13.46,
                add: S5735I-L8P4X-A-V2(537791),        --S5735I-L8P4X-A-V2
                add: S5735I-L10T4X-A-V2(537792),       --S5735I-L10T4X-A-V2
                add: 16700,       ---HUAWEI S16700
              "

           REVISION    "202211300000Z"	
              DESCRIPTION "V13.45,	
               Add: fnameNETENGINE-A820-M(229517),       -- V8R21C00 for NETENGINE-A820-M chassis
               Add: virent8090DEVME0D0SRUAH78(553461),   --  for ME0D0SRUAH78(SBOM) Switch and Route Processing Unit A22A(SRUA-480A-J, 32G Memory)
               Add: virent8090DEVME0D0SRUAH79(553462),   --  for ME0D0SRUAH79(SBOM) Switch and Route Processing Unit A22(SRUA-480-J, 32G Memory)
               Add: virent8090DEVCR8DE2UB00D1(676980),   -- V8R22C10 for CR8DE2UB00D1(SBOM) 2-Port 1.2TBase Integrated Line Processing Unit(LPUI-2T4A)
               Add: virent8090DEVTPND02CXPB01(901611),   --  for TPND02CXPB01(SBOM) OptiX PTN 980, TPN2CXPA3, System Control,Cross-connect and Multi-protocol Process Unit
               Add: virent8090DEVTPND02CXPB02(932124),   --  for TPND02CXPB02(SBOM) OptiX PTN 980, TPN2CXPA4, System Control,Cross-connect and Multi-protocol Process Unit
               Add: virent8090DEVTPQD01CXPB01(852453),   --  for TPQD01CXPB01(SBOM) OptiX PTN 990E, TPQ1CXPA4, System Control,Cross-connect and Multi-protocol Process Unit
               Add: virent8090DEVTPQD01CXPB02(967204),   --  for TPQD01CXPB02(SBOM) OptiX PTN 990E, TPQ1CXPA4, System Control,Cross-connect and Multi-protocol Process Unit
              "

           REVISION    "202211280000Z"	
              DESCRIPTION "V13.44,	
               Add: subbname8090DEVCR5D0LEXFM20(483067),   -- 20-Port 10GBase LAN/WAN-SFP+ Flexible Card(P483)
              "

           REVISION    "202211260000Z"	
              DESCRIPTION "V13.43,	
               virent8090DEVCR5D0MPUB97A(689102),  -- V8R22C10 for CR5D0MPUB97A(SBOM) Main Processing Unit B12(32G Memory)
               virent8090DEVCR5D0MPUB97B(689103),  -- V8R22C10 for CR5D0MPUB97B(SBOM) Main Processing Unit B12A(32G Memory)
               virent8090DEVCX6DMPUX867A(689104),  -- V8R22C10 for CX6DMPUX867A(SBOM) Main Processing Unit B12(32G Memory)
               virent8090DEVCX6DMPUB121A(689105),  -- V8R22C10 for CX6DMPUB121A(SBOM) Main Processing Unit B12A(32G Memory)
               virent8090DEVTNRDMPUX867A(689106),  -- V8R22C10 for TNRDMPUX867A(SBOM) Main Processing Unit B12(32G Memory)
               virent8090DEVME0DMPUX867A(689107),  -- V8R22C10 for ME0DMPUX867A(SBOM) Main Processing Unit B12(32G Memory)
               virent8090DEVME0DMPUX867B(689108),  -- V8R22C10 for ME0DMPUX867B(SBOM) Main Processing Unit B12A(32G Memory)
               virent8090DEVIG2D0MPUB97B(689109),  -- V8R22C10 for IG2D0MPUB97B(SBOM) Main Processing Unit B12A(32G Memory)
              "

		   REVISION    "202211240000Z"	
              DESCRIPTION "V13.42,	
              Add: subbnameH901CPCDE(148525),       -- Clock subboard of EA5800-X2 H901MPSDE.
              Add: subbnameH903CKUF(148526),        -- CLock subboard of MA5800.
		      Add: bnameV921FLHFE(148787),          --  16*GPON board of EA5801E_FL16_H1.
			  Add: bnameV921MPCBE(148788),          --  control board of EA5801E_FL16_H1.
              Add: bnameH903PISB(148789),           --  AC Power board of MA5800-X2.
			  Add: bnameH901MPSDE(148797),          -- control board of EA5800-X2.
              Add: bnameH907MPLB(148798),           -- control board of MA5800.
              Add: bnameH907MPLBE(148799),          -- control board of EA5800.
			  Add: bnameH902MPLG(148802),           -- control board of MA5800.
              Add: bnameH902MPLGE(148803),          -- control board of EA5800.
              Add: bnameORCSF2(148806),             -- 16*XGS combo board of EA5800.
              Add: bnameH902CSPDE(148807),          -- 8*XGS combo board of EA5800.
              Add: bnameH902CGPDE(148808),          -- 8*XG/G combo board of EA5800.
              "
		   
		   REVISION    "202211230000Z"	
              DESCRIPTION "V13.41,	
              Add:subbname8090DEVCR5D0LFXFM76(303393),   -- 24-Port 10GBase LAN/WAN-SFP+ MACsec Flexible Card(P483D)
              Add:subbname8090DEVCR5DE1NBFM76(656681),   -- 2-Port 50GBase/1-Port 100GBase-QSFP28 FlexE/MACsec Flexible Card(P243D)
			  Add:subbname8090DEVCR5D0LBXFM76(878564),   -- 12-Port 10GBase LAN/WAN-SFP+ MACsec Flexible Card (P243D)
			  Add:subbname8090DEVCR5D0EFGFM76(945736),   -- 24-Port 100/1000Base-X-SFP MACsec Flexible Card (P53D)
			  Add:subbname8090DEVCR57L8XEDI0(295993),    --8-Port GE-SFP/10GE-SFP+ and 16-Port GE-SFP Unflexible Card(P243)
              "
			  
		   REVISION    "202211220000Z"	
              DESCRIPTION "V13.36,	
              Add:virent8090DEVCR5DLPUF5371(689091),  --Flexible Card Line Processing Unit(LPUF-53)
              Add:virent8090DEVCR5DLPUF5373(689092),  --Flexible Card Line Processing Unit(LPUF-53)
			  Add:virent8090DEVCR5DLPUF5370(689093),  --Flexible Card Line Processing Unit(LPUF-53A)
			  Add:virent8090DEVCR5DLPUF5374(689094),  --Flexible Card Line Processing Unit(LPUF-53A)
			  Add:virent8090DEVCR5DLPUF5372(689095),  --Flexible Card Line Processing Unit(LPUF-53A)
			  Add:virent8090DEVCR5DLPUF5375(689096),  --Flexible Card Line Processing Unit(LPUF-53)
			  Add:virent8090DEVCR5DLPUFF370(689097),  --Flexible Card Line Processing Unit(LPUF-243)
			  Add:virent8090DEVCR5DLPUFF371(689098),  --Flexible Card Line Processing Unit(LPUF-243A)
			  Add:virent8090DEVCR5DLPUFF374(689099),  --Flexible Card Line Processing Unit(LPUF-243A)
			  Add:virent8090DEVCR5DLPUFF377(689100),  --Flexible Card Line Processing Unit(LPUF-243A-CM)
			  Add:virent8090DEVCR5DLPUFF378(689101),  --Flexible Card Line Processing Unit(LPUF-243A-CM)
              "
		   
		   REVISION    "202211210000Z"	
              DESCRIPTION "V13.39,	
              bnameCEL24XS12CQFDE(688515),   -- V3R22C10 for CEL24XS12CQFD-E
              "
			  
           REVISION    "202211170000Z"	
              DESCRIPTION "V13.38,	
              virent8090DEVME0DBSUFT07C(493006),   -- V8R22C10 for ME0DBSUFT07C(SBOM) Flexible Card Broadband Service Unit(BSUF-1T2A-E,2 sub-slots)
              virent8090DEVME0DBSUFT07E(493007),   -- V8R22C10 for ME0DBSUFT07E(SBOM) Flexible Card Broadband Service Unit(BSUF-1T2-E,2 sub-slots)
              "

           REVISION    "202211160000Z"	
              DESCRIPTION "V13.37,	
               virent8090DEVCR8PM4BASDC6(689008),  -- V8R22C10 for CR8PM4BASDC6(SBOM) NetEngine 8000 M4 Basic Configuration CM (Enable Fixed Interface(2*100GE or 8*25GE combo+16*10GE,#4~19 enable GE), DC Power, without Software Charge,Document and auxiliary materials)
               virent8090DEVCR8PM4BASDC7(689009),  -- V8R22C10 for CR8PM4BASDC7(SBOM) NetEngine 8000 M4 Basic Configuration CM (Includes NetEngine 8000 M4 Chassis, Enable Fixed Interface, DC Power,without Software Charge,Document and auxiliary materials)
               virent8090DEVCR8PM4BASAC6(689010),  -- V8R22C10 for CR8PM4BASAC6(SBOM) NetEngine 8000 M4 Basic Configuration CM (Enable Fixed Interface(2*100GE or 8*25GE combo+16*10GE,#4~19 enable GE),AC Power,without Software Charge,Document and auxiliary materials)
               virent8090DEVCR8PM4BASAC7(689011),  -- V8R22C10 for CR8PM4BASAC7(SBOM) NetEngine 8000 M4 Basic Configuration CM (Includes NetEngine 8000 M4 Chassis, Enable Fixed Interface, AC Power,without Software Charge,Document and auxiliary materials)
               virent8090DEVCR8PM9BASACQ(689012),  -- V8R22C10 for CR8PM9BASACQ(SBOM) Integrated Network Processing Unit (IPUA-1T2-F)
               virent8090DEVCR8DIPU640C9(689013),  -- V8R22C10 for CR8DIPU640C9(SBOM) Integrated Network Processing Unit (IPUA-640)
               virent8090DEVTNRDIPU1T292(689014),  -- V8R22C10 for TNRDIPU1T292(SBOM) Integrated Network Processing Unit (IPU-1T2-F)
               virent8090DEVTNRDIPU48091(689015),  -- V8R22C10 for TNRDIPU48091(SBOM) Integrated Network Processing Unit (IPU-480-F)
               virent8090DEVCR8DIPU1T213(689016),  -- V8R22C10 for CR8DIPU1T213(SBOM) Integrated Network Processing Unit (IPUA-1T2-F)
               virent8090DEVCR8DIPU480MA(689017),  -- V8R22C10 for CR8DIPU480MA(SBOM) Integrated Network Processing Unit (IPU-480-CN)
               virent8090DEVCR8DIPU480MB(689018),  -- V8R22C10 for CR8DIPU480MB(SBOM) Integrated Network Processing Unit (IPUA-480-CN)
               virent8090DEVCR8DIPU1T2M6(689019),  -- V8R22C10 for CR8DIPU1T2M6(SBOM) Integrated Network Processing Unit (IPU-1T2-E)
               virent8090DEVCR8DIPU480M2(689020),  -- V8R22C10 for CR8DIPU480M2(SBOM) Integrated Network Processing Unit (IPU-480-E)
               virent8090DEVCR8D0IPU1T2MG(689021),  -- V8R22C10 for CR8D0IPU1T2MG(SBOM) Integrated Network Processing Unit (IPUA-1T2-E)
               virent8090DEVCR8D0IPU480MB(689022),  -- V8R22C10 for CR8D0IPU480MB(SBOM) Integrated Network Processing Unit (IPUA-480-E)
               virent8090DEVCR8DIPU480MC(689023),  -- V8R22C10 for CR8DIPU480MC(SBOM) Integrated Network Processing Unit (IPUA-480-E)
               virent8090DEVCR8D0IPU1T2MP(689024),  -- V8R22C10 for CR8D0IPU1T2MP(SBOM) Integrated Network Processing Unit (IPUA-1T2-E)
               virent8090DEVCR8DIPU1T2MT(689025),  -- V8R22C10 for CR8DIPU1T2MT(SBOM) Integrated Network Processing Unit (IPU-1T2-DA)
               virent8090DEVCR8DIPU480MG(689026),  -- V8R22C10 for CR8DIPU480MG(SBOM) Integrated Network Processing Unit (IPU-480-DA)
               virent8090DEVCR8DIPU1T2M4(689027),  -- V8R22C10 for CR8DIPU1T2M4(SBOM) Integrated Network Processing Unit (IPUA-1T2-DA)
               virent8090DEVCR8DIPU480M1(689028),  -- V8R22C10 for CR8DIPU480M1(SBOM) Integrated Network Processing Unit (IPUA-480-DA)
               virent8090DEVCR8D0IPU2TD2(689029),  -- V8R22C10 for CR8D0IPU2TD2(SBOM) Integrated Network Processing Unit (IPUA-2T-F)
               virent8090DEVCR8D0IPU2TM1(689030),  -- V8R22C10 for CR8D0IPU2TM1(SBOM) Integrated Network Processing Unit (IPU-2T-E)
               virent8090DEVCR8DIPUT2TM1(689031),  -- V8R22C10 for CR8DIPUT2TM1(SBOM) Integrated Network Processing Unit (IPU-1T2-E)
               virent8090DEVTNRD0IPU2T90(689032),  -- V8R22C10 for TNRD0IPU2T90(SBOM) Integrated Network Processing Unit (IPU-2T-F)
               virent8090DEVTNRDIPUT2T90(689033),  -- V8R22C10 for TNRDIPUT2T90(SBOM) Integrated Network Processing Unit (IPU-1T2-F)
               virent8090DEVCR5D0IPU2T91(689034),  -- V8R22C10 for CR5D0IPU2T91(SBOM) Integrated Network Processing Unit (IPU-2T-E)
               virent8090DEVCR5DIPUT2T91(689035),  -- V8R22C10 for CR5DIPUT2T91(SBOM) Integrated Network Processing Unit (IPU-1T2-E)
               virent8090DEVCR8D0IPU2TM2(689036),  -- V8R22C10 for CR8D0IPU2TM2(SBOM) Integrated Network Processing Unit (IPUA-2T-E)
               virent8090DEVCR8DIPU1T2M3(689037),  -- V8R22C10 for CR8DIPU1T2M3(SBOM) Integrated Network Processing Unit (IPU-1T2-EN)
               virent8090DEVTNRDIPU1T290(689038),  -- V8R22C10 for TNRDIPU1T290(SBOM) Integrated Network Processing Unit (IPU-1T2-FN)
               virent8090DEVCR5DIPU1T291(689039),  -- V8R22C10 for CR5DIPU1T291(SBOM) Integrated Network Processing Unit (IPU-1T2-EN)
               virent8090DEVCR8D0IPU1T2ME(689040),  -- V8R22C10 for CR8D0IPU1T2ME(SBOM) Integrated Network Processing Unit (IPUA-1T2-EN)
               virent8090DEVCR8D0IPU1T2MK(689041),  -- V8R22C10 for CR8D0IPU1T2MK(SBOM) Integrated Network Processing Unit (IPUA-1T2-EN)
               virent8090DEVCR8DIPU1T2MS(689042),  -- V8R22C10 for CR8DIPU1T2MS(SBOM) Integrated Network Processing Unit (IPU-1T2-DA)
               virent8090DEVCR8DIPU1T2M2(689043),  -- V8R22C10 for CR8DIPU1T2M2(SBOM) Integrated Network Processing Unit (IPUA-1T2-DA)
               virent8090DEVANND00CXPC00(689044),  -- V8R22C10 for ANND00CXPC00(SBOM) System Control,Cross-connect and Multi-protocol Process Unit with 800G
               virent8090DEVANND00CXPC03(689045),  -- V8R22C10 for ANND00CXPC03(SBOM) System Control,Cross-connect and Multi-protocol Process Unit with 360G
               virent8090DEVANND00CXPB01(689046),  -- V8R22C10 for ANND00CXPB01(SBOM) System Control,Cross-connect and Multi-protocol Process Unit with 320G
               virent8090DEVANND00CXPB02(689047),  -- V8R22C10 for ANND00CXPB02(SBOM) System Control,Cross-connect and Multi-protocol Process Unit with 360G
               virent8090DEVANND01CXPB01(689048),  -- V8R22C10 for ANND01CXPB01(SBOM) System Control,Cross-connect and Multi-protocol Process Unit with 800G
               virent8090DEVANRD00CXPC00(689049),  -- V8R22C10 for ANRD00CXPC00(SBOM) System Control, Cross-connect and Multi-protocol Process Unit with 160G
               virent8090DEVANRD00CXPA21(689050),  -- V8R22C10 for ANRD00CXPA21(SBOM) System Control, Cross-connect and Multi-protocol Process Unit with 160G
               virent8090DEVANRD01CXPD00(689051),  -- V8R22C10 for ANRD01CXPD00(SBOM) System Control, Cross-connect and Multi-protocol Process Unit with 400G
               virent8090DEVANRD01CXPE00(689052),  -- V8R22C10 for ANRD01CXPE00(SBOM) System Control, Cross-connect and Multi-protocol Process Unit with 800G
               virent8090DEVCR8DCXP160C6(689053),  -- V8R22C10 for CR8DCXP160C6(SBOM) System Control,Cross-connect and Multi-protocol Process Unit (CXP-160-C)
               virent8090DEVCR8DCXP160C7(689054),  -- V8R22C10 for CR8DCXP160C7(SBOM) System Control,Cross-connect and Multi-protocol Process Unit (CXPA-160-C)
               virent8090DEVANHMHSTA0101(689055),  -- V8R22C10 for ANHMHSTA0101(SBOM) ATN 910D-A, DC Power, Port Capacity 4*100GE/50GE + 16*25GE/10GE/GE/FE + 8*10GE/GE/FE, default all the GE/FE ports is enabled
               virent8090DEVANHMHSTA0201(689056),  -- V8R22C10 for ANHMHSTA0201(SBOM) ATN 910D-A, AC Power, Port Capacity 4*100GE/50GE + 16*25GE/10GE/GE/FE + 8*10GE/GE/FE, default all the GE/FE ports is enabled
               virent8090DEVANHMHSTA0122(689057),  -- V8R22C10 for ANHMHSTA0122(SBOM) ATN 910D-A, DC Power, Port Capacity 4*100GE/50GE + 16*25GE/10GE/GE/FE + 8*10GE/GE/FE, default all the GE/FE ports is enabled
               virent8090DEVANHMHSTA0222(689058),  -- V8R22C10 for ANHMHSTA0222(SBOM) ATN 910D-A, AC Power, Port Capacity 4*100GE/50GE + 16*25GE/10GE/GE/FE + 8*10GE/GE/FE, default all the GE/FE ports is enabled
               virent8090DEVANHMHSTA0332(689059),  -- V8R22C10 for ANHMHSTA0332(SBOM) ATN 910D-A, AC+DC Power, Port Capacity 4*100GE/50GE + 16*25GE/10GE/GE/FE + 8*10GE/GE/FE, default all the GE/FE ports is enabled
               virent8090DEVANEMHSTA0100(120021),  -- V8R25C00 for ANEMHSTA0100(SBOM) ATN 910E, DC Power, Port Capacity 2*400GE/100GE+4*100GE/50GE+8*50GE/25GE/10GE/GE+16*25GE/10GE/GE, all the GE ports is enabled
               virent8090DEVCR8PM1DBASCFP(689060),  -- V8R22C10 for CR8PM1DBASCFP(SBOM) NetEngine 8000 M1D-B DC(Port Capacity 2*50GE+2*25GE/10GE+2*10GE+14*GE,default 2*25GE&all GE,no aux material)
               virent8090DEVCR8PM1DBASCQ(689061),  -- V8R22C10 for CR8PM1DBASCQ(SBOM) NetEngine 8000 M1D-B DC(A)(Port Capacity 2*50GE+2*25GE/10GE+2*10GE+14*GE,default 2*25GE&all GE,no aux material)
               virent8090DEVCR8PM1DBASCR(689062),  -- V8R22C10 for CR8PM1DBASCR(SBOM) NetEngine 8000 M1D-B AC(Port Capacity 2*50GE+2*25GE/10GE+2*10GE+14*GE,default 2*25GE&all GE,no aux material)
               virent8090DEVCR8PM1DBASCS(689063),  -- V8R22C10 for CR8PM1DBASCS(SBOM) NetEngine 8000 M1D-B AC(A)(Port Capacity 2*50GE+2*25GE/10GE+2*10GE+14*GE,default 2*25GE&all GE,no aux material)
               virent8090DEVANHMHSTA0502(689064),  -- V8R22C10 for ANHMHSTA0502(SBOM) ATN 910D-B, DC Power, Port Capacity 2*50GE+2*25GE/10GE/GE+2*10GE/GE+10*GE(o)+4*GE(e), default 2*25GE and all GE/FE ports
               virent8090DEVANHMHSTA0602(689065),  -- V8R22C10 for ANHMHSTA0602(SBOM) ATN 910D-B, AC Power, Port Capacity 2*50GE+2*25GE/10GE/GE+2*10GE/GE+10*GE(o)+4*GE(e), default 2*25GE and all GE/FE ports
               virent8090DEVANGMHSTG0105(689066),  -- V8R22C10 for ANGMHSTG0105(SBOM) ATN 910C-G, DC Power, Port Capacity 16*10GE/GE/FE(o)+12*GE/FE(o)+4*GE/FE(e), Default 2*10GE+8*GE
               virent8090DEVANGMHSTG0204(689067),  -- V8R22C10 for ANGMHSTG0204(SBOM) ATN 910C-G, AC Power, Port Capacity 16*10GE/GE/FE(o)+12*GE/FE(o)+4*GE/FE(e), Default 2*10GE+8*GE
               virent8090DEVCR8PM1ABASD0(689068),  -- V8R22C10 for CR8PM1ABASD0(SBOM) NetEngine 8000 M1A, DC Power,Port Capacity 16*10GE+12*GE(o)+4*GE(e)
               virent8090DEVCR8PM1ABASA0(689069),  -- V8R22C10 for CR8PM1ABASA0(SBOM) NetEngine 8000 M1A, AC Power,Port Capacity 16*10GE+12*GE(o)+4*GE(e)
               virent8090DEVCR8PM1ABASD1(689070),  -- V8R22C10 for CR8PM1ABASD1(SBOM) NetEngine 8000 M1A, DC Power,Port Capacity 16*10GE+12*GE(o)+4*GE(e)
               virent8090DEVCR8PM1ABASA1(689071),  -- V8R22C10 for CR8PM1ABASA1(SBOM) NetEngine 8000 M1A, AC Power,Port Capacity 16*10GE+12*GE(o)+4*GE(e)
               virent8090DEVANGMHSTK0103(689072),  -- V8R22C10 for ANGMHSTK0103(SBOM) ATN 910C-K, DC Power, Port Capacity 16*10GE/GE/FE+8*GE/FE(o)+4*GE/FE(e)+16*E1,None of the ports are available by default
               virent8090DEVANGMHSTK0203(689073),  -- V8R22C10 for ANGMHSTK0203(SBOM) ATN 910C-K, AC Power, Port Capacity 16*10GE/GE/FE+8*GE/FE(o)+4*GE/FE(e)+16*E1,None of the ports are available by default
               virent8090DEVANGMHSTM0103(689074),  -- V8R22C10 for ANGMHSTM0103(SBOM) ATN 910C-M, DC Power, Port Capacity 16*10GE/GE/FE+8*GE/FE(o)+4*GE/FE(e),None of the ports are available by default
               virent8090DEVANGMHSTM0203(689075),  -- V8R22C10 for ANGMHSTM0203(SBOM) ATN 910C-M, AC Power, Port Capacity 16*10GE/GE/FE+8*GE/FE(o)+4*GE/FE(e),None of the ports are available by default
               virent8090DEVANGMHSTM0301(689076),  -- V8R22C10 for ANGMHSTM0301(SBOM) ATN 910C-M, AC+DC Power, Port Capacity 16*10GE/GE/FE+8*GE/FE(o)+4*GE/FE(e),None of the ports are available by default
               virent8090DEVCR8PM1CBASD0(689077),  -- V8R22C10 for CR8PM1CBASD0(SBOM) NetEngine 8000 M1C, 2*DC Power, Port Capacity 16*10GE+8*GE(o)+4*GE(e), None of the ports are available by default
               virent8090DEVCR8PM1CBASAQ(689078),  -- V8R22C10 for CR8PM1CBASAQ(SBOM) NetEngine 8000 M1C, 2*AC Power, Port Capacity 16*10GE+8*GE(o)+4*GE(e), None of the ports are available by default
               virent8090DEVCR8PM1CBASD1(689079),  -- V8R22C10 for CR8PM1CBASD1(SBOM) NetEngine 8000 M1C(A), 2*DC Power, Port Capacity 16*10GE+8*GE(o)+4*GE(e), None of the ports are available by default
               virent8090DEVCR8PM1CBASAS(689080),  -- V8R22C10 for CR8PM1CBASAS(SBOM) NetEngine 8000 M1C(A), 2*AC Power, Port Capacity 16*10GE+8*GE(o)+4*GE(e), None of the ports are available by default
               virent8090DEVANGMHSTH0110(689081),  -- V8R22C10 for ANGMHSTH0110(SBOM) ATN 910C-H DC Basic Configuration(Includes Fixed Enable Interface (4*10GE/GE/FE(o)+4*GE/FE(o)+4*GE/FE(e))/Dual Power/FAN/Chassis)
               virent8090DEVANGMHSTS0110(689082),  -- V8R22C10 for ANGMHSTS0110(SBOM) ATN 910C-S DC Basic Configuration(Includes Fixed Enable Interface (5*10GE/GE/FE(o)+3*GE/FE(o)+4*GE/FE(e))/Dual Power/FAN/Chassis)
               virent8090DEVANGMHSTH0210(689083),  -- V8R22C10 for ANGMHSTH0210(SBOM) ATN 910C-H AC Basic Configuration(Includes Fixed Enable Interface (4*10GE/GE/FE(o)+4*GE/FE(o)+4*GE/FE(e))/Power/FAN/Chassis)
               virent8090DEVANGMHSTS0210(689084),  -- V8R22C10 for ANGMHSTS0210(SBOM) ATN 910C-S AC Basic Configuration(Includes Fixed Enable Interface (5*10GE/GE/FE(o)+3*GE/FE(o)+4*GE/FE(e))/Power/FAN/Chassis)
               virent8090DEVCR5DLPUFM397(689085),  -- V8R22C10 for CR5DLPUFM397(SBOM) Flexible Card Line Processing Unit(LPUF-483D)
               virent8090DEVCR5DLPUFF394(689086),  -- V8R22C10 for CR5DLPUFF394(SBOM) Flexible Card Line Processing Unit(LPUF-243D)
               virent8090DEVCR5DLPUF5376(689087),  -- V8R22C10 for CR5DLPUF5376(SBOM) Flexible Card Line Processing Unit(LPUF-53D)
               virent8090DEVME0DVSUIK07F(689088),  -- V8R22C10 for ME0DVSUIK07F(SBOM) Integrated Service Unit 400(VSUI-400D)
               virent8090DEVANGMHSTM03D0(689089),  -- V8R22C10 for ANGMHSTM03D0(SBOM) ATN 910C-M,2*DC Power, Port Capacity 6*10GE+4*GE/FE(o)+4*GE/FE(e)
               virent8090DEVANGMHSTM03A0(689090),  -- V8R22C10 for ANGMHSTM03A0(SBOM) ATN 910C-M, 2*AC Power, Port Capacity 6*10GE+4*GE/FE(o)+4*GE/FE(e)
              "

           REVISION    "202211140000Z"	
              DESCRIPTION "V13.36,	
              Add:fnameEA5801SFL16H2(148540),     -- Backplane of the EA5801S-FL16-H2.			
              Add:bnameH907CIUA(148724),          --  GPIO board of MA5800.
              Add:bnameV932MPBAE(148800),         -- control board of EA5801S-FL16-H2.			
              Add:bnameV932FLHFE(148801),         -- 16*flex-PON board of EA5801S-FL16-H2.			
              "

		REVISION    "202211102000Z"
            DESCRIPTION "V13.35,
            Add: fnameET1BS12704EZ0(700427),               -- S12700E-4-Z Assembly Chassis for V2R22C10
            Add: fnameET1BS12708EZ0(700428),               -- S12700E-4-Z Assembly Chassis for V2R22C10
            Add: bnameLST7MPUE000Z0(700546),    		 -- S12700E main control unit E(Z) for V2R22C10
            Add: bnameLST7SFUEX10Z0(700547),    		   -- S12700E switch fabric unit E(Z) for V2R22C10
            Add: bnameLST7SFUHX10Z0(700548),    		   -- S12700E switch fabric unit H(Z) for V2R22C10
            Add: bnameLST7G48SX6EZ0(700549),    		   -- 48-port GE SFP interface card (Z,SFP) for V2R22C10
            Add: bnameLST7X24BX6EZ0(700550),    		   -- 24-port 10GE SFP+ interface and 24-port GE SFP interface card (Z,SFP+) for V2R22C10
            Add: bnameLST7X48SX6EZ0(700551),    		   -- 48-Port 10GE SFP+ interface card (Z,SFP+) for V2R22C10
            Add: bnameLST7C06HX6EZ0(700553),    		   -- 6-port 100GE QSFP28 interface card (Z,QSFP28) for V2R22C10
            Add: bnameLST7C24HX6EZ0(700554),    		   -- 6-port 100GE QSFP28 interface card (Z,QSFP28) for V2R22C10
            Add: bnameLST7G48TX5EZ0(700552),    		   -- 6-port 100GE QSFP28 interface card (Z,QSFP28) for V2R22C10
            Add: bnameLST7G48TX6EZ0(700564),    		   -- 48-port 100/1000BASE-T interface card (Z,RJ45) for V2R22C10
            "
        
		REVISION    "202211100000Z"
            DESCRIPTION "V13.34,
            Add:subbname8090DEVCX6DE4NE8VA0(229729),   -- 4-Port 100GBase-QSFP28 FlexE Flexible Card(S1T)
            "

        REVISION    "202211080000Z"
            DESCRIPTION "V13.33,
            Add:subbname8090DEVCR2D0LBXFME0(784745),
            Add:subbname8090DEVCR2DE1NBFME0(784746),
            Add:virent8090DEVTPZM0HOSTA00(229537),
            Add:virent8090DEVTPZM0HOSTA02(229538),
            Add:fnamePTN907-AC(229547),
            "

        REVISION    "202211080000Z"
            DESCRIPTION "V13.31,
            Add:virent8090DEVCR8DMPUF8AF2(468786),   -- V8R22C10 for CR8DMPUF8AF2(SBOM) NetEngine 8000E F Main Processing Unit B2A(MPUB2A)
            Add:virent8090DEVCR8DMPUF8BF1(468787),   -- V8R22C10 for CR8DMPUF8BF1(SBOM) NetEngine 8000 F Main Processing Unit B2(MPUB2)
            "
		
		REVISION    "202211070000Z"
            DESCRIPTION "V13.31,
            Add:subbname8090DEVDPE1E4NBIYF(258024),   -- 4-Port 100GBase-QSFP28 or 16-Port 25GBase-SFP28 Combo + 16-Port 25GBase-SFP28
            Add:subbname8090DEVDPE1E4NBIYFS(258023),   -- 4-Port 100GBase-QSFP28 or 16-Port 25GBase-SFP28 Combo + 16-Port 25GBase-SFP28
            "

        REVISION    "202211040000Z"
        DESCRIPTION "V13.30,
            Add:bnameSIC-4E1-V2(668162),                     --SIC-4E1-V2 Lpu Control Unit
            "

        REVISION    "202211030000Z"
            DESCRIPTION "V13.29,
            Modify:fnameNETENGINE-A835-T-DC(229683),
            Add:fnameNETENGINE-A835-T-AC(229684),
            Add:fnameNETENGINE-NE20-X3(229690),
            Add:virent8090DEVCR2D0MPUD4E1(468800),
            Add:virent8090DEVCR2DLPUFF3E1(468801),
            Add:virent8090DEVCR2D0LBXFME0(468802),
            Add:virent8090DEVCR2DE1NBFME0(468803),
            Add:virent8090DEVCR2B0BKP03EB(468804),
            Add:virent8090DEVCR2B0BKP03E9(468805),
            "

        REVISION    "202211010000Z"
            DESCRIPTION "V13.28,
            Add:subbnameCE98D32CQA(688146),
            "
        REVISION    "202210310000Z"
            DESCRIPTION "V13.27,
            Add:subbname8090DEVANND001EN100(934629),
            Add:subbname8090DEVCR5D00E1KB74(452214),
			Add:subbname8090DEVCR5D00E1KB75(541988),
			Add:subbname8090DEVIG2D00E1KB72(443624),
			Add:subbname8090DEVCR57EENBD0(887788),
			Add:subbname8090DEVCR57EENBDS0(198210),
			Add:subbname8090DEVGPLI36YS10CQE2(582392),
			Add:subbname8090DEVGPLI8KQ8CQES4(824727),
			Add:subbname8090DEVGPLI8KQ8CQE5(806150),
			Add:subbname8090DEVGPI2KFE1(675384),
            "
        REVISION    "202210250000Z"
            DESCRIPTION "V13.26,
            Delete:virent8090DEVTPXM01HSTA00(229533),
            Add:virent8090DEVTPXM0HOSTA00(229533),
            Add:virent8090DEVTPVM0HOSTA02(229544),
            Modify:fnameNETENGINE-A831-E-DC(229665)
            Modify:virent8090DEVCP8PHST2EA10(525137)
            "
        REVISION    "202210240000Z"
            DESCRIPTION "V13.25,
            Add:fnameCE6882H48S8CQ(688251),
            Add:fnameCE6867ULL(688252),
            Add:fnameCE6867H48S8CQ(688253),
            Add:fnameCE6867H48S8CQT(688254),
            Add:fnameCE6867HAM(688255),
            Add:fnameCE6867SAN(688256),
            Add:fnameCE885236CQ(688257),
            Add:fnameCE16804H(688258),
            Add:fnameCE16808H(688259),
            Add:fnameCE16816H(688260),
            Add:bnameCE6882H48S8CQ(688496),
            Add:bnameCE6867ULL(688497),
            Add:bnameCE6867H48S8CQ(688498),
            Add:bnameCE6867H48S8CQT(688499),
            Add:bnameCE6867HAM(688500),
            Add:bnameCE6867SAN(688501),
            Add:bnameCE885236CQ(688502),
            Add:bnameCEL36CQHGP1(688503),
            Add:bnameCEL48XSHGP1(688504),
            Add:bnameCEL48XSHGAP1(688505),
            Add:bnameCE16804H(688506),
            Add:bnameCE16808H(688507),
            Add:bnameCE16816H(688508),
            Add:bnameCEL36LQHGP1(688509),
            Add:bnameCEL24CQHGP1(688510),
            Add:bnameCESFU08DL2E(688511),
            Add:bnameCESFU04DL2E(688512),
            Add:bnameCESFU04DH2E(688513),
            Add:bnameCESFU16DL2E(688514),
            "
        REVISION    "202210190000Z"
            DESCRIPTION "V13.24,
            Add:fnameMA5801SFL16H2(148539),    --  Backplane of the MA5801S-FL16-H2.
            Add:bnameV932MPBA(148793),         --  control board of MA5801S-FL16-H2.
            Add:bnameV935NXHC(148794),         --  4*10GE board of MA5801S-FL16-H2.
            Add:bnameV932FLHF(148795),         --  16*flex-PON board of MA5801S-FL16-H2.
            "

        REVISION    "202210180001Z"
        DESCRIPTION "V13.23,
                     Add: fortyOptPort(595),              -- 40GE optical port.
                     "

        REVISION "202210170001Z" 
        DESCRIPTION "V13.22, 
            Add: bnameDP22PDC1K2A1(229013),    --V8R22C00 NetEngine-8000-M4 DP22PDC1K2A1
            Add: bnameANRD000FAN00(229015),    --V8R22C00 NetEngine-8000-M4 ANR1FAN01
            "

        REVISION "202210170000Z" 
        DESCRIPTION "V13.21,
            Add: fnameAirEngine9700D-S(692405),          -- WLAN R22C10 New AP
            Add: fnameAirEngine8761-X1(692406),          -- WLAN R22C10 New AP
            Add: fnameAirEngine5762-17W(692407),         -- WLAN R22C10 New AP
            Add: fnameAirEngine5762-10(692408),          -- WLAN R22C10 New AP
            Add: fnameAirEngine5762-10SW(692409),        -- WLAN R22C10 New AP
            Add: fnameAirEngine6761-23T(692410),         -- WLAN R22C10 New AP
            Add: bnameAirEngine9700D-S(692405),          -- WLAN R22C10 New AP
            Add: bnameAirEngine8761-X1(692406),          -- WLAN R22C10 New AP
            Add: bnameAirEngine5762-17W(692407),         -- WLAN R22C10 New AP
            Add: bnameAirEngine5762-10(692408),          -- WLAN R22C10 New AP
            Add: bnameAirEngine5762-10SW(692409),        -- WLAN R22C10 New AP
            Add: bnameAirEngine6761-23T(692410),         -- WLAN R22C10 New AP
            "

        REVISION    "202210140000Z"
        DESCRIPTION "V13.20,
            Add:bnameMIC-LTE4-CN-V2(668159),            --MIC-LTE4-CN-V2 Lpu Control Unit
            Add:bnameMIC-LTE4-EA-V2(668160),            --MIC-LTE4-EA-V2 Lpu Control Unit
            Add:bnameMIC-LTE4-AU-V2(668161),            --MIC-LTE4-AU-V2 Lpu Control Unit
            "

        REVISION    "202210080000Z"
        DESCRIPTION "V13.19,
            Add:vrientNECD00CXPL00(704576),           -- NE05E-S2
            "

        REVISION    "202209270001Z"
        DESCRIPTION "V13.18,
            Add:virent8090DEVCP8P15HALA02(525146),   -- V8R22C00 for CP8P15HALA02(SBOM) NetEngine A815 T, CP8P15HALA02, NetEngine A815 T AC System (4*GE(o)+4*GE/FE(e))
            Add:virent8090DEVCP8P25HALD02(525147),   -- V8R22C00 for CP8P25HALD02(SBOM) NetEngine A825 T, CP8P25HALD02, NetEngine A825 T DC System(16*10GE/GE/FE(o)+12*GE/FE(o)+4*GE/FE(e), Default 2*10GE+8*GE)
            Add:virent8090DEVCP8P25HALA02(525148),   -- V8R22C00 for CP8P25HALA02(SBOM) NetEngine A825 T, CP8P25HALA02, NetEngine A825 T AC System(16*10GE/GE/FE(o)+12*GE/FE(o)+4*GE/FE(e), Default 2*10GE+8*GE)
            Add:virent8090DEVCP8DCXP16001(525149),   -- V8R22C00 for CP8DCXP16001(SBOM) NetEngine A835 T, CP8DCXP16001, System Control,Cross-connect and Multi-protocol Process Unit (CXPA-160)
            Add:fnameNETENGINE-A815-T-AC(229680), -- V8R22C00 for NetEngine-A815-T-AC chassis
            Add:fnameNETENGINE-A825-T-DC(229681), -- V8R22C00 for NetEngine-A825-T-DC chassis
            Add:fnameNETENGINE-A825-T-AC(229682), -- V8R22C00 for NetEngine-A825-T-AC chassis
            Add:fnameNETENGINE-A835-T(229683), -- V8R22C00 for NetEngine-A835-T chassis
            "

        REVISION    "202209270000Z"
        DESCRIPTION "V13.17,
            Add:virent8090DEVCR8DSFUI4TDE(175386),   -- V8R22C10 for CR8DSFUI4TDE(SBOM) NetEngine 8000 X4 4Tbps Switch Fabric Unit(SFUI-4T-F)
            Add:virent8090DEVCR8DSFU14TD1(175387),   -- V8R22C10 for CR8DSFU14TD1(SBOM) NetEngine 8000 X4 14.4Tbps Switch Fabric Unit(SFUI-14T4-D)
            Add:virent8090DEVCR8DSFUI4TDF(175388),   -- V8R22C10 for CR8DSFUI4TDF(SBOM) NetEngine 8000 X8 4Tbps Switch Fabric Unit(SFUI-4T-G)
            Add:virent8090DEVCR8DSFU14TDE(175389),   -- V8R22C10 for CR8DSFU14TDE(SBOM) NetEngine 8000 X8 14.4Tbps Switch Fabric Unit(SFUI-14T4-E)
            Add:virent8090DEVCR8DSFUI4TD1(175390),   -- V8R22C10 for CR8DSFUI4TD1(SBOM) NetEngine 8000 X4 4Tbps Switch Fabric Unit(SFUIA-4T-F)
            Add:virent8090DEVCR8DSFU14TD2(175391),   -- V8R22C10 for CR8DSFU14TD2(SBOM) NetEngine 8000 X4 14.4Tbps Switch Fabric Unit(SFUIA-14T4-D)
            Add:virent8090DEVCR8DSFUI4TD2(175392),   -- V8R22C10 for CR8DSFUI4TD2(SBOM) NetEngine 8000 X8 4Tbps Switch Fabric Unit(SFUIA-4T-G)
            Add:virent8090DEVCR8DSFU14TD3(175393),   -- V8R22C10 for CR8DSFU14TD3(SBOM) NetEngine 8000 X8 14.4Tbps Switch Fabric Unit(SFUIA-14T4-E)
            Add:virent8090DEVCR8DSFUI2TDA(175394),   -- V8R22C10 for CR8DSFUI2TDA(SBOM) NetEngine 8000 X4 2Tbps Switch Fabric Unit(SFUI-2T-A)
            Add:virent8090DEVCR8DSFUI2TDB(175395),   -- V8R22C10 for CR8DSFUI2TDB(SBOM) NetEngine 8000 X8 2Tbps Switch Fabric Unit(SFUI-2T-B)
            Add:virent8090DEVCR8DSFUI2TD1(175396),   -- V8R22C10 for CR8DSFUI2TD1(SBOM) NetEngine 8000 X4 2Tbps Switch Fabric Unit(SFUIA-2T-A)
            Add:virent8090DEVCR8DSFUI2TD2(175397),   -- V8R22C10 for CR8DSFUI2TD2(SBOM) NetEngine 8000 X8 2Tbps Switch Fabric Unit(SFUIA-2T-B)
            Add:subbname8090DEVNetEngine-A815-T(115921),   --CARD NetEngine A815 T
            Add:subbname8090DEVNetEngine-A825-T(115922),   --CARD NetEngine A825 T
            "

       REVISION    "202209210000Z"
        DESCRIPTION "V13.16,
            Add:fnameAR8700-8(668047),        --AR8700-8 FRAME
            Add:bnameMPU-100(668156),         --MPU-100 Main Control Unit
            Add:bnameMPU-100-T(668157),       --MPU-100-T Main Control Unit
            Add:bnameSPU-700H(668158),        --SPU-700H SPU Control Unit
            "

		REVISION    "202209200000Z"
        DESCRIPTION "V13.15,
            Add: virent8090DEVCR8PM1ABAS0(689484),    -- V8R22C00 for CR8PM1ABAS0(SBOM) NetEngine 8000,CR8PM1ABAS0,NetEngine 8000 M1A, AC Power,Port Capacity 16*10GE+12*GE(o)+4*GE(e)
            Add: virent8090DEVCR8PM1ABAS1(689485),    -- V8R22C00 for CR8PM1ABAS1(SBOM) NetEngine 8000,CR8PM1ABAS1,NetEngine 8000 M1A, AC Power,Port Capacity 16*10GE+12*GE(o)+4*GE(e)
            Add: virent8090DEVCR8PM1ABAS2(689486),    -- V8R22C00 for CR8PM1ABAS2(SBOM) NetEngine 8000,CR8PM1ABAS2,NetEngine 8000 M1A, DC Power,Port Capacity 16*10GE+12*GE(o)+4*GE(e)
            "

        REVISION    "202209200000Z"
        DESCRIPTION "V13.14,
            Add: bnameDX511(688493),     -- DX511
            Add: bnameDX112(688494),     -- DX112
            Add: fnameDX511(688249),     -- DX511
            Add: fnameDX112(688250),     -- DX112
            "

        REVISION    "202209190000Z"
        DESCRIPTION "V13.13,
            Add: virent8090DEVME0DMSUFT07E(482952),   -- V8R22C10 for ME0DMSUFT07E(SBOM) Flexible Card Broadband Service Unit(BSUF-1T2-E,2 sub-slots)
            Add: virent8090DEVME0DMSUFT07B(482953),   -- V8R22C10 for ME0DMSUFT07B(SBOM) Flexible Card Multi Service Unit(MSUF-1T2-E,2 sub-slots)
            Add: virent8090DEVME0DMSUFT07C(482954),   -- V8R22C10 for ME0DMSUFT07C(SBOM) Flexible Card Broadband Service Unit(BSUF-1T2A-E,2 sub-slots)
            Add: virent8090DEVME0DMSUFT07D(482955),   -- V8R22C10 for ME0DMSUFT07D(SBOM) Flexible Card Multi Service Unit(MSUF-1T2A-E,2 sub-slots)
            "
		REVISION    "202209160000Z"
        DESCRIPTION "V13.13,
            Add: virent8090DEVCX6D0SRUAH13(773066),   -- for CX6D0SRUAH13(SBOM) Switch and Route Processing Unit A20(SRUA-480-I, 32G Memory)
			Add: virent8090DEVCX6D0SRUAI13(394381),   -- for CX6D0SRUAI13(SBOM) Switch and Route Processing Unit A21(SRUA-1T-H, 32G Memory)
            "

        REVISION    "202209130000Z"
        DESCRIPTION "V13.12,
            Add: virent8090DEVANGMHSTH0101(226375),  -- V8R22C00 for ANGMHSTH0101(SBOM) ATN 910C,ANG1CXPQ,ATN 910C-H DC Basic Configuration(Includes Fixed Enable Interface (4*10GE/GE/FE(o)+4*GE/FE(o)+4*GE/FE(e))/Dual Power/FAN/Chassis)
            Add: virent8090DEVANGMHSTS0101(226376),  -- V8R22C00 for ANGMHSTS0101(SBOM) ATN 910C,ANG1CXPQ,ATN 910C-S DC Basic Configuration(Includes Fixed Enable Interface (5*10GE/GE/FE(o)+3*GE/FE(o)+4*GE/FE(e))/Dual Power/FAN/Chassis)
            Add: virent8090DEVANGMHSTH0201(226377),  -- V8R22C00 for ANGMHSTH0201(SBOM) ATN 910C,ANG1CXPQ,ATN 910C-H AC Basic Configuration(Includes Fixed Enable Interface (4*10GE/GE/FE(o)+4*GE/FE(o)+4*GE/FE(e))/Power/FAN/Chassis)
            Add: virent8090DEVANGMHSTS0201(226378),  -- V8R22C00 for ANGMHSTS0201(SBOM) ATN 910C,ANG1CXPQ,ATN 910C-S AC Basic Configuration(Includes Fixed Enable Interface (5*10GE/GE/FE(o)+3*GE/FE(o)+4*GE/FE(e))/Power/FAN/Chassis)
            Add: virent8090DEVCR8DEANEJXDM(634588),   -- V8R22C10 for CR8DEANEJXDM(SBOM) 10-Port 100GBase-QSFP28 MACsec + 36-Port 10GE(SFP+)/GE(SFP) MACsec Integrated Line Processing Unit CM(LPUI-1T-CM)
            Add: virent8090DEVCR8DEANEJXD1(979962),   -- V8R22C10 for CR8DEANEJXD1(SBOM) 10-Port 100GBase-QSFP28 + 36-Port 10GE(SFP+)/GE(SFP) Integrated Line Processing Unit CM(LPUI-1T-CM)
            Add: virent8090DEVCR8DEANEJXD2(709131),   -- V8R22C10 for CR8DEANEJXD2(SBOM) 10-Port 100GBase-QSFP28 + 36-Port 10GE(SFP+)/GE(SFP) Integrated Line Processing Unit CM(LPUI-1TA-CM)
            Add: virent8090DEVCR8DEANEJXDN(315861),   -- V8R22C10 for CR8DEANEJXDN(SBOM) 10-Port 100GBase-QSFP28 MACsec + 36-Port 10GE(SFP+)/GE(SFP) MACsec Integrated Line Processing Unit CM(LPUI-1TA-CM)
            "

        REVISION    "202209080000Z"
        DESCRIPTION "V13.09,
            Add: virent8090DEVANND00CXPA02(227999),  -- V8R22C10 ATN 980C,ANN1CXPA29,System Control,Cross-connect and Multi-protocol Process Unit with 360G
            Add: virent8090DEVANND02CXPAU4(228000),  -- V8R22C10 ATN 980C,ANN3CXPA00,System Control,Cross-connect and Multi-protocol Process Unit with 400G
            Add: virent8090DEVCR5DVSUIK07E(954290),   -- V8R22C00 for CR5DVSUIK07E(SBOM) Enhanced Data Redundancy Elimination Integrated Service Unit 400(VSUI-400-E)
            Add: virent8090DEVCR5DVSUIK07F(158967),   -- V8R22C00 for CR5DVSUIK07F(SBOM) Enhanced Data Redundancy Elimination Integrated Service Unit 400(VSUI-400A-E)
            Add: virent8090DEVCR5DVSUIK07G(185740),   -- V8R22C00 for CR5DVSUIK07G(SBOM) Data Redundancy Elimination Integrated Service Unit 400(VSUI-400-S)
            Add: virent8090DEVCR5DVSUIK07H(544950),   -- V8R22C00 for CR5DVSUIK07H(SBOM) Data Redundancy Elimination Integrated Service Unit 400(VSUI-400A-S)
            "

        REVISION    "202209060000Z"
        DESCRIPTION "V13.09,
            Add: subbname8090DEVCR5D0L6XFA71(591763),   -- 6-Port 10GBase LAN/WAN-SFP+ Flexible Card A(P120-A)
            Add: subbname8090DEVCR5DE4NE8V73(513209),   -- 4-Port 100GBase-QSFP28 FlexE Flexible Card(P1T)
            Add: subbname8090DEVCR5DE2NBFM72(973460),   -- 2-Port 100GBase-QSFP28 Flexible Card(P483)
            "

        REVISION    "202209050000Z"
        DESCRIPTION "V13.08,
            Add: virent8090DEVCR8DIPU1T2M1(468779),   -- V8R22C00 for CR8DIPU1T2M1(SBOM) Integrated Network Processing Unit (IPUA-1T2-D)
            Add: virent8090DEVCR8DIPU480M0(468780),   -- V8R22C00 for CR8DIPU480M0(SBOM) Integrated Network Processing Unit (IPUA-480-D)
            Add: virent8090DEVCR8DIPU1T2CL(468781),   -- V8R22C00 for CR8DIPU1T2CL(SBOM) Integrated Network Processing Unit (IPU-1T2-D)
            Add: virent8090DEVCR8DIPU480CA(468782),   -- V8R22C00 for CR8DIPU480CA(SBOM) Integrated Network Processing Unit (IPU-480-D)
            Add: virent8090DEVCR8DIPU1T2M0(468783),   -- V8R22C00 for CR8DIPU1T2M0(SBOM) Integrated Network Processing Unit (IPUA-1T2-D)
            Add: virent8090DEVCR8DIPU1T2CN(468784),   -- V8R22C00 for CR8DIPU1T2CN(SBOM) Integrated Network Processing Unit (IPU-1T2-D)
            Add: virent8090DEVCR8DIPU1T2CU(468785),   -- V8R22C00 for CR8DIPU1T2CU(SBOM) Integrated Network Processing Unit (IPU-1T2-D)
            Add: virent8090DEVCR8DE4KFBNC1(468775),   -- V8R22C00 for CR8DE4KFBNC1(SBOM) Integrated Line Processing Unit CM (LPUI-4TA-L-CM)
            Add: virent8090DEVCR8DEKNBFED1(520102),   -- V8R22C10 for CR8DEKNBFED1(SBOM) 40-Port 100GBase-QSFP28 Integrated Line Processing Unit CM(LPUI-4T-E-CM)
            Add: virent8090DEVCR8DE4KEFND1(350519),   -- V8R22C10 for CR8DE4KEFND1(SBOM) 4-Port 400GBase-QSFP-DD + 24-Port 100GBase-QSFP28 Integrated Line Processing Unit CM (LPUI-4T-E-CM)
            Add: virent8090DEVCR8DEKNBFED2(472559),   -- V8R22C10 for CR8DEKNBFED2(SBOM) 40-Port 100GBase-QSFP28 Integrated Line Processing Unit CM(LPUI-4TA-E-CM)
            Add: virent8090DEVCR8DE4KEFND2(468790),   -- V8R22C10 for CR8DE4KEFND2(SBOM) 4-Port 400GBase-QSFP-DD + 24-Port 100GBase-QSFP28 Integrated Line Processing Unit CM (LPUI-4TA-E-CM)
            Add: virent8090DEVCR8DERYBFED1(796564),   -- V8R22C10 for CR8DERYBFED1(SBOM) 72-Port 25GE(SFP28)/10GE(SFP+)/GE(SFP) Integrated Line Processing Unit CM(LPUI-2T-E-CM)
            Add: virent8090DEVCR8DEENBFED1(229061),   -- V8R22C10 for CR8DEENBFED1(SBOM) 20-Port 100GBase-QSFP28 Integrated Line Processing Unit CM(LPUI-2T-E-CM)
            Add: virent8090DEVCR8DEANEJYD1(855770),   -- V8R22C10 for CR8DEANEJYD1(SBOM) 10-Port 100GBase-QSFP28 + 36-Port 25GE(SFP28)/10GE(SFP+)/GE(SFP) Integrated Line Processing Unit CM(LPUI-2T-E-CM)
            Add: virent8090DEVCR8DERYBFED2(175385),   -- V8R22C10 for CR8DERYBFED2(SBOM) 72-Port 25GE(SFP28)/10GE(SFP+)/GE(SFP) Integrated Line Processing Unit CM(LPUI-2TA-E-CM)
            Add: virent8090DEVCR8DEENBFED2(548567),   -- V8R22C10 for CR8DEENBFED2(SBOM) 20-Port 100GBase-QSFP28 Integrated Line Processing Unit CM(LPUI-2TA-E-CM)
            Add: virent8090DEVCR8DEANEJYD2(468791),   -- V8R22C10 for CR8DEANEJYD2(SBOM) 10-Port 100GBase-QSFP28 + 36-Port 25GE(SFP28)/10GE(SFP+)/GE(SFP) Integrated Line Processing Unit CM(LPUI-2TA-E-CM)
            Add: virent8090DEVCR8DE8KE8ND1(463229),   -- V8R22C10 for CR8DE8KE8ND1(SBOM) 8-Port 400GBase-QSFP-DD + 8-Port 100GBase-QSFP28 Integrated Line Processing Unit CM(LPUI-4T-E-CM,Enable 16*100GE by default)
            Add: virent8090DEVCR8DE8KE8ND2(588800),   -- V8R22C10 for CR8DE8KE8ND2(SBOM) 8-Port 400GBase-QSFP-DD + 8-Port 100GBase-QSFP28 Integrated Line Processing Unit CM(LPUI-4TA-E-CM,Enable 16*100GE by default)
            Add: virent8090DEVCR5DLPUFT07F(130553),   -- V8R22C10 for CR5DLPUFT07F(SBOM) Flexible Card Line Processing Unit(LPUF-1T2A-E)
            Add: virent8090DEVCR5DLPUFT07E(830576),   -- V8R22C10 for CR5DLPUFT07E(SBOM) Flexible Card Line Processing Unit(LPUF-1T2-E)
            Add: virent8090DEVCR5D00EENB7E(843286),   -- V8R22C10 for CR5D00EENB7E(SBOM) 20-Port 100GBase-QSFP28 Integrated Line Processing Unit (LPUI-2TA-E)
            Add: virent8090DEVCR5D00EENB7S(608128),   -- V8R22C10 for CR5D00EENB7S(SBOM) 20-Port 100GBase-QSFP28 FlexE/MACsec Integrated Line Processing Unit CM(LPUI-2T-E-CM)
            Add: virent8090DEVME0DBSUFT07A(493005),   -- V8R22C10 for ME0DBSUFT07A(SBOM) Integrated Broadband Service Unit(BSUI-2T-CM)
            Add: virent8090DEVME0DMSUFT07A(482951),   -- V8R22C10 for ME0DMSUFT07A(SBOM) Integrated Multi Service Unit(MSUI-2T-CM)
            Add: fnameATNDEV980C-PL-DC(229801),         --ATN980C-PL-DC chassis
            Add: fnameATNDEV980C-PL-AC(229802),         --ATN980C-PL-AC chassis
            "

        REVISION    "202209010000Z"
        DESCRIPTION "V13.07,
            Add: bnameH908CGHF(148790),              -- 16*XG/G combo board of MA5800.
            Add: bnameH902DQHF(148791),              -- DQ ODN OAI board of MA5800 and EA5800.
            Add: bnameH905CGUD(148792),              -- 8*XG/G combo board of MA5800.
            Add: bnameH905XEHF(148796),              -- 16*10G EPON board of MA5800.
            Delete: fnameMA5800H901BPLG(148530),     -- Backplane of MA5800-X17E/EA5800-X17E.
            Delete: fnameMA5800H901BPIG(148531),     -- Backplane of MA5800-X15E/EA5800-X15E.
            Delete: fnameMA5800H901BPMG(148532),     -- Backplane of MA5800-X7E/EA5800-X7E.
            "

        REVISION "202208291100Z" 
            DESCRIPTION "V13.06,
               Add:virent8090DEVCR5D5KBASN61(562124),    -- V8R22C00 for CR5D5KBASN61(SBOM) NetEngine5000E 8-Port 400GBase QSFP-DD Integrated Line Process Unit(NE5000E LPUI-3T2)
               Add:virent8090DEVCR5D5KBASN62(562125),    -- V8R22C00 for CR5D5KBASN62(SBOM) NetEngine5000E 32-Port 100GBase QSFP28 Integrated Line Process Unit(NE5000E LPUI-3T2)
               Add:virent8090DEVCR5D5KHALN63(562126),    -- V8R22C00 for CR5D5KHALN63(SBOM) NetEngine5000E 8-Port 400GBase QSFP-DD Integrated Line Process Unit CM(NE5000E LPUI-3T2-CM) (Including 2*400GE Setup Port)
               Add:virent8090DEVCR5D5KHALN64(562127),    -- V8R22C00 for CR5D5KHALN64(SBOM) NetEngine5000E 32-Port 100GBase QSFP28 Integrated Line Process Unit CM(NE5000E LPUI-3T2-CM) (Including 8*100GE Setup Port)
               "

        REVISION "202208290000Z" 
            DESCRIPTION "V13.05,
               Change the fname and bname of the 5750 and 5350."


		REVISION "202208240000Z"
        DESCRIPTION "V13.04,
            Add:subbname8090DEVCR59E4KBB(165000),         -- 4-Port 400GBase QSFP-DD
            Add:subbname8090DEVCR59EDNBC(709793),         -- 16-Port 100GBase QSFP28
            Add:virent8090DEVCR8PM4BASDC2(468761),   -- V8R21C10 for CR8PM4BASDC2(SBOM) NetEngine 8000 M4 Integrated DC Chassis Components(Including DC Power,Fan Box)
            Add:virent8090DEVCR8PM4BASDC3(468762),   -- V8R21C10 for CR8PM4BASDC3(SBOM) NetEngine 8000 M4 Integrated AC Chassis Components(Including AC Power,Fan Box)
            Add:virent8090DEVCR8PM4BASAC2(468764),   -- V8R21C10 for CR8PM4BASAC2(SBOM) NetEngine 8000 M4 Integrated DC Chassis Components(Including DC Power,Fan Box)
            Add:virent8090DEVCR8PM4BASAC3(468765),   -- V8R21C10 for CR8PM4BASAC3(SBOM) NetEngine 8000 M4 Integrated AC Chassis Components(Including AC Power,Fan Box)
            Add:fnameNETENGINE-8000-M4(688896),        -- NETENGINE-8000-M4 (fnameNETENGINE-8000-M4)
			Add:fnameNETENGINE-8000-M4-AC(688897),     -- NETENGINE-8000-M4-AC (fnameNETENGINE-8000-M4-AC)
            Add:fnameNETENGINE-8000-M4-DC(688898),     -- NETENGINE-8000-M4-DC (fnameNETENGINE-8000-M4-DC)
            Add:virent8090DEVCR8DIPU1T2CJ(285693),   -- V8R21C10 for CR8DIPU1T2CJ(SBOM) Integrated Network Processing Unit (IPU-1T2-C)
            Add:virent8090DEVCR8DIPU1T2CK(867258),   -- V8R21C10 for CR8DIPU1T2CK(SBOM) Integrated Network Processing Unit (IPUA-1T2-C)
            Add:virent8090DEVCR5DIPU1T2C5(983151),   -- V8R21C10 for CR5DIPU1T2C5(SBOM) Integrated Network Processing Unit (IPU-1T2-C)
            "
        REVISION "202208220000Z"
        DESCRIPTION "V13.03,
            Add:fnameAR611W-LTE6EA(668044),  -- AR611W-LTE6EA FRAME
            Add:fnameAR631I-LTE4CN(668045),  -- AR631I-LTE4CN FRAME
            Add:fnameAR631I-LTE4EA(668046),  -- AR631I-LTE4EA FRAME
            Add:bnameAR611W-LTE6EA(668153),  -- AR611W-LTE6EA Main Control Unit
            Add:bnameAR631I-LTE4CN(668154),  --AR631I-LTE4CN Main Control Unit
            Add:bnameAR631I-LTE4EA(668155),  --AR631I-LTE4EA Main Control Unit
            "

        REVISION    "202208190000Z"	
        DESCRIPTION "V13.02,
				Modify: virent8090DEVIG2D0SRUAI72(385921),   --  for IG2D0SRUAI72(SBOM) Switch and Route Processing Unit A18A(SRUA-1TA-H, 32G Memory)
                "



        REVISION    "202208130000Z"	
        DESCRIPTION "V13.01,
				Add: virent8090DEVCX6DMPUB1215(429159),   -- V8R22C00 for CX6DMPUB1215(SBOM) Main Processing Unit B112(32G Memory)
                "
		
		REVISION "202208120000Z" 
            DESCRIPTION "V13.00,
               Change the fname and bname of the 5750 and 5350 series to 5735 and 5335."

                REVISION    "202208100000Z"
		DESCRIPTION "V12.99,
				Add: virent8090DEVTPXM0HOSTA01(229543),           -- V8R22C00 for TPXM0HOSTA01(SBOM) PTN 91A-F,3*10G/GE/FE(o)+7*GE/FE(o)+4*GE/FE(e)
                "

        REVISION    "202207250000Z"	
        DESCRIPTION "V12.98,
				Add: bnamePTN7900TPA2CH1G(229678),    --TPA2CH1G, 16 channelized STM-1 processing board
				Add: bnamePTN7900TPA2MQ1G(229679),    --TPA2MQ1G, 63 Channels E1 Interface Processing Board
                "

        REVISION    "202207250000Z" 	 
        DESCRIPTION "V12.97,
                Add: subbname8090DEVCR8D00E4XFD0(998318), -- 4-Port 10GE-SFP+ FlexE MACsec Physical Interface Card(PIC)
                Add: subbname8090DEVCR8D00E4XFC4(694693), -- 4-Port 10GE-SFP+ FlexE MACsec Physical Interface Card(PIC)
                Add: subbname8090DEVCR8D00E4XFC5(582390), -- 4-Port 10GE-SFP+ FlexE MACsec Physical Interface Card(PIC)
                Add: subbname8090DEVNetEngine-8000-M1D-B(115915), -- CARD NetEngine 8000 M1D-B
                Add: subbname8090DEVNetEngine-A813(115916),       -- CARD NetEngine A813
                Add: subbname8090DEVATN-905-S(115918),            -- CARD ATN 905-S
                Add: subbname8090DEVNetEngine-A831-E(115919),     -- CARD NetEngine A831 E
                Add: subbname8090DEVNetEngine-A822-E(115920),     -- CARD NetEngine A822 E
                Add: subbname8090DEVGPLI36YS10CQES1(582391),   -- 36-Port 25GE(SFP28)/10GE(SFP+)/GE(SFP) 10-Port 100GBase QSFP28 Integrated Line Process Unit
                Add: subbname8090DEVGPLI72YSE8(778133),   -- 72-Port 25GE(SFP28)/10GE(SFP+)/GE(SFP) Integrated Line Processing Unit
                Add: subbname8090DEVGPLI72YSES7(464797),   -- 72-Port 25GE(SFP28)/10GE(SFP+)/GE(SFP) Integrated Line Processing Unit
                Add: subbname8090DEV910D-B(115914),            --CARD ATN 910D-B
                "
                
                REVISION    "202207221400Z" 	 
        DESCRIPTION "V12.96,
                Add: bnameDP52PDC2K4A1(564504),    --V8R13C00 NetEngine-8000-M14 DP52PDC2K4A1, M14
                Add: bnameDP32PDC1K6A1(564506),    --V8R13C00 NetEngine-8000-M14 DP32PDC1K6A1, M14
                Add: bnamePAC1K5S53-AL(564508),    --V8R13C00 NetEngine-8000-M14 PAC1K5S53-AL, M14
                Add: bnameCR8M002FBXC1(564505),    --V8R13C00 NetEngine-8000-M14 CR8M002FBXC1, M14
                Add: bnameCR8MM82FBXC1(564507),    --V8R13C00 NetEngine-8000-M14 CR8MM82FBXC1, M14
                Add: bnameCR8M002FBXZ1(564509),    --V8R13C00 NetEngine-8000-M14 CR8M002FBXZ1, M14
                Add: bnameCR8MME2FBXK1(564510),    --V8R13C00 NetEngine-8000-M14 CR8MME2FBXK1, M14
                Add: bnameCR8M002FBXC2(564511),    --V8R13C00 NetEngine-8000-M14 CR8M002FBXC2, M14
                Add: bnameCR8MM82FBXK1(564512),    --V8R13C00 NetEngine-8000-M14 CR8MM82FBXK1, M14
                Add: bnameCR8MM82FBXC2(564513),    --V8R13C00 NetEngine-8000-M14 CR8MM82FBXC2, M14
                Add: bnameCR8MM62FBXK1(564528),    --V8R13C00 NetEngine-8000-M6K CR8MM62FBXK1, M6K
                Add: bnameCR8M002FBX11(564533),    --V8R21C10 NetEngine-8000E-M14 CR8M002FBX11, M14
                Add: bnameCR8MM82FBX11(564534),    --V8R21C10 NetEngine-8000E-M8 CR8MM82FBX11, M8
                Modify: bnameNE8KF8FAN(564535),       --V8R22C00 NetEngine-8000E-F8 NE8KF8FAN
                Modify: bnameNE8KF8PIU(564536),       --V8R22C00 NetEngine-8000E-F8 NE8KF8PIU
                Modify: bnameNE8KF8APIU(564537),       --V8R22C00 NetEngine-8000E-F8 NE8KF8APIU
                " 
        REVISION "202207220000Z" 
            DESCRIPTION "V12.95,                
                add: bnamePAC600S56-EB(713499),  --PAC600S56-EB  for V6R22C00
                add: bnamePAC1000S56-EB(713500),   --PAC1000S56-EB   for V6R22C00
                add: bnamePDC1000S56-EB(713501),  --PDC1000S56-EB  for V6R22C00" 
                
                REVISION    "202207210000Z" 	 
        DESCRIPTION "V12.94,
				Add: bnamePTN7900TPA2MQ1(229649),    --TPA2MQ1, 63 Channels E1 Interface Processing Board
				Add: bnamePTN7900TPA2MQ1A(229658),    --TPA2MQ1A, 63 Channels E1 Interface Processing Board
				Add: bnamePTN7900TPA2MQ1B(229659),    --TPA2MQ1B, 63 Channels E1 Interface Processing Board
				Add: bnamePTN7900TPA2CH1(229660),    --TPA2CH1, 16 channelized STM-1 processing board
				Add: bnamePTN7900TPA7EX8S(229676),   --TPA7EX8S, 8-Port GE/GE adaptive ethernet processing board
				Add: bnamePTN7900TPA7EG24(229677),   --TPA7EG24, 24-Port GE/FE adaptive ethernet service processing board
                "
                REVISION    "202207200000Z" 	 
        DESCRIPTION "V12.93,
				fnameCE98604CEIA(688248),  -- CE V2R22C10
				bnameCE98604CEIA(688485),  -- CE V2R22C10
				bnameCEMPUDFULL2C(688486),  -- CE V2R22C00
				bnameCEMPUDHALF2C(688487), -- CE V2R22C00
				bnameCESFU08FH1E(688488),  -- CE V3R22C10
				bnameCEL36DQHGX(688489),  -- CE V3R22C10
				bnameCEMPUDH3ET(688491),  -- CE V3R22C10
				bnameCEMPUDF3ET(688492),  -- CE V3R22C10
                " 
		REVISION    "202207150000Z" 	 
        DESCRIPTION "V12.92,
                Add:bnameH83GSDPD(156102),                  -- 64-channel super vectoring vdsl2+ service board
                Add:bnameH833CCMS(156103),                  --Master board of MA5818 deviceProcess Unit
				Add:bnameH83GCSPE(156105),                  -- 64-channel Vectoring VDSL2 + POTS COMBO service board, supports super vectoring feature.
                "
		REVISION    "202207140000Z" 	 
        DESCRIPTION "V12.91,
                Add: subbname8090DEVGPLI40CQE8(172720),    -- 40-Port 100GBase QSFP28 Integrated Line Process Unit
                Add: subbname8090DEVGPLI4KQ24CQE2(733887),    -- 4-Port 400GBase QSFPDD 24-Port 100GBase QSFP28 Integrated Line Process Unit
                "
		
		REVISION    "202207110000Z" 	 
        DESCRIPTION "V12.90,
                Add: subbname8090DEVCR5D0LFXFM20(482067),   -- 20-Port 10GBase LAN/WAN-SFP+ Flexible Card(P483)
                Add:subbname8090DEVME0M0LEXFB76(108199),   -- 20-Port 10GBase LAN/WAN-SFP+ Flexible Card(P483)
                "
		
                REVISION    "202207050000Z" 	 
        DESCRIPTION "V12.89,
                Add: subbname8090DEVCR8D00L8YFC1(723821),       --8-Port 25GE(SFP28)/10GE(SFP+) MACsec Physical Interface Card (PIC)
                Modify: subbname8090DEVCR8D00E1NCC1(295791),      --1-Port 100GBase-CFP2 Physical Interface Card(PIC)
                Add:subbname8090DEVCR8D00E8GED2(567354),      --8-Port 100/1000Base-RJ45 Physical Interface Card(PIC)
                Add:subbname8090DEVCR8D25E2XFC1(141601),       --2-port 25G (SFP28)/2 Channels 10G (SFP+) Physical Interface Card(PIC)
                Add:subbname8090DEVCR8D00L4XFC5(115913),      --4-Port 10GE(SFP+)/GE(SFP) MACsec Physical Interface Card(PIC)
                Add:subbname8090DEVCR8D00E2XFC1(115912),       --2-port 10GE(SFP+)/GE(SFP) Physical Interface Card(PIC)
                Add:subbname8090DEVCR8D00EEGFC1(723820),       --20-Port 100/1000Base-X-CSFP/10-Port 100/1000Base-X-SFP Physical Interface Card(PIC)
                Add:subbname8090DEVCR8D00EAGFC5(355930),       --10-port 100/1000Base-X-SFP MACsec Physical Interface Card(PIC)
                "

		REVISION    "202207020000Z" 	 
        DESCRIPTION "V12.88,
                Add: virent8090DEVCR8DE4KFBNC2(629167),   --  for CR8DE4KFBNC2(SBOM) 4-Port 400GBase-QSFP-DD + 24-Port 100GBase-QSFP28 Integrated Line Processing Unit CM (LPUI-4T-L-CM)
				Add: virent8090DEVCR5DLPUFM392(688683),   -- V8R22C00 for CR5DLPUFM392(SBOM) Flexible Card Line Processing Unit(LPUF-483A, Supportting DIP)
                Add: virent8090DEVCR5DLPUFM393(688684),   -- V8R22C00 for CR5DLPUFM393(SBOM) Flexible Card Line Processing Unit(LPUF-483A, Supportting DIP)
                "

        REVISION    "202206300000Z" 	 
        DESCRIPTION "V12.87,
                Add: virent600DEVNE8KF8FAN(564535),       --V8R22C00 NetEngine-8000E-F8 NE8KF8FAN
                Add: virent600DEVNE8KF8PIU(564536),       --V8R22C00 NetEngine-8000E-F8 NE8KF8PIU
                Add: virent600DEVNE8KF8APIU(564537),       --V8R22C00 NetEngine-8000E-F8 NE8KF8APIU
                "

        REVISION    "202206280000Z" 	 
        DESCRIPTION "V12.86,
		Add: fnameEudemon1000E-C1(16716029),   -- Assembling Components,fnameEudemon1000E-C1
		Add: fnameEudemon1000E-S1(16716030),   -- Assembling Components,fnameEudemon1000E-S1
		Add: fnameEudemon1000E-S5(16716031),   -- Assembling Components,fnameEudemon1000E-S5
		Add: fnameEudemon1000E-S8(16716032),   -- Assembling Components,fnameEudemon1000E-S8
		Add: fnameEudemon1000E-M1(16716033),   -- Assembling Components,fnameEudemon1000E-M1
		Add: fnameEudemon1000E-M2(16716034),   -- Assembling Components,fnameEudemon1000E-M2
		Add: fnameEudemon1000E-M3(16716035),   -- Assembling Components,fnameEudemon1000E-M3
		Add: fnameEudemon1000E-M5(16716036),   -- Assembling Components,fnameEudemon1000E-M5
		Add: fnameAntiDDoS1905-N(16716037),   -- Assembling Components,fnameAntiDDoS1905-N
		Add: fnameASG5303(16716038),   -- Assembling Components,fnameASG5303
		Add: fnameASG5305(16716039),   -- Assembling Components,fnameASG5305
		Add: fnameASG5308(16716040),   -- Assembling Components,fnameASG5308
		Add: fnameASG5310(16716041),   -- Assembling Components,fnameASG5310
		Add: fnameASG5315(16716042),   -- Assembling Components,fnameASG5315
		Add: fnameASG5320(16716043),   -- Assembling Components,fnameASG5320
		Add: fnameASG5505(16716044),   -- Assembling Components,fnameASG5505
		Add: fnameASG5510(16716045),   -- Assembling Components,fnameASG5510
		Add: fnameASG5520(16716046),   -- Assembling Components,fnameASG5520
		Add: fnameASG5530(16716047),   -- Assembling Components,fnameASG5530
		Add: fnameASG5550(16716048),   -- Assembling Components,fnameASG5550
		Add: fnameASG5610(16716049),   -- Assembling Components,fnameASG5610
		Add: fnameASG5000-S1050(16716050),   -- Assembling Components,fnameASG5000-S1050
		Add: fnameASG5000-S1055(16716051),   -- Assembling Components,fnameASG5000-S1055
		Add: fnameASG5000-D1060(16716052),   -- Assembling Components,fnameASG5000-D1060
		Add: fnameASG5000-S1100(16716053),   -- Assembling Components,fnameASG5000-S1100
		Add: fnameASG5000-E1108(16716054),   -- Assembling Components,fnameASG5000-E1108
		Add: fnameASG5000-D1120(16716055),   -- Assembling Components,fnameASG5000-D1120
		Add: fnameASG5000-S1220(16716056),   -- Assembling Components,fnameASG5000-S1220
		Add: fnameASG5000-D1300(16716057),   -- Assembling Components,fnameASG5000-D1300
		Add: fnameASG5000-E1400(16716058),   -- Assembling Components,fnameASG5000-E1400
		Add: fnameASG5000-S1460(16716059),   -- Assembling Components,fnameASG5000-S1460
		Add: fnameASG5000-D1500(16716060),   -- Assembling Components,fnameASG5000-D1500
		Add: fnameASG5000-E2100(16716061),   -- Assembling Components,fnameASG5000-E2100
		Add: fnameASG5000-D2100(16716062),   -- Assembling Components,fnameASG5000-D2100
		Add: fnameASG5000-D2250(16716063),   -- Assembling Components,fnameASG5000-D2250
		Add: fnameASG5000-D2500(16716064),   -- Assembling Components,fnameASG5000-D2500
		Add: fnameASG5000-D3100(16716065),   -- Assembling Components,fnameASG5000-D3100
		Add: bnameEudemon1000E-C1(16716017),    --FW bnameEudemon1000E-C1
		Add: bnameEudemon1000E-S1(16716018),    --FW bnameEudemon1000E-S1
		Add: bnameEudemon1000E-S5(16716019),    --FW bnameEudemon1000E-S5
		Add: bnameEudemon1000E-S8(16716020),    --FW bnameEudemon1000E-S8
		Add: bnameEudemon1000E-M1(16716021),    --FW bnameEudemon1000E-M1
		Add: bnameEudemon1000E-M2(16716022),    --FW bnameEudemon1000E-M2
		Add: bnameEudemon1000E-M3(16716023),    --FW bnameEudemon1000E-M3
		Add: bnameEudemon1000E-M5(16716024),    --FW bnameEudemon1000E-M5
		Add: bnameMPUD-USG-X4X8(16716026),    --FW bnameMPUD-USG-X4X8
		Add: bnameMPUD-U-X4X8-T(16716027),    --FW bnameMPUD-U-X4X8-T
		Add: bnameMPUD-E9KE-X4X8(16716028),    --FW bnameMPUD-E9KE-X4X8
		Add: bnameMPUD-E-X4X8-T(16716029),    --FW bnameMPUD-E-X4X8-T
		Add: bnameMPUD-ADS-X4X8(16716030),    --FW bnameMPUD-ADS-X4X8
		Add: bnameMPUD-A-X4X8-T(16716031),    --FW bnameMPUD-A-X4X8-T
		Add: bnameMPUD-IPS-X4X8(16716032),    --FW bnameMPUD-IPS-X4X8
		Add: bnameASG5303(16716033),    --FW bnameASG5303
		Add: bnameASG5305(16716034),    --FW bnameASG5305
		Add: bnameASG5308(16716035),    --FW bnameASG5308
		Add: bnameASG5310(16716036),    --FW bnameASG5310
		Add: bnameASG5315(16716037),    --FW bnameASG5315
		Add: bnameASG5320(16716038),    --FW bnameASG5320
		Add: bnameASG5505(16716039),    --FW bnameASG5505
		Add: bnameASG5510(16716040),    --FW bnameASG5510
		Add: bnameASG5520(16716041),    --FW bnameASG5520
		Add: bnameASG5530(16716042),    --FW bnameASG5530
		Add: bnameASG5550(16716043),    --FW bnameASG5550
		Add: bnameASG5610(16716044),    --FW bnameASG5610
		Add: bnameASG5000-S1050(16716045),    --FW bnameASG5000-S1050
		Add: bnameASG5000-S1055(16716046),    --FW bnameASG5000-S1055
		Add: bnameASG5000-D1060(16716047),    --FW bnameASG5000-D1060
		Add: bnameASG5000-S1100(16716048),    --FW bnameASG5000-S1100
		Add: bnameASG5000-E1108(16716049),    --FW bnameASG5000-E1108
		Add: bnameASG5000-D1120(16716050),    --FW bnameASG5000-D1120
		Add: bnameASG5000-S1220(16716051),    --FW bnameASG5000-S1220
		Add: bnameASG5000-D1300(16716052),    --FW bnameASG5000-D1300
		Add: bnameASG5000-E1400(16716053),    --FW bnameASG5000-E1400
		Add: bnameASG5000-S1460(16716054),    --FW bnameASG5000-S1460
		Add: bnameASG5000-D1500(16716055),    --FW bnameASG5000-D1500
		Add: bnameASG5000-E2100(16716056),    --FW bnameASG5000-E2100
		Add: bnameASG5000-D2100(16716057),    --FW bnameASG5000-D2100
		Add: bnameASG5000-D2250(16716058),    --FW bnameASG5000-D2250
		Add: bnameASG5000-D2500(16716059),    --FW bnameASG5000-D2500
		Add: bnameASG5000-D3100(16716060),    --FW bnameASG5000-D3100
		Add: bnamePAC180S12-CN(16716061),    --FW bnamePAC180S12-CN
		Add: bnamePAC350S12-CR(16716062),    --FW bnamePAC350S12-CR
		Add: bnamePAC600S12-PB(16716063),    --FW bnamePAC600S12-PB
		Add: bnamePDC1K2S12-CE(16716064),    --FW bnamePDC1K2S12-CE
		Add: bnamePAC1K2S12-PB(16716065),    --FW bnamePAC1K2S12-PB

                "

		REVISION    "202206250000Z" 	 
        DESCRIPTION "V12.85,
                Add: subbname8090DEVCR57E8VBF2(226010),       --16-Port 50GBase/8-Port 100GBase-QSFP28 FlexE/MACsec Integrated Line Processing Unit (LPUI-1T)
                " 
		 
        REVISION    "202206230000Z" 	 
        DESCRIPTION "V12.84,
                Add: virent8090DEVTPXM01HSTA01(229536),           -- V8R22C00 for TPXM01HSTA01(SBOM) PTN 91A-F,3*10G/GE/FE(o)+7*GE/FE(o)+4*GE/FE(e)
                Add:virent8090DEVISR801BASAX1(525144),   -- V8R22C00 for ISR801BASAX1(SBOM) Mining intrinsic safety 10GE router KJJ12, NetEngine A831 E(3*10G/GE/FE(o)+7*GE/FE(o)+4*GE/FE(e))
                "

        REVISION    "202206220000Z" 	 
        DESCRIPTION "V12.83,
                Add: fnameEA5801EFL16H1(148538),         -- Backplane of the EA5801E-FL16-H1.
                "

        REVISION "202206210000Z" 
            DESCRIPTION "V12.82,
                modify: bnameLSG7SRUDX000(713497),
                modify: bnameLSG7SRUDX0H0(713498),
                add: fname8031S5732-H48UM4Y2CZ-KV2(537682),  --S5732-H48UM4Y2CZ-KV2  for V6R22C00
                add: fname8031S5732-H24UM4Y2CZ-V2(537683),   --S5732-H24UM4Y2CZ-V2   for V6R22C00
                add: fname8031S5732-H24UM4Y2CZ-TV2(537684),  --S5732-H24UM4Y2CZ-TV2  for V6R22C00
                add: fname8031S5732-H24UM4Y2CZ-KV2(537685),  --S5732-H24UM4Y2CZ-KV2  for V6R22C00
                add: fname8031S6730-H48X6CZ-V2(537686),      --S6730-H48X6CZ-V2      for V6R22C00
                add: fname8031S6730-H48X6CZ-TV2(537687),     --S6730-H48X6CZ-TV2     for V6R22C00
                add: fname8031S5732-H44S4X6QZ-V2(537688),    --S5732-H44S4X6QZ-V2    for V6R22C00
                add: fname8031S5732-H44S4X6QZ-TV2(537689),   --S5732-H44S4X6QZ-TV2   for V6R22C00

                add: fname8031S5750-L8T4X-QA(537690),        --S5750-L8T4X-QA    for V6R22C01
                add: fname8031S5750-L8T4S-A(537691),         --S5750-L8T4S-A     for V6R22C01
                add: fname8031S5750-L10T4X-A(537692),        --S5750-L10T4X-A    for V6R22C01
                add: fname8031S5750-L10T4X-TA(537693),       --S5750-L10T4X-TA   for V6R22C01
                add: fname8031S5350-L10T4X-A(537694),        --S5350-L10T4X-A    for V6R22C01
                add: fname8031S5750-L8P4X-QA(537696),        --S5750-L8P4X-QA    for V6R22C01
                add: fname8031S5750-L8P4S-A(537697),         --S5750-L8P4S-A     for V6R22C01
                add: fname8031S5750-L10P4X-A(537698),        --S5750-L10P4X-A    for V6R22C01
                add: fname8031S5750-L10P4X-TA(537699),       --S5750-L10P4X-TA   for V6R22C01
                add: fname8031S5350-L10P4X-A(537700),        --S5350-L10P4X-A    for V6R22C01
                add: fname8031S5350-L10T4X-D(537701),        --S5350-L10T4X-D    for V6R22C01
                add: fname8031S5750-L16T4X-QA(537702),       --S5750-L16T4X-QA   for V6R22C01
                add: fname8031S5750-L16T4S-A(537703),        --S5750-L16T4S-A    for V6R22C01
                add: fname8031S5350-L16T4X-A(537704),        --S5350-L16T4X-A    for V6R22C01
                add: fname8031S5750-L24T4X-QA(537705),       --S5750-L24T4X-QA   for V6R22C01
                add: fname8031S5750-L24T4S-A(537706),        --S5750-L24T4S-A    for V6R22C01
                add: fname8031S5750-L24T4XE-A(537707),       --S5750-L24T4XE-A   for V6R22C01
                add: fname8031S5350-L24T4XE-A(537708),       --S5350-L24T4XE-A   for V6R22C01
                add: fname8031S5750-L24T4XE-D(537709),       --S5750-L24T4XE-D   for V6R22C01
                add: fname8031S5350-L24T4XE-D(537710),       --S5350-L24T4XE-D   for V6R22C01
                add: fname8031S5750-S24T4XE(537712),         --S5750-S24T4XE     for V6R22C01
                add: fname8031S5350-S24T4XE(537713),         --S5350-S24T4XE     for V6R22C01
                add: fname8031S5750I-S24T4XE(537714),        --S5750I-S24T4XE    for V6R22C01
                add: fname8031S5750I-S24T4XE-T(537715),      --S5750I-S24T4XE-T  for V6R22C01
                add: fname8031S5750-L24P4S-A(537716),        --S5750-L24P4S-A    for V6R22C01
                add: fname8031S5750-L24P4XE-A(537717),       --S5750-L24P4XE-A   for V6R22C01
                add: fname8031S5750-L24P4XE-TA(537718),      --S5750-L24P4XE-TA  for V6R22C01
                add: fname8031S5350-L24P4XE-A(537719),       --S5350-L24P4XE-A   for V6R22C01
                add: fname8031S5750-S24P4XE(537721),         --S5750-S24P4XE     for V6R22C01
                add: fname8031S5350-S24P4XE(537722),         --S5350-S24P4XE     for V6R22C01
                add: fname8031S5750-L48T4S-A(537723),        --S5750-L48T4S-A    for V6R22C01
                add: fname8031S5750-L48T4XE-A(537724),       --S5750-L48T4XE-A   for V6R22C01
                add: fname8031S5350-L48T4XE-A(537725),       --S5350-L48T4XE-A   for V6R22C01
                add: fname8031S5750-L48T4XE-TA(537726),      --S5750-L48T4XE-TA  for V6R22C01
                add: fname8031S5750-L48T4XE-D(537727),       --S5750-L48T4XE-D   for V6R22C01
                add: fname8031S5750-S48T4XE(537728),         --S5750-S48T4XE     for V6R22C01
                add: fname8031S5350-S48T4XE(537729),         --S5350-S48T4XE     for V6R22C01
                add: fname8031S5750-L48LP4S-A(537730),       --S5750-L48LP4S-A   for V6R22C01
                add: fname8031S5750-L48LP4XE-A(537731),      --S5750-L48LP4XE-A  for V6R22C01
                add: fname8031S5750-L48P4XE-A(537732),       --S5750-L48P4XE-A   for V6R22C01
                add: fname8031S5750-S48P4XE(537733),         --S5750-S48P4XE     for V6R22C01
                add: fname8031S5350-S48P4XE(537734),         --S5350-S48P4XE     for V6R22C01
                add: fname8031S5750-S24U4XE(537735),         --S5750-S24U4XE     for V6R22C01
                add: fname8031S5350-S24U4XE(537736),         --S5350-S24U4XE     for V6R22C01
                add: fname8031S5750-S48U4XE(537737),         --S5750-S48U4XE     for V6R22C01
                add: fname8031S5350-S48U4XE(537738),         --S5350-S48U4XE     for V6R22C01
                add: fname8031S5750I-S24U4XE(537739),        --S5750I-S24U4XE    for V6R22C01
                add: fname8031S5750I-S24U4XE-T(537740),      --S5750I-S24U4XE-T  for V6R22C01
                add: fname8031S5750I-S8T4XN(537741),         --S5750I-S8T4XN     for V6R22C01
                add: fname8031S5750I-S8T4XN-T(537742),       --S5750I-S8T4XN-T   for V6R22C01
                add: fname8031S5750I-S8T4SN(537743),         --S5750I-S8T4SN     for V6R22C01
                add: fname8031S5750I-S8U4XN(537744),         --S5750I-S8U4XN     for V6R22C01

                add: bname8031S5732-H48UM4Y2CZ-KV2(537866),  --S5732-H48UM4Y2CZ-KV2 for V6R22C00 
                add: bname8031S5732-H24UM4Y2CZ-V2(537867),   --S5732-H24UM4Y2CZ-V2  for V6R22C00
                add: bname8031S5732-H24UM4Y2CZ-TV2(537868),  --S5732-H24UM4Y2CZ-TV2 for V6R22C00
                add: bname8031S5732-H24UM4Y2CZ-KV2(537869),  --S5732-H24UM4Y2CZ-KV2 for V6R22C00
                add: bname8031S6730-H48X6CZ-V2(537870),      --S6730-H48X6CZ-V2     for V6R22C00
                add: bname8031S6730-H48X6CZ-TV2(537871),     --S6730-H48X6CZ-TV2    for V6R22C00
                add: bname8031S5732-H44S4X6QZ-V2(537872),    --S5732-H44S4X6QZ-V2   for V6R22C00
                add: bname8031S5732-H44S4X6QZ-TV2(537873),   --S5732-H44S4X6QZ-TV2  for V6R22C00

                add: bname8031S5750-L8T4X-QA(537874),        --S5750-L8T4X-QA   for V6R22C01
                add: bname8031S5750-L8T4S-A(537875),         --S5750-L8T4S-A    for V6R22C01
                add: bname8031S5750-L10T4X-A(537876),        --S5750-L10T4X-A   for V6R22C01
                add: bname8031S5750-L10T4X-TA(537877),       --S5750-L10T4X-TA  for V6R22C01
                add: bname8031S5350-L10T4X-A(537878),        --S5350-L10T4X-A   for V6R22C01
                add: bname8031S5750-L8P4X-QA(537880),        --S5750-L8P4X-QA   for V6R22C01
                add: bname8031S5750-L8P4S-A(537881),         --S5750-L8P4S-A    for V6R22C01
                add: bname8031S5750-L10P4X-A(537882),        --S5750-L10P4X-A   for V6R22C01
                add: bname8031S5750-L10P4X-TA(537883),       --S5750-L10P4X-TA  for V6R22C01
                add: bname8031S5350-L10P4X-A(537884),        --S5350-L10P4X-A   for V6R22C01
                add: bname8031S5350-L10T4X-D(537885),        --S5350-L10T4X-D   for V6R22C01
                add: bname8031S5750-L16T4X-QA(537886),       --S5750-L16T4X-QA  for V6R22C01
                add: bname8031S5750-L16T4S-A(537887),        --S5750-L16T4S-A   for V6R22C01
                add: bname8031S5350-L16T4X-A(537888),        --S5350-L16T4X-A   for V6R22C01
                add: bname8031S5750-L24T4X-QA(537889),       --S5750-L24T4X-QA  for V6R22C01
                add: bname8031S5750-L24T4S-A(537890),        --S5750-L24T4S-A   for V6R22C01
                add: bname8031S5750-L24T4XE-A(537891),       --S5750-L24T4XE-A  for V6R22C01
                add: bname8031S5350-L24T4XE-A(537892),       --S5350-L24T4XE-A  for V6R22C01
                add: bname8031S5750-L24T4XE-D(537893),       --S5750-L24T4XE-D  for V6R22C01
                add: bname8031S5350-L24T4XE-D(537894),       --S5350-L24T4XE-D  for V6R22C01
                add: bname8031S5750-S24T4XE(537896),         --S5750-S24T4XE    for V6R22C01
                add: bname8031S5350-S24T4XE(537897),         --S5350-S24T4XE    for V6R22C01
                add: bname8031S5750I-S24T4XE(537898),        --S5750I-S24T4XE   for V6R22C01
                add: bname8031S5750I-S24T4XE-T(537899),      --S5750I-S24T4XE-T for V6R22C01
                add: bname8031S5750-L24P4S-A(537900),        --S5750-L24P4S-A   for V6R22C01
                add: bname8031S5750-L24P4XE-A(537901),       --S5750-L24P4XE-A  for V6R22C01
                add: bname8031S5750-L24P4XE-TA(537902),      --S5750-L24P4XE-TA for V6R22C01
                add: bname8031S5350-L24P4XE-A(537903),       --S5350-L24P4XE-A  for V6R22C01
                add: bname8031S5750-S24P4XE(537905),         --S5750-S24P4XE    for V6R22C01
                add: bname8031S5350-S24P4XE(537906),         --S5350-S24P4XE    for V6R22C01
                add: bname8031S5750-L48T4S-A(537907),        --S5750-L48T4S-A   for V6R22C01
                add: bname8031S5750-L48T4XE-A(537908),       --S5750-L48T4XE-A  for V6R22C01
                add: bname8031S5350-L48T4XE-A(537909),       --S5350-L48T4XE-A  for V6R22C01
                add: bname8031S5750-L48T4XE-TA(537910),      --S5750-L48T4XE-TA for V6R22C01
                add: bname8031S5750-L48T4XE-D(537911),       --S5750-L48T4XE-D  for V6R22C01
                add: bname8031S5750-S48T4XE(537912),         --S5750-S48T4XE    for V6R22C01
                add: bname8031S5350-S48T4XE(537913),         --S5350-S48T4XE    for V6R22C01
                add: bname8031S5750-L48LP4S-A(537914),       --S5750-L48LP4S-A  for V6R22C01
                add: bname8031S5750-L48LP4XE-A(537915),      --S5750-L48LP4XE-A for V6R22C01
                add: bname8031S5750-L48P4XE-A(537916),       --S5750-L48P4XE-A  for V6R22C01
                add: bname8031S5750-S48P4XE(537917),         --S5750-S48P4XE    for V6R22C01
                add: bname8031S5350-S48P4XE(537918),         --S5350-S48P4XE    for V6R22C01
                add: bname8031S5750-S24U4XE(537919),         --S5750-S24U4XE    for V6R22C01
                add: bname8031S5350-S24U4XE(537920),         --S5350-S24U4XE    for V6R22C01
                add: bname8031S5750-S48U4XE(537921),         --S5750-S48U4XE    for V6R22C01
                add: bname8031S5350-S48U4XE(537922),         --S5350-S48U4XE    for V6R22C01
                add: bname8031S5750I-S24U4XE(537923),        --S5750I-S24U4XE   for V6R22C01
                add: bname8031S5750I-S24U4XE-T(537924),      --S5750I-S24U4XE-T for V6R22C01
                add: bname8031S5750I-S8T4XN(537925),         --S5750I-S8T4XN    for V6R22C01
                add: bname8031S5750I-S8T4XN-T(537926),       --S5750I-S8T4XN-T  for V6R22C01
                add: bname8031S5750I-S8T4SN(537927),         --S5750I-S8T4SN    for V6R22C01
                add: bname8031S5750I-S8U4XN(537928),         --S5750I-S8U4XN    for V6R22C01

                add: subnamePAC180S12-CN(536829)     --PAC180S12-CN for V6R22C00
                add: subnamePAC600S12-PB(536830)     --PAC600S12-PB for V6R22C00
                add: subnamePAC1K2S12-PB(536831)     --PAC1K2S12-PB for V6R22C00
                add: subnamePDC1K2S12-CE(536832)     --PDC1K2S12-CE for V6R22C00"

		         REVISION    "202206200000Z"
        DESCRIPTION "V12.81,
           		Add:bnameCEL36CQFDC1G(688481), 
				Add:bnameCEL18CQFDC1G(688482), 
				Add:bnameCEL36LQFDC1G(688483), 
				Add:bnameCEL48XSFDC1G(688484), 
            "
			
        REVISION    "202206140000Z"
        DESCRIPTION "V12.80,
            Add:bnameH901acsc(148783),            -- Access Edge Computing board of MA5800.
            "

        REVISION    "202206110000Z"
        DESCRIPTION "V12.79,
            Add:bnameH902TNSC(148751),            -- 4*OTN board of MA5800
            Add:bnameH901DQHT(148784),            -- DQ ODN OAI board of MA5800 and EA5800.
            Add:bnameH902CSPD(148785),            -- 8*XGS combo board of MA5800.
            Modify:bnameH907CGHD(148663) to bnameH907CGHD(148786).
            Add:fnameMA5800H901BPLG(148530),      -- Backplane of MA5800-X17E/EA5800-X17E.
            Add:fnameMA5800H901BPIG(148531),      -- Backplane of MA5800-X15E/EA5800-X15E.
            Add:fnameMA5800H901BPMG(148532),      -- Backplane of MA5800-X7E/EA5800-X7E.
            "

		REVISION "202206080000Z" 
         DESCRIPTION "V12.78,
             virent8090DEVME0DVSUIK07B(688692),    -- V8R21C00 for ME0DVSUIK07B(SBOM) Integrated Service Unit 401(VSUI-401)
             virent8090DEVME0DVSUIK07C(688693),    -- V8R21C00 for ME0DVSUIK07C(SBOM) Integrated Service Unit 401(VSUI-401A)
             virent8090DEVME0DVSUIK07D(688694),    -- V8R21C00 for ME0DVSUIK07D(SBOM) Integrated Service Unit 401(VSUI-401-E)
             virent8090DEVME0DVSUIK07E(688695),    -- V8R21C00 for ME0DVSUIK07E(SBOM) Integrated Service Unit 401(VSUI-401A-E)
         "
		 
        REVISION    "202206061900Z"
        DESCRIPTION  "V12.77,
            Add:fname8031S5735-S24U4X(537780),  --  S5735-S24U4X (24*10/100/1000BASE-T ports, 4*10GE SFP+ ports, PoE++, without power module)
            Add:fname8031S5735-S48U4X(537781),  --  S5735-S48U4X (48*10/100/1000BASE-T ports, 4*10GE SFP+ ports, PoE++, without power module)
            Add:fname8031S5735S-S24S4X-A(537782),  --  S5735S-S24S4X bundle (24*GE SFP ports, 4*10GE SFP+ ports, 1*AC power module)
            Add:fname8031S5735S-S48S4X-A(537783),  --  S5735S-S48S4X bundle (48*GE SFP ports, 4*10GE SFP+ ports, 1*AC power module)
            Add:fname8031S6720S-S36S16X-A(537784),  --  S6720S-S36S16X-A (36*GE SFP ports, 16*10GE SFP+ ports, AC power supply, front access)
            Add:fname8031S5735S-S24T4S-XA(537785),  --  S5735S-S24T4S-X Bundle (24*10/100/1000BASE-T ports, 4*GE SFP ports, 1*AC power)"

		REVISION "202206060000Z" 
         DESCRIPTION "V12.76,  
             Add:subnamePAC600S56-EB(536825), --Function Module,AC&240VDC PSU,PAC600S56-EB,600W AC&240V DC Power Module (66mm Width Case,Back to Front,Power panel side exhaust) for V2R22C00
             Add:subnamePAC1000S56-EB(536826), --Function Module,AC&240VDC PSU,PAC1000S56-EB,1000W AC&240V DC Power Module(66mm Width Case,Back to Front, Power panel side exhaust) for V2R22C00
             Add:subnamePDC1000S56-EB(536827), --Function Module,DC PSU,PDC1000S56-EB,POE1000W DC Power Module (66mm Width Case, Back to Front, Power panel side exhaust) for V2R22C00 
         "
		 
		REVISION "202206010000Z"
            DESCRIPTION "V12.75,
		Add: virent8090DEVCR5D0SRUAH72(884885),   --  for CR5D0SRUAH72(SBOM) Switch and Route Processing Unit A20A(SRUA-480A-I, 32G Memory)
                Add: virent8090DEVCR5D0SRUAH73(923108),   --  for CR5D0SRUAH73(SBOM) Switch and Route Processing Unit A20(SRUA-480-I, 32G Memory)
                Add: virent8090DEVCX6D0SRUAH73(773065),   --  for CX6D0SRUAH73(SBOM) Switch and Route Processing Unit A20(SRUA-480-I, 32G Memory)
                Add: virent8090DEVTNRD0SRUAH73(727642),   --  for TNRD0SRUAH73(SBOM) Switch and Route Processing Unit A20(SRUA-480-I, 32G Memory)
                Add: virent8090DEVME0D0SRUAH76(256575),   --  for ME0D0SRUAH76(SBOM) Switch and Route Processing Unit A20A(SRUA-480A-I, 32G Memory)
                Add: virent8090DEVME0D0SRUAH77(553460),   --  for ME0D0SRUAH77(SBOM) Switch and Route Processing Unit A20(SRUA-480-I, 32G Memory)
                Add: virent8090DEVCR5D0SRUAI72(872979),   --  for CR5D0SRUAI72(SBOM) Switch and Route Processing Unit A21A(SRUA-1TA-H, 32G Memory)
                Add: virent8090DEVCR5D0SRUAI73(179748),   --  for CR5D0SRUAI73(SBOM) Switch and Route Processing Unit A21(SRUA-1T-H, 32G Memory)
                Add: virent8090DEVCX6D0SRUAI73(394380),   --  for CX6D0SRUAI73(SBOM) Switch and Route Processing Unit A21(SRUA-1T-H, 32G Memory)
                Add: virent8090DEVTNRD0SRUAI73(959654),   --  for TNRD0SRUAI73(SBOM) Switch and Route Processing Unit A21(SRUA-1T-H, 32G Memory)
                Add: virent8090DEVME0D0SRUAI74(870511),   --  for ME0D0SRUAI74(SBOM) Switch and Route Processing Unit A21A(SRUA-1TA-H, 32G Memory)
                Add: virent8090DEVME0D0SRUAI75(576765),   --  for ME0D0SRUAI75(SBOM) Switch and Route Processing Unit A21(SRUA-1T-H, 32G Memory)
                Add: virent8090DEVIG2D0SRUAI72(385921),   --  for IG2D0SRUAI72(SBOM) Switch and Route Processing Unit A18A(SRUA-1TA-H, 32G Memory)
		Add: virent8090DEVCR8DIPU480C9(468763),   -- V8R22C00 for CR8DIPU480C9(SBOM) Integrated Network Processing Unit (IPUA-480-C)
                Add: virent8090DEVCR8DIPU1T2E2(468767),   -- V8R22C00 for CR8DIPU1T2E2(SBOM) Integrated Network Processing Unit (IPUA-480-C)
                Add: virent8090DEVCR8DIPU480E1(468768),   -- V8R22C00 for CR8DIPU480E1(SBOM) Integrated Network Processing Unit (IPUA-1T2-C)
                Add: virent8090DEVCR8DIPU1T2CF(468769),   -- V8R22C00 for CR8DIPU1T2CF(SBOM) Integrated Network Processing Unit (IPUA-1T2-CN)
                Add: virent8090DEVCR8DIPU1T2E1(468773),   -- V8R22C00 for CR8DIPU1T2E1(SBOM) Integrated Network Processing Unit (IPUA-1T2-CN)
                Add: virentANHMHSTA4800(225307),         -- V800R022C00 for ANHMHSTA4800  ATN 910D-A, DC Power, Port Capacity 2*100GE/50GE+4*25GE/10GE/GE/FE+16*10GE/GE/FE+4*GE/FE, default all the GE/FE ports is enabled
                Add: virentANHMHSTA4801(225308),         -- V800R022C00 for ANHMHSTA4801  ATN 910D-A, AC Power, Port Capacity 2*100GE/50GE+4*25GE/10GE/GE/FE+16*10GE/GE/FE+4*GE/FE, default all the GE/FE ports is enabled"

                REVISION "202205300000Z"
            DESCRIPTION "V12.74,
            Add:virentTPQD02CXPA03(229670),          -- OptiX PTN 990E,TPQ2CXPA2,System Control,Cross-connect and Multi-protocol Process Unit
            Add:virentTPQD01CXPA03(229671),          -- OptiX PTN 990E,TPQ1CXPA2,System Control,Cross-connect and Multi-protocol Process Unit
            Add:virentTPQD01CXPA04(229672),          -- OptiX PTN 990E,TPQ1CXPA3,System Control,Cross-connect and Multi-protocol Process Unit
            Add:virentTPTD01CXPA03(229673),          -- OptiX PTN 980B,TPT1CXPA03,System Control,Cross-connect and Multi-protocol Process Unit
            Add:virentTPRD01CXPA03(229674),          -- OptiX PTN 970C,TPR1CXPA2,System Control,Cross-connect and Multi-protocol Process Unit
            Add:virentTPRD01CXPA04(229675),          -- OptiX PTN 970C,TPR1CXPA3,System Control,Cross-connect and Multi-protocol Process Unit
            "

                REVISION "202205230000Z"
            DESCRIPTION "V12.73,
            Add:fnameAR611-lte4ea(668043),  -- AR611-lte4ea FRAME
            Add:bnameAR611-lte4ea(668151),  -- AR611-lte4ea Main Control Unit
            Add:bnameSRU400L(668152),  --SRU400L Main Control Unit
            "
        
		REVISION    "202205211200Z"
            DESCRIPTION "V12.72,
            deleted: fnameCE6860ZQ(688245),     -- CE V3R22C00 added
            deleted: fnameCE8850ZQ(688246),     -- CE V3R22C00 added
            deleted: bnameCE6860ZQ(688478),     -- CE V3R22C00 added
            deleted: bnameCE8850ZQ(688479),     -- CE V3R22C00 added
            Add: fnameCE6860HAM(688245),     -- CE V3R22C00 added
            Add: fnameCE8850HAM(688246),     -- CE V3R22C00 added
            Add: bnameCE6860HAM(688478),     -- CE V3R22C00 added
            Add: bnameCE8850HAM(688479)      -- CE V3R22C00 added "

		REVISION    "202205201200Z"
            DESCRIPTION "V12.71,
                Add: virent8090DEVTPRD01CXPB00(340340),   --  for TPRD01CXPB00(SBOM) System Control,Cross-connect and Multi-protocol Process Unit
                Add: virent8090DEVTPRD01CXPB02(454776),   --  for TPRD01CXPB02(SBOM) System Control,Cross-connect and Multi-protocol Process Unit
                Add: virent8090DEVTPQD02CXPB00(607496),   --  for TPQD02CXPB00(SBOM) System Control,Cross-connect and Multi-protocol Process Unit
                Add: virent8090DEVTPQD02CXPB02(843488),   --  for TPQD02CXPB02(SBOM) System Control,Cross-connect and Multi-protocol Process Unit
                Add: virent8090DEVTPND01CXPD00(345510),   --  for TPND01CXPD00(SBOM) System Control,Cross-connect and Multi-protocol Process Unit
                Add: virent8090DEVTPND01CXPD02(520639),   --  for TPND01CXPD02(SBOM) System Control,Cross-connect and Multi-protocol Process Unit
                Add: virent8090DEVTPTD01CXPB01(981763),   --  for TPTD01CXPB01(SBOM) System Control,Cross-connect and Multi-protocol Process Unit
                Add: virent8090DEVTPSM1HOSTA0(823614),   --  for TPSM1HOSTA0(SBOM) PTN 916-F - DC Power,with 4*10GE(o),16*GE/FE(o),4*GE/FE(e) 
                Add: virent8090DEVTPSM1HOSTB0(912192),   --  for TPSM1HOSTB0(SBOM) PTN 916-F - AC Power,with 4*10GE(o),16*GE/FE(o),4*GE/FE(e) 
                Add: virent8090DEVTPSM1HOSTA1(707597),   --  for TPSM1HOSTA1(SBOM) PTN 916-F - DC Power,with 4*10GE(o),16*GE/FE(o),4*GE/FE(e) 
                Add: virent8090DEVTPSM1HOSTB1(436296),   --  for TPSM1HOSTB1(SBOM) PTN 916-F - AC Power,with 4*10GE(o),16*GE/FE(o),4*GE/FE(e) 
                Add: virent8090DEVTPSM1HOSTC0(232607),   --  for TPSM1HOSTC0(SBOM) PTN 916-F - DC Power,with 4*10GE(o,RTU control,default rate is 100 Mbit/s),16*GE/FE(o),4*GE/FE(e) 
                Add: virent8090DEVTPSM1HOSTD0(204144),   --  for TPSM1HOSTD0(SBOM) PTN 916-F - AC Power,with 4*10GE(o,RTU control,default rate is 100 Mbit/s),16*GE/FE(o),4*GE/FE(e)
                Add: virent8090DEVCR8DEANCJXCD(468753),   -- V8R22C00 for CR8DEANCJXCD(SBOM) 10-Port 100GBase-QSFP28 + 36-Port 25GE(SFP28)/10GE(SFP+)/GE(SFP) Integrated Line Processing Unit CM(LPUI-2TA-CM)
                Add: virent8090DEVCR8DEANCJXCE(468754),   -- V8R22C00 for CR8DEANCJXCE(SBOM) 10-Port 100GBase-QSFP28 + 36-Port 25GE(SFP28)/10GE(SFP+)/GE(SFP) Integrated Line Processing Unit L CM(LPUI-2TA-L-CM)
                Add: virent8090DEVCR8DEANCJXCC(468755),   -- V8R22C00 for CR8DEANCJXCC(SBOM) 10-Port 100GBase-QSFP28 + 36-Port 25GE(SFP28)/10GE(SFP+)/GE(SFP) Integrated Line Processing Unit L CM(LPUI-2T-L-CM)
                Add: virent8090DEVCR8DSSUFT4CS(468756),   -- V8R22C00 for CR8DSSUFT4CS(SBOM) 32-Port 100GBase-QSFP28 FlexE Integrated Line Processing Unit CM (LPUI-3T2-CM)
                Add: virent8090DEVCR8DSSUFT4CP(468757),   -- V8R22C00 for CR8DSSUFT4CP(SBOM) 32-Port 100GBase-QSFP28 FlexE Integrated Line Processing Unit CM (LPUI-3T2A-CM)
                Add: virent8090DEVCR8DSSUFT4CU(468758),   -- V8R22C00 for CR8DSSUFT4CU(SBOM) 32-Port 100GBase-QSFP28 FlexE Integrated Line Processing Unit L CM (LPUI-3T2A-L-CM)
                Add: virent8090DEVCR8DSSUFT4CW(468759),   -- V8R22C00 for CR8DSSUFT4CW(SBOM) 32-Port 100GBase-QSFP28 FlexE Integrated Line Processing Unit L CM (LPUI-3T2-L-CM)
                Add: virent8090DEVCR8DE4KEFNC1(468760),   -- V8R22C00 for CR8DE4KEFNC1(SBOM) 4-Port 400GBase-QSFP-DD + 24-Port 100GBase-QSFP28 Integrated Line Processing Unit CM (LPUIA-4T-CM)				
                "
		
        REVISION    "202205181200Z"
            DESCRIPTION "V12.70,
                Add: subbname8090DEVCR8DLPUTK0C0(226051),        --Trunk Line Processing Unit(LPUT-800-CM, 400G Enabled by Default)
                Add: subbname8090DEVCR8D00LAXFD0(226052),        --10-Port 10GE/GE LAN/WAN-SFP+ MACsec Physical Interface Card(PIC)
                Add: subbname8090DEVCR8DE2V1NBD0(226053),        --2-Port 50GBase/1-Port 100GBase-QSFP28 FlexE MACsec Physical Interface Card(PIC)
                Add: subbname8090DEVCR8D00EAGFD5(226054),        --10-port 100/1000Base-X-SFP MACsec Physical Interface Card(PIC)
                Add: subbname8090DEVCR8D00CDE1D0(226055),        --16-Port E1 Physical Interface Card(PIC,75ohm/120ohm)
                Add: subbname8090DEVCR8D00C4CFD0(226056),        --4-Port OC-3c/STM-1c POS-SFP Flexible Interface Card(PIC)
                Add: subbname8090DEVCR8D00E8GED0(226057),        --8-Port 100/1000Base-RJ45 Physical Interface Card(PIC)
                Add: subbname8090DEVCR8D00P8CFD0(226058),        --8-Port STM-1c/8-Port STM-4c POS Card (PIC)(Default Enable 4*STM-1c)
                Add: subbname8090DEVGPLI20CQES9(729921),   -- 20-Port 100GBase QSFP28 Integrated Line Process Unit
                Add: subbname8090DEVGPLI20CQE10(208306),   -- 20-Port 100GBase QSFP28 Integrated Line Process Unit
                Add: subbname8090DEVGPLI40CQES7(172719),   -- 40-Port 100GBase QSFP28 Integrated Line Process Unit
                Add: subbname8090DEVGPLI32CQE4(964151),   -- 32-Port 100GBase QSFP28 Integrated Line Process Unit
                Add: subbname8090DEVCR59E8NBD(165996),    -- 8-Port 100GBase QSFP28 Fixed card
                Add: subbname8090DEVCR59LJXFA(859868),    -- 36-Port 10GBase LAN/WAN-SFP+ Fixed card
                Add: subbname8090DEVGPLI4KQ24CQES1(733886),   -- 4-Port 400GBase QSFPDD 24-Port 100GBase QSFP28 Integrated Line Process Unit
                "

         REVISION "202205171200Z" 
         DESCRIPTION "V12.69,  
             Add:subnameS7C02000(536828), --2-port 100GE QSFP28 interface card for V2R22C00 
         "

        REVISION "202205130000Z" 
        DESCRIPTION "V12.68,
            Add: fnameAP161(692402),        -- WLAN R21C11 New AP
            Add: fnameAP162(692403),        -- WLAN R21C11 New AP
            Add: fnameAP362(692404),        -- WLAN R21C11 New AP
            Add: bnameAP161(692402),        -- WLAN R21C11 New AP
            Add: bnameAP162(692403),        -- WLAN R21C11 New AP
            Add: bnameAP362(692404),        -- WLAN R21C11 New AP
            "

        REVISION    "202205121500Z"
           DESCRIPTION "V12.67,
              Add: fname8031S5731-S24N4X2Q-A(537673), --S5731-S24N4X2Q-A(24*100M/1G/2.5G Ethernet ports, 4*10GE SFP+ ports, 2*40GE QSFP ports, AC power, front access)
              Add: fname8031S5331-S24N4X2Q-A(537674), --S5331-S24N4X2Q-A(24*100M/1G/2.5G Ethernet ports, 4*10GE SFP+ ports, 2*40GE QSFP ports, AC power, front access)
              Add: fname8031S5731S-S24N4X2Q-A1(537675), --S5731S-S24N4X2Q-A1(24*100M/1G/2.5G Ethernet ports, 4*10GE SFP+ ports, 2*40GE QSFP ports, AC power, front access)
              Add: fname8031S5731-S24UN4X2Q(537676), --S5731-S24NU4X2Q (24*100M/1G/2.5G Ethernet ports, 4*10GE SFP+ ports, 2*40GE QSFP ports, without power module)
              Add: fname8031S5731S-S24UN4X2Q(537677), --S5731S-S24NU4X2Q Bundle(24*100M/1G/2.5G/5G Ethernet ports, 4*10GE SFP+ ports or 2*40GE QSFP ports, with AC power supply)
              Add: fname8031S5731-S24UR2Q(537678), --S5731-S24RU2Q (24*100M/1G/2.5G/5G Ethernet ports, 4*10GE SFP+ ports or 2*40GE QSFP ports, without power module)
              Add: fname8031S5731S-S24UR2Q(537679), --S5731S-S24NU4X2Q Bundle(24*100M/1G/2.5G Ethernet ports, 4*10GE SFP+ ports, 2*40GE QSFP ports, with AC power supply)
              Add: fname8031S5731-S8UM16UN2Q(537680), --S5731-S8UM16UN2Q (8*100M/1G/2.5G/5G/10G,16*100M/1G/2.5G Ethernet ports, 2*40GE QSFP ports, switch to 16*100M/1G/2.5G/5G/10G,8*100M/1G Ethernet ports, 4*10GE SFP+ ports, without power module)
              Add: fname8031S5731S-S8UM16UN2Q(537681), --S5731-S8UM16UN2Q Bundle(8*100M/1G/2.5G/5G/10G,16*100M/1G/2.5G Ethernet ports, 2*40GE QSFP ports, switch to 16*100M/1G/2.5G/5G/10G,8*100M/1G Ethernet ports, 4*10GE SFP+ ports, with AC power supply)
              Add: bname8031S5731-S24N4X2Q-A(537857), --S5731-S24N4X2Q-A(24*100M/1G/2.5G Ethernet ports, 4*10GE SFP+ ports, 2*40GE QSFP ports, AC power, front access)
              Add: bname8031S5331-S24N4X2Q-A(537858), --S5331-S24N4X2Q-A(24*100M/1G/2.5G Ethernet ports, 4*10GE SFP+ ports, 2*40GE QSFP ports, AC power, front access)
              Add: bname8031S5731S-S24N4X2Q-A1(537859), --S5731S-S24N4X2Q-A1(24*100M/1G/2.5G Ethernet ports, 4*10GE SFP+ ports, 2*40GE QSFP ports, AC power, front access)
              Add: bname8031S5731-S24UN4X2Q(537860), --S5731-S24NU4X2Q (24*100M/1G/2.5G Ethernet ports, 4*10GE SFP+ ports, 2*40GE QSFP ports, without power module)
              Add: bname8031S5731S-S24UN4X2Q(537861), --S5731S-S24NU4X2Q Bundle(24*100M/1G/2.5G/5G Ethernet ports, 4*10GE SFP+ ports or 2*40GE QSFP ports, with AC power supply)
              Add: bname8031S5731-S24UR2Q(537862), --S5731-S24RU2Q (24*100M/1G/2.5G/5G Ethernet ports, 4*10GE SFP+ ports or 2*40GE QSFP ports, without power module)
              Add: bname8031S5731S-S24UR2Q(537863), --S5731S-S24NU4X2Q Bundle(24*100M/1G/2.5G Ethernet ports, 4*10GE SFP+ ports, 2*40GE QSFP ports, with AC power supply)
              Add: bname8031S5731-S8UM16UN2Q(537864), --S5731-S8UM16UN2Q (8*100M/1G/2.5G/5G/10G,16*100M/1G/2.5G Ethernet ports, 2*40GE QSFP ports, switch to 16*100M/1G/2.5G/5G/10G,8*100M/1G Ethernet ports, 4*10GE SFP+ ports, without power module)
              Add: bname8031S5731S-S8UM16UN2Q(537865), --S5731-S8UM16UN2Q Bundle(8*100M/1G/2.5G/5G/10G,16*100M/1G/2.5G Ethernet ports, 2*40GE QSFP ports, switch to 16*100M/1G/2.5G/5G/10G,8*100M/1G Ethernet ports, 4*10GE SFP+ ports, with AC power supply)
              "

		 
		REVISION    "202205120000Z"
        DESCRIPTION "V12.66,
          Add:subbname8090DEVCR8D00E2NBC4(295996),        --2-Port 50GBase/1-Port 100GBase-QSFP28 FlexE MACsec Physical Interface Card(PIC)
          Add:subbname8090DEVCR8D00E4XFC3(920246),      --4-Port 10GE(SFP+)/GE(SFP) MACsec Physical Interface Card(PIC)
          Add:subbname8090DEVCR8D00E4YFC0(742487),      --4-Port 25GE(SFP28)/10GE(SFP+) MACsec Physical Interface Card (PIC)
          Add:subbname8090DEVCR8D00EAGFCA(998794),      --10-port 100/1000Base-X-SFP MACsec Physical Interface Card(PIC)
          Add:subbname8090DEVCR8D00EAXFC1(607802),      --10-Port 10GE/GE LAN/WAN-SFP+ MACsec Physical Interface Card(PIC)
          Add:subbname8090DEVCR8D00EEGFXA(817470),      --20-Port 100/1000Base-X-CSFP/10-Port 100/1000Base-X-SFP Physical Interface Card(PIC)
          Add:subbname8090DEVCX6D0EFGFA14(913971),   -- 24-Port 100/1000Base-X-SFP Flexible Card A(S480-A)
          Add:subbname8090DEVCR8D00E8GEB2(226873),        --8-Port 100/1000Base-RJ45 Physical Interface Card(PIC)
          Add:subbname8090DEVCR5D00E1ND97(295791),      --1-Port 100GBase-CFP2 Physical Interface Card(PIC)
          Add:subbname8090DEVCR57LFXFN4(295992),         --24-Port 10GBase LAN/WAN-SFP+ MACsec Unflexible Card(P483)
          Add:subbname8090DEVCR58EKNBC1(270655),   -- 40-Port 100GE/50GE-QSFP28 Integrated Line Process Unit
          Add:subbname8090DEVCR58EKNBCS1(808683),   -- 40-Port 100GE/50GE-QSFP28 Integrated Line Process Unit
          Add:subbname8090DEVCR58E8KE8ND1(125263),   -- 8-Port 400GE-QSFP-DD + 8-Port 100GE-QSFP28 Integrated Line Process Unit
          Add:subbname8090DEVCR58E8KE8NDS1(245954),   -- 8-Port 400GE-QSFP-DD + 8-Port 100GE-QSFP28 Integrated Line Process Unit
          Add:subbname8090DEVCR58EENBJS1(470120),   -- 20-Port 100GE/50GE-QSFP28 Integrated Line Process Unit
          Add:subbname8090DEVCR58EENBJ1(669469),   -- 20-Port 100GE/50GE-QSFP28 Integrated Line Process Unit
          Add:subbname8090DEVGPR8CQ20YSC(295722),         --8-Port 100GBase-QSFP28 + 48-Port 25GBase-Y-SFP+  
		"
		
		REVISION    "202205110000Z"
        DESCRIPTION "V12.65,
          Add:fnameCE686648S8CQP6(688247), 
          Add:bnameCE686648S8CQP6(688480),
		"

		 
		REVISION    "202205050000Z"
        DESCRIPTION "V12.64,
          Add:fnameAR611E-S(668042),         --AR611E-S FRAME
          Add:bnameAR611E-S(668150),         --AR611E-S Main Control Unit
		"
        
        REVISION    "202205040000Z"
        DESCRIPTION "V12.63,
                Add: virent8090DEVCR5D00EDNB66(562120),    -- V8R22C00 for CR5D00EDNB66(SBOM) 16-Port 100GBase QSFP28 Integrated Line Process Unit C(NE5000E LPUI-1T6-C)
                Add: virent8090DEVCR5D00EDNB67(562121),    -- V8R22C00 for CR5D00EDNB67(SBOM) 16-Port 100GBase QSFP28 Integrated Line Process Unit C CM(NE5000E LPUI-1T6-C-CM)(4 ports enable)
                Add: virent8090DEVCR5D00LRXF63(562122),    -- V8R22C00 for CR5D00LRXF63(SBOM) 72-Port 10GBase LAN/WAN-SFP+ Integrated Line Process Unit C(NE5000E LPUI-1T6-C)
                Add: virent8090DEVCR5D00LRXF64(562123),    -- V8R22C00 for CR5D00LRXF64(SBOM) 72-Port 10GBase LAN/WAN-SFP+ Integrated Line Process Unit C CM(NE5000E LPUI-1T6-C-CM)(24 ports enable)
                Add: virent8090DEVCR5DSFUIT362(562190),    -- V8R22C00 for CR5DSFUIT362(SBOM) NE5000E-20 3.2T CLC Switch Fabric Unit for Single Chassis(SFU-3T2-S2)
            "

		REVISION    "202204250000Z"
        DESCRIPTION "V12.62,
          Add:virent8090DEVCR8PM1DBADC1(912355),   -- V8R21C12 for CR8PM1DBADC1(SBOM) NetEngine 8000 M1D, DC Power (Port Capacity 4*100GE/50GE+16*25GE/10GE/GE/FE+8*10GE/GE/FE,exclude auxiliary materials)
		  Add:virent8090DEVCR8PM1DBADC3(341533),   -- V8R21C12 for CR8PM1DBADC3(SBOM) NetEngine 8000 M1D, DC Power (Port Capacity 4*100GE/50GE+16*25GE/10GE/GE/FE+8*10GE/GE/FE,exclude auxiliary materials)
		  Add:virent8090DEVCR8PM1DBAACD(704146),   -- V8R21C12 for CR8PM1DBAACD(SBOM) NetEngine 8000 M1D, AC Power (Port Capacity 4*100GE/50GE+16*25GE/10GE/GE/FE+8*10GE/GE/FE,exclude auxiliary materials)
		  Add:virent8090DEVCR8PM1DBAACE(225775),   -- V8R21C12 for CR8PM1DBAACE(SBOM) NetEngine 8000 M1D, AC Power (Port Capacity 4*100GE/50GE+16*25GE/10GE/GE/FE+8*10GE/GE/FE,exclude auxiliary materials)
		  Add:virent8090DEVCR9D00EKNB83(624060),   -- V8R21C10 for CR9D00EKNB83(SBOM) 40-Port 100GE/50GE-QSFP28 Integrated Line Process Unit(LPUI-4TA)
          Add:virent8090DEVCR9DE8KE8N8X(613774),   -- V8R21C10 for CR9DE8KE8N8X(SBOM) 8-Port 400GE-QSFP-DD + 8-Port 100GE-QSFP28 Integrated Line Process Unit(LPUI-4TA)
          Add:virent8090DEVCR9D00EKNB8V(355341),   -- V8R21C10 for CR9D00EKNB8V(SBOM) 40-Port 100GE/50GE-QSFP28 Integrated Line Process Unit CM(LPUI-4T-CM)
          Add:virent8090DEVCR9D00EKNB8Y(359774),   -- V8R21C10 for CR9D00EKNB8Y(SBOM) 40-Port 100GE/50GE-QSFP28 Integrated Line Process Unit L(LPUI-4T-L)
          Add:virent8090DEVCR9DE8KE8N8Z(949736),   -- V8R21C10 for CR9DE8KE8N8Z(SBOM) 8-Port 400GE-QSFP-DD + 8-Port 100GE-QSFP28 Integrated Line Process Unit CM(LPUI-4T-CM, 8*100G RTU Enabled by default)
          Add:virent8090DEVCR9D00EENB88(309227),   -- V8R21C10 for CR9D00EENB88(SBOM) 20-Port 100GE/50GE-QSFP28 Integrated Line Process Unit CM(LPUI-2T-CM)
          Add:virent8090DEVCR9D00EKNB87(102386),   -- V8R21C10 for CR9D00EKNB87(SBOM) 20-Port 100GE/50GE-QSFP28 Integrated Line Process Unit L(LPUI-2T-L)
          Add:virent8090DEVCR9P9KHALM8F(536293),   -- V8R21C10 for CR9P9KHALM8F(SBOM) 20-Port 100GE/50GE-QSFP28 Integrated Line Process Unit (LPUI-2TA)
		"
		
		REVISION    "202204190000Z"
        DESCRIPTION "V12.61,
          Add:bnameTPQD02CXPA02(229566),                       --OptiX PTN 990E,TPQ2CXPA3,System Control,Cross-connect and Multi-protocol Process Unit
          Add:fnameATN910D-B-AC(229666),                       -- V8R22C00 for ATN910D-B AC chassis
          Add:fnameATN910D-B-DC(229667),                       -- V8R22C00 for ATN910D-B DC chassis
          Add:fnameNETENGINE-8000-M1D-B-AC(229668),            -- V8R22C00 for NetEngine-8000-M1D-B-AC chassis
          Add:fnameNETENGINE-8000-M1D-B-DC(229669),            -- V8R22C00 for NetEngine-8000-M1D-B-DC chassis
          Add:virent8090DEVANHMHSTA0600(525138),               -- V8R22C00 for ANHMHSTA0600(SBOM) ATN 910D-B, AC Power, Port Capacity 2*50GE(convertible into 10*10GE)+2*25GE(convertible into 4*10GE/GE)+2*10GE/GE+10*GE(o)+4*GE(e), default 2*25GE ports and all the GE/FE ports are enabled
          Add:virent8090DEVANHMHSTA0500(525139),               -- V8R22C00 for ANHMHSTA0500(SBOM) ATN 910D-B, DC Power, Port Capacity 2*50GE(convertible into 10*10GE)+2*25GE(convertible into 4*10GE/GE)+2*10GE/GE+10*GE(o)+4*GE(e), default 2*25GE ports and all the GE/FE ports are enabled
          Add:virent8090DEVCR8PM1DBASCJ(525140),               -- V8R22C00 for CR8PM1DBASCJ(SBOM) NetEngine 8000 M1D-B, AC Power (Port Capacity 2*50GE(convertible into 10*10GE)+2*25GE(convertible into 4*10GE/GE)+2*10GE/GE+10*GE(0)+4*GE(e), default 2*25GE ports and all the GE/FE ports are enabled,exclude auxiliary materials)
          Add:virent8090DEVCR8PM1DBASCK(525141),               -- V8R22C00 for CR8PM1DBASCK(SBOM) NetEngine 8000 M1D-B, AC Power (Port Capacity 2*50GE(convertible into 10*10GE)+2*25GE(convertible into 4*10GE/GE)+2*10GE/GE+10*GE(0)+4*GE(e), default 2*25GE ports and all the GE/FE ports are enabled,exclude auxiliary materials)
          Add:virent8090DEVCR8PM1DBASCF(525142),               -- V8R22C00 for CR8PM1DBASCF(SBOM) NetEngine 8000 M1D-B, DC Power (Port Capacity 2*50GE(convertible into 10*10GE)+2*25GE(convertible into 4*10GE/GE)+2*10GE/GE+10*GE(0)+4*GE(e), default 2*25GE ports and all the GE/FE ports are enabled,exclude auxiliary materials)
          Add:virent8090DEVCR8PM1DBASCH(525143),               -- V8R22C00 for CR8PM1DBASCH(SBOM) NetEngine 8000 M1D-B, DC Power (Port Capacity 2*50GE(convertible into 10*10GE)+2*25GE(convertible into 4*10GE/GE)+2*10GE/GE+10*GE(0)+4*GE(e), default 2*25GE ports and all the GE/FE ports are enabled,exclude auxiliary materials)
          Add:virent8090DEVCR8D00LRXFC5(120022),               -- V8R22C00 for CR8D00LRXFC5(SBOM) 72-Port 25GE(SFP28)/10GE(SFP+)/GE(SFP) Integrated Line Processing Unit CM(LPUI-2TA-CM)
          Add:virent8090DEVCR8DE4KEFNC0(629166),               -- V8R22C00 for CR8DE4KEFNC0(SBOM) 4-Port 400GBase-QSFP-DD + 24-Port 100GBase-QSFP28 Integrated Line Processing Unit CM (LPUI-4T-CM)
          Add:virent8090DEVCR5D0MPUB977(398204),               -- V8R22C00 for CR5D0MPUB977(SBOM) Main Processing Unit B12A(32G Memory)
          Add:virent8090DEVCR5D0MPUB976(168741),               -- V8R22C00 for CR5D0MPUB976(SBOM) Main Processing Unit B12(32G Memory)
          Add:virent8090DEVME0DMPUX8677(817646),               -- V8R22C00 for ME0DMPUX8677(SBOM) Main Processing Unit B12A(32G Memory)
          Add:virent8090DEVME0DMPUX8676(816731),               -- V8R22C00 for ME0DMPUX8676(SBOM) Main Processing Unit B12(32G Memory)
          Add:virent8090DEVCX6DMPUX8674(768006),               -- V8R22C00 for CX6DMPUX8674(SBOM) Main Processing Unit B12(32G Memory)
          Add:virent8090DEVTNRDMPUX8674(754372),               -- V8R22C00 for TNRDMPUX8674(SBOM) Main Processing Unit B12(32G Memory)
          Add:virent8090DEVIG2D0MPUB977(997356),               -- V8R22C00 for IG2D0MPUB977(SBOM) Main Processing Unit B12A(32G Memory)
          Add:virent8090DEVCR5DLPUFF376(688992),               -- V8R21C12 for CR5DLPUFF376(SBOM) Flexible Card Line Processing Unit(LPUF-243A)
          Add:virent8090DEVCR5DLPUFM379(688993),               -- V8R21C12 for CR5DLPUFM379(SBOM) 48-Port 10GBase LAN/WAN-SFP+ Integrated Line Processing Unit L(LPUI-483-L)
          Modify:fnameNETENGINE-A813-AC(229661),               -- V8R22C00 for NetEngine-A813-AC chassis
          Modify:fnameNETENGINE-A813-E-AC(229662)              -- V8R22C00 for NetEngine-A813-E-AC chassis
          Modify:fnameATN905-S-AC(229663),                     -- V8R22C00 for ATN905-S-AC chassis
          Modify:fnameNETENGINE-A822-E-AC(229664),             -- V8R22C00 for NetEngine-A822-E-AC chassis
		"
		
		REVISION    "202204140000Z"
        DESCRIPTION "V12.59,
          Modify: virent8090DEVCP8PHST1MA00(229514),           -- V8R21C00 for CP8PHST1MA00(SBOM) NetEngine A811 M AC System (10*GE/FE(o), 8*GE/FE(e))
          Modify: virent8090DEVCP8PHST10A03(229520),           -- V8R21C00 for CP8PHST10A03(SBOM) NetEngine A811 AC System (10*GE/FE(o), 8*GE/FE(e))
          Modify: virent8090DEVCP8PHST10A06(229524),           -- V8R21C10 for CP8PHST10A06(SBOM) NetEngine A811 AC System (10*GE/FE(o)+8*GE/FE(e))
          Modify: virent8090DEVHGFM0HOSTB00(229522),           -- V8R21C00 for HGFM0HOSTB00(SBOM) HG-FM CPE-02 AC Power,with 6*GE/FE(o),8*GE/FE(e)
          Modify: virent8090DEVCP8PHST1MA02(229523),           -- V8R21C00 for CP8PHST1MA02(SBOM) NetEngine A810 M AC System (10*GE/FE(o), 8*GE/FE(e))
          Modify: virent8090DEVHGFM0HOSTC00(229529),           -- V8R22C00 for HGFM0HOSTC00(SBOM) HG-FM CPE-03 AC Power,with 2*10GE Fine Granularity Unit(o),4*10GE/GE/FE(o),4*GE/FE(o),8*GE/FE(e)
          Modify: virent8090DEVCP8PHST5MA01(229530),           -- V8R22C00 for CP8PHST5MA01(SBOM) NetEngine A850 M AC System (4*GE/FE(o)+2*GE(o)+8*GE/FE(e)+5G(dual SIM))
          Modify: virent8090DEVHGFM0HOSTA00(229531),           -- V8R22C00 for HGFM0HOSTA00(SBOM) HG-FM CPE-01 AC Power,with 5G module ,6*GE/FE(o),8*GE/FE(e)
          Modify: virent8090DEVCP8PHST1MA04(229532),           -- V8R22C00 for CP8PHST1MA04(SBOM) NetEngine A813 M AC System (6*GE/FE(o)+8*GE/FE(e))
          Modify: virent8090DEVTPXM01HSTA00(229533),           -- V8R22C00 for TPXM01HSTA00(SBOM) PTN 91A-F DC Power,with 3*10G/GE/FE(o),7*GE/FE(o),4*GE/FE(e)
		"
		
		REVISION    "202204110000Z"
        DESCRIPTION "V12.59,
			Add:virent8090DEVCR8P8KHALMC7(689243),   -- V8R22C00 for CR8P8KHALMC7(SBOM) 20-Port 100GBase-QSFP28 Integrated Line Processing Unit CM(LPUI-2T-CM)
            Add:virent8090DEVCR8DEANCJXCB(539206),   -- V8R22C00 for CR8DEANCJXCB(SBOM) 10-Port 100GBase-QSFP28 + 36-Port 25GE(SFP28)/10GE(SFP+)/GE(SFP) Integrated Line Processing Unit CM(LPUI-2T-CM)
			Add:fnameNETENGINE-A831-E-DC(229665),    -- V8R22C00 for CP8PHST2EA10(SBOM) NetEngine-A831-E-DC chassis
			Add:virent8090DEVCP8PHST2EA10(525137),   -- V8R22C00 for CP8PHST2EA10(SBOM) NetEngine A831 E, CP8PHST2EA10, NetEngine A831 E AC Chassis(A) (3*10G/GE/FE(o)+7*GE/FE(o)+4*GE/FE(e))
			Add:fnamePTN910D-F-AC(229540),           -- V8R22C00 for PTN910D-F-AC chassis
            Add:fnamePTN910D-F-DC(229542),           -- V8R22C00 for PTN910D-F-DC chassis
			"
		
		REVISION    "202204080000Z"
        DESCRIPTION "V12.58,
            Add:fnameNETENGINE-8000-F8(688437),           -- Quidway fnameNETENGINE-8000-F8 FRAME for V8R22C00
            Add:fnameNETENGINE-8000E-F8(688438),          -- Quidway fnameNETENGINE-8000E-F8 FRAME for V8R22C00
            Add:fnameNETENGINE-8000E-F8-Z(688439),        -- Quidway fnameNETENGINE-8000E-F8-Z FRAME for V8R22C00
			Add:virent8090DEVCR8DMPUF8AZ1(800103),    -- V8R22C00 CR8DMPUF8AZ1(SBOM) NetEngine 8000E F Main Processing Unit B1Z(MPUB1Z)
            Add:virent8090DEVCR8DMPUF8AC1(800104),    -- V8R22C00 CR8DMPUF8AC1(SBOM) NetEngine 8000E F Main Processing Unit B1A(MPUB1A)
            Add:virent8090DEVCR8DMPUF8AC0(800105),    -- V8R22C00 CR8DMPUF8AC0(SBOM) NetEngine 8000 F Main Processing Unit B1(MPUB1)
            Add:virent8090DEVCR8DSFUIK0C1(800106),    -- V8R22C00 CR8DSFUIK0C1(SBOM) NetEngine 8000E F 2T Switch Routing Unit(SRUA-2T-A)
            Add:virent8090DEVCR8DSFUIK0C0(800107),    -- V8R22C00 CR8DSFUIK0C0(SBOM) NetEngine 8000 F 2T Switch Routing Unit(SRU-2T-A)
            Add:fnameNETENGINE-A813-AC(229534), -- V8R22C00 for NetEngine-A813-AC chassis
            Add:fnameNETENGINE-A813-E-AC(229535), -- V8R22C00 for NetEngine-A813-E-AC chassis
            Add:fnameATN905-S-AC(229536), -- V8R22C00 for ATN905-S-AC chassis
            Add:fnameNETENGINE-A822-E-AC(229537), -- V8R22C00 for NetEngine-A822-E-AC chassis
            Add:virent8090DEVCP8PHST10A08(525130),   -- V8R22C00 for CP8PHST10A08(SBOM) NetEngine A813, CP8PHST10A08, NetEngine A813 AC System (6*GE/FE(o)+8*GE/FE(e))
            Add:virent8090DEVCP8PHST1EA07(525131),   -- V8R22C00 for CP8PHST1EA07(SBOM) NetEngine A813 E, CP8PHST1EA07, NetEngine A813 E AC Chassis (6*GE/FE(o)+8*GE/FE(e))
            Add:virent8090DEVCP8PHST1EAA6(525132),   -- V8R22C00 for CP8PHST1EAA6(SBOM) NetEngine A813 E, CP8PHST1EAA6, NetEngine A813 E AC Chassis (6*GE/FE(o)+8*GE/FE(e))
            Add:virent8090DEVANPM01HOST5(525133),    -- V8R22C00 for ANPM01HOST5(SBOM)  ATN 905, ANPM01HOST5, ATN 905-S System,AC,4*GE/FE(o),4*GE/FE(e)
            Add:virent8090DEVANPM01HOST6(525134),    -- V8R22C00 for ANPM01HOST6(SBOM)  ATN 905, ANPM01HOST6, ATN 905-S System,AC,4*GE/FE(o),4*GE/FE(e)
            Add:virent8090DEVCP8PHST2EA21(525135),   -- V8R22C00 for CP8PHST2EA21(SBOM) NetEngine A822 E, CP8PHST2EA21, NetEngine A822 E AC Chassis(A)(2*10GE/GE/FE(o)+4*GE/FE(o)+8*GE/FE(e))
            Add:virent8090DEVCP8PHST2EA22(525136),   -- V8R22C00 for CP8PHST2EA22(SBOM) NetEngine A822 E, CP8PHST2EA22, NetEngine A822 E AC Chassis (2*10GE/GE/FE(o)+4*GE/FE(o)+8*GE/FE(e))
			"

		REVISION    "202204070000Z"
        DESCRIPTION "V12.57,
			Add:virent8090DEVCR5DSFUIT27S(112979),   -- V8R21C12 for CR5DSFUIT27S(SBOM) 2Tbps Switch Fabric Unit I(SFUI-2TA-I)
			Add:virent8090DEVCR5DSFUITD74(700991),   -- V8R21C12 for CR5DSFUITD74(SBOM) 2Tbps Switch Fabric Unit J(SFUI-2TA-J)
			Add:virent8090DEVME0DSFUIM07N(370522),   -- V8R21C12 for ME0DSFUIM07N(SBOM) 480Gbps Switch Fabric Unit N(SFUI-480A-M)
			Add:virent8090DEVME0DSFUIM07M(487111),   -- V8R21C12 for ME0DSFUIM07M(SBOM) 480Gbps Switch Fabric Unit N(SFUI-480-M)
			Add:virent8090DEVME0D0SRUAH74(688990),    -- V8R21C12 for ME0D0SRUAH74(SBOM) Switch and Route Processing Unit A20A(SRUA-480A-G, 32G Memory)
			Add:virent8090DEVME0D0SRUAH75(688991),   -- V8R21C12 for ME0D0SRUAH75(SBOM) Switch and Route Processing Unit A20(SRUA-480-G, 32G Memory)
			Add:virent8090DEVTPWM0HOSTA02(229534),   -- V8R22C00 for TPWM0HOSTA02(SBOM) PTN 910D-F AC Power,with 2*50GE(o),6*10GE/GE/FE(o),10*GE/FE(o),4*GE/FE(e)
            Add:virent8090DEVTPWM0HOSTB02(229535),   -- V8R22C00 for TPWM0HOSTB02(SBOM) PTN 910D-F DC Power,with 2*50GE(o),6*10GE/GE/FE(o),10*GE/FE(o),4*GE/FE(e)
			"
			
        REVISION    "202203310000Z"
        DESCRIPTION "V12.56,
            Add:fnameMA5801GP16H2(148526),        -- Backplane of the MA5801-GP16-H2.
            Add:fnameMA5801GP08H3(148527),        -- Backplane of the MA5801-GP08-H3.
            Add:fnameMA5801SGP16S2(148529),       -- Backplane of the MA5801S-GP16-S2.
            Add:fnameMA5801SGP16H2(148533),       -- Backplane of the MA5801S-GP16-H2.
            Add:bnameV922MPCC(148759),            -- control board of MA5801-GP16-H2.
            Add:bnameV922GPHF(148760),            -- 16*GPON board of MA5801-GP16-H2.
            Add:bnameV925NXHC(148762),            -- 4*10GE/GE board of MA5801-GP16-H2.
            Add:bnameV932MPBB(148763),            -- control board of MA5801S-GP16-H2.
            Add:bnameV932GPHF(148764),            -- 16*GPON board of MA5801S-GP16-H2.
            Add:bnameV932GPSF(148765),            -- 16*GPON board of MA5801S-GP16-S2.
            Add:bnameV933NXHC(148766),            -- 4*10GE/GE board of MA5801S-GP16-H2.
            Add:bnameV933NXSC(148767),            -- 4*GE board of MA5801S-GP16-S2.
            Add:bnameV922GPHD(148768),            -- 8*GPON board of MA5801-GP08-H3.
            Add:fnameEA5801EGP16H2(148534),       -- Backplane of the EA5801E-GP16-H2.
            Add:fnameEA5801EGP08H3(148535),       -- Backplane of the EA5801E-GP08-H3.
            Add:fnameEA5801EGP04H2(148536),       -- Backplane of the EA5801E-GP04-H2.
            Add:fnameEA5801SGP16H2(148537),       -- Backplane of the EA5801S-GP16-H2.
            Add:bnameV922MPCCE(148775),           -- control board of EA5801E-GP16-H2.
            Add:bnameV922MPCEE(148776),           -- control board of EA5801E-GP04-H2.
            Add:bnameV932MPBBE(148776),           -- control board of EA5801S-GP16-H2.
            Add:bnameV922MPCDE(148778),           -- control board of EA5801E-GP08-H3.
            Add:bnameV922GPHFE(148779),           -- 16*GPON board of EA5801E-GP16-H2.
            Add:bnameV922GPHDE(148780),           -- 8*GPON board of EA5801E-GP08-H3.
            Add:bnameV922GPHCE(148781),           -- 4*GPON board of EA5801E-GP04-H2.
            Add:bnameV932GPHFE(148782),           -- 16*GPON board of EA5801S-GP16-H2
            "
		
		REVISION    "202203280000Z"
        DESCRIPTION "V12.55,
            Add: virent8090DEVCR5DMPUX8675(898253),       -- V8R21C10 for CR5DMPUX8675(SBOM) Main Processing Unit B112A(32G Memory)
            "

        REVISION    "202203210000Z"
        DESCRIPTION "V12.54,
            Add: bnameH907CGHD(148663),      -- 8*XG combo board of MA5800.
            Add: bnameH902CGPD(148753),      -- 8*XG combo board of MA5800.
            Add: bnameH905FLHF(156026),      -- 16*flex-PON board of MA5800.
            Add: bnameH905FLHFE(156028),     -- 16*flex-PON board of EA5800.
            Add: bnameH905CSHF(148769),      -- 16*XG/G GPON combo board of MA5800.
            Add: bnameH905CSHFE(148770),     -- 16*XG/G GPON combo board of EA5800.
            Add: bnameH905XSHF(148771),      -- 16*10G XGS-PON board of MA5800.
            Add: bnameH905XSHFE(148772),     -- 16*10G XGS-PON board of EA5800.
            Add: bnameH903OGHK(148773),      -- 48 P2P board of MA5800.
            Add: bnameH905OXEG(148774),      -- 24*10GE board of MA5800.
            "
		
        REVISION    "202203152000Z"
           DESCRIPTION "V12.47,
              Add: fname8031S600-S24S28X(537654), --S600-S24S28X (24*GE SFP ports, 28*10GE SFP+ ports, AC power supply, front access) for V2R21C10
              Add: bname8031S600-S24S28X(537838), --S600-S24S28X (24*GE SFP ports, 28*10GE SFP+ ports, AC power supply, front access) for V2R21C10
              "
        REVISION    "202203150000Z"
           DESCRIPTION "V12.52
               Add: fnameLSS8704SP0(713474),                -- HUAWEI S8704 FRAME
               Add: bnameLSG7SRUDX1C0(713497),  --S8700-4 main control unit D, supporting 2*10GE SFP+, 24*GE SFP ports
               Add: bnameLSG7SRUDX1T0(713498),  --S8700-4 main control unit D, supporting 2*10GE SFP+, 24*GE SFP ports(TPM)

               Add: fname8031S6730-H28X6CZ-V2(537667), --S6730-H28X6C-V2 (28*10GE SFP+ ports, 6*100GE QSFP28, 1*expansion slot, without power module) for V6R22C00
               Add: fname8031S6730-H28X6CZ-TV2(537668), --S6730-H28X6C-TV2 (28*10GE SFP+ ports, 6*100GE QSFP28, 1*expansion slot, HTM, without power module) for V6R22C00
               Add: fname8031S5732-H24S4X6QZ-V2(537669), --S5732-H24S4X6QZ-V2 (24*GE SFP ports,4*10GE SFP+ ports,6*40GE QSFP ports, 1*expansion slot, without power module) for V6R22C00
               Add: fname8031S5732-H24S4X6QZ-TV2(537670), --S5732-H24S4X6QZ-TV2 (24*GE SFP ports,4*10GE SFP+ ports,6*40GE QSFP ports, 1*expansion slot, HTM, without power module) for V6R22C00
               Add: fname8031S5732-H48UM4Y2CZ-V2(537671), --S5732-H48UM4Y2CZ-V2 2.5G Bundle(48*100M/1G/2.5G Ethernet ports, Optional RTU upgrade to 5/10G, 4*25GE SFP28, 2*100GE QSFP28 ports, 1*expansion slot, PoE++, with AC power supply) for V6R22C00
               Add: fname8031S5732-H48UM4Y2CZ-TV2(537672), --S5732-H48UM4Y2CZ-TV2 2.5G Bundle(48*100M/1G/2.5G Ethernet ports, Optional RTU upgrade to 5/10G, 4*25GE SFP28, 2*100GE QSFP28 ports, 1*expansion slot, PoE++, HTM, with AC power supply) for V6R22C00

               Add: bname8031S6730-H28X6CZ-V2(537851), --S6730-H28X6C-V2 (28*10GE SFP+ ports, 6*100GE QSFP28, 1*expansion slot, without power module) for V6R22C00
               Add: bname8031S6730-H28X6CZ-TV2(537852), --S6730-H28X6C-TV2 (28*10GE SFP+ ports, 6*100GE QSFP28, 1*expansion slot, HTM, without power module) for V6R22C00
               Add: bname8031S5732-H24S4X6QZ-V2(537853), --S5732-H24S4X6QZ-V2 (24*GE SFP ports,4*10GE SFP+ ports,6*40GE QSFP ports, 1*expansion slot, without power module) for V6R22C00
               Add: bname8031S5732-H24S4X6QZ-TV2(537854), --S5732-H24S4X6QZ-TV2 (24*GE SFP ports,4*10GE SFP+ ports,6*40GE QSFP ports, 1*expansion slot, HTM, without power module) for V6R22C00
               Add: bname8031S5732-H48UM4Y2CZ-V2(537855), --S5732-H48UM4Y2CZ-V2 2.5G Bundle(48*100M/1G/2.5G Ethernet ports, Optional RTU upgrade to 5/10G, 4*25GE SFP28, 2*100GE QSFP28 ports, 1*expansion slot, PoE++, with AC power supply) for V6R22C00
               Add: bname8031S5732-H48UM4Y2CZ-TV2(537856), --S5732-H48UM4Y2CZ-TV2 2.5G Bundle(48*100M/1G/2.5G Ethernet ports, Optional RTU upgrade to 5/10G, 4*25GE SFP28, 2*100GE QSFP28 ports, 1*expansion slot, PoE++, HTM, with AC power supply) for V6R22C00
         "

        REVISION    "202203110000Z"
           DESCRIPTION "V12.51
        bnameFMSFU04G1(716832),
        bnameFMSFU08G1(716833),
         "
        REVISION    "202203100000Z"
           DESCRIPTION "V12.50
                Add: fnameUSG6308E-B(16716010),   -- Assembling Components,USG6308E-AC,USG6308E-AC,,USG6308E AC Host(16*GE RJ45+8*GE Combo+2*10GE SFP+,0 AC power)
                Add: fnameUSG6318E-B(16716011),   -- Assembling Components,USG6318E-AC,USG6318E-AC,,USG6318E AC Host(16*GE RJ45+8*GE Combo+2*10GE SFP+,1 AC power)
                Add: fnameUSG6338E-B(16716012),   -- Assembling Components,USG6338E-AC,USG6338E-AC,,USG6338E AC Host(16*GE RJ45+8*GE Combo+2*10GE SFP+,1 AC power)
                Add: fnameUSG6358E-B(16716013),   -- Assembling Components,USG6358E-AC,USG6358E-AC,,USG6358E AC Host(16*GE RJ45+8*GE Combo+2*10GE SFP+,1 AC power)
                Add: fnameUSG6378E-B(16716014),   -- Assembling Components,USG6378E-AC,USG6378E-AC,,USG6378E AC Host(16*GE RJ45+8*GE Combo+2*10GE SFP+,1 AC power)
                Add: fnameUSG6388E-B(16716015),   -- Assembling Components,USG6388E-AC,USG6388E-AC,,USG6388E AC Host(16*GE RJ45+8*GE Combo+2*10GE SFP+,1 AC power)
                Add: fnameUSG6398E-B(16716016),   -- Assembling Components,USG6398E-AC,USG6398E-AC,,USG6398E AC Host(16*GE RJ45+8*GE Combo+2*10GE SFP+,1 AC power)
                Modify: fnameUSG6000F-E20(16716017),   -- Assembling Components,USG6000F-E20-AC,USG6000F-E20-AC,USG6000F-E20 host(16*GE RJ45 + 12*GE SFP + 4*10GE SFP+ ,1AC POWER)
                Modify: fnameUSG6000F-E15(16716018),   -- Assembling Components,USG6000F-E15-AC,USG6000F-E15-AC,USG6000F-E15 AC host(16*GE RJ45 + 12*GE SFP + 4*10GE SFP+ ,1AC POWER)
                Modify: fnameUSG6000F-E12(16716019),   -- Assembling Components,USG6000F-E12-AC,USG6000F-E12-AC,USG6000F-E12 AC host(16*GE RJ45 + 12*GE SFP + 4*10GE SFP+ ,1AC POWER)
                Modify: fnameUSG6000F-E09(16716020),   -- Assembling Components,USG6000F-E9-AC,USG6000F-E9-AC,USG6000F-E9 AC host(16*GE RJ45 + 12*GE SFP + 4*10GE SFP+ ,1AC POWER)
                Modify: fnameUSG6000F-E07(16716021),   -- Assembling Components,USG6000F-E7-AC,USG6000F-E7-AC,USG6000F-E7 AC host(16*GE RJ45 + 12*GE SFP + 4*10GE SFP+ ,1AC POWER)
                Modify: fnameUSG6000F-E05(16716022),   -- Assembling Components,USG6000F-E5-AC,USG6000F-E5-AC,USG6000F-E5 AC host(16*GE RJ45 + 12*GE SFP + 4*10GE SFP+ ,1AC POWER)
                Modify: fnameUSG6000F-E03(16716023),   -- Assembling Components,USG6000F-E3-AC,USG6000F-E3-AC,USG6000F-E3 AC host(16*GE RJ45 + 12*GE SFP + 4*10GE SFP+ ,1AC POWER)
                Modify: fnameUSG6000F-E01(16716024),   -- Assembling Components,USG6000F-E2-AC,USG6000F-E2-AC,USG6000F-E2 AC host(16*GE RJ45 + 12*GE SFP + 4*10GE SFP+ ,1AC POWER)
                Modify: fnameProbe1005(16716025),   -- Assembling Components,Probe1005-AC,Probe1005-AC,Probe1005 host(8*GE COMBO + 4*GE RJ45 + 10*10GE SFP+ , 2 AC POWER)
                Modify: fnameProbe1010(16716026),   -- Assembling Components,Probe1005-AC,Probe1005-AC,Probe1005 host(8*GE COMBO + 4*GE RJ45 + 10*10GE SFP+ , 2 AC POWER)
                Modify: fnameProbe1020(16716027),   -- Assembling Components,USG6715F-AC,USG6715F-AC,USG6715F-AC-host(2*QSFP28 + 2*QSFP+ + 8*ZSFP+ + 20*SFP+ , 2 AC POWER)
                Modify: fnameProbe1030(16716028),   -- Assembling Components,USG6725F-AC,USG6725F-AC,USG6725F-AC-host(4*QSFP28 + 16*ZSFP+ + 8*SFP+ , 2 AC POWER)
                Add: bnameUSG6000E-E03(16748778),    --FW Assembling Components,USG6000E-E03-AC,USG6000E-E03-AC,USG6000E-E03 AC Host(2*GE WAN+8*GE Combo+2*10GE SFP+,1 AC power)
                Add: bnameUSG6000E-E07(16748779),    --FW Assembling Components,USG6000E-E07-AC,USG6000E-E07-AC,USG6000E-E07 AC Host(2*GE WAN+8*GE Combo+2*10GE SFP+,1 AC power)
                Add: bnameUSG6000E-E10(16748780),    --FW Assembling Components,USG6000E-E10-ACUSG6000E-E10-AC,USG6000E-E10 AC Host(16*GE RJ45+8*GE Combo+2*10GE SFP+,1 AC power)
                Add: bnameUSG6308E-B(16748781),    --FW Assembling Components,USG6308E-B-AC,USG6308E-B-AC,USG6308E-B AC Host(16*GE RJ45+8*GE Combo+2*10GE SFP+,0 AC power)
                Add: bnameUSG6318E-B(16748782),    --FW Assembling Components,USG6318E-B-AC,USG6318E-B-AC,USG6318E-B AC Host(16*GE RJ45+8*GE Combo+2*10GE SFP+,1 AC power)
                Add: bnameUSG6338E-B(16748783),    --FW Assembling Components,USG6338E-B-AC,USG6338E-B-AC,USG6338E-B AC Host(16*GE RJ45+8*GE Combo+2*10GE SFP+,1 AC power)
                Add: bnameUSG6358E-B(16748784),    --FW Assembling Components,USG6358E-B-AC,USG6358E-B-AC,USG6358E-B AC Host(16*GE RJ45+8*GE Combo+2*10GE SFP+,1 AC power)
                Add: bnameUSG6378E-B(16748785),    --FW Assembling Components,USG6378E-B-AC,USG6378E-B-AC,USG6378E-B AC Host(16*GE RJ45+8*GE Combo+2*10GE SFP+,1 AC power)
                Add: bnameUSG6388E-B(16748786),    --FW Assembling Components,USG6388E-B-AC,USG6388E-B-AC,USG6388E-B AC Host(16*GE RJ45+8*GE Combo+2*10GE SFP+,1 AC power)
                Add: bnameUSG6398E-B(16748787),    --FW Assembling Components,USG6398E-B-AC,USG6398E-B-AC,USG6398E-B AC Host(16*GE RJ45+8*GE Combo+2*10GE SFP+,1 AC power)
            "

        REVISION    "202203080000Z"
           DESCRIPTION "V12.49
              Add:bnameAR5710-H8T2TS1(668145),           --AR5710-H8T2TS1 Main Control Unit
              Add:bnameAR5710-H8T2TS1-T(668146),         --AR5710-H8T2TS1-T Main Control Unit
              Add:bnameAR6710-L8T3TS1X2(668147),         --AR6710-L8T3TS1X2 Main Control Unit
              Add:bnameAR6710-L8T3TS1X2-T(668148),       --AR6710-L8T3TS1X2-T Main Control Unit
              Add:bnameRU-5G-101(668149),                --RU-5G-101 Main Control Unit
              Add:fnameAR5710-H8T2TS1(668037),           --AR5710-H8T2TS1 FRAME
              Add:fnameAR5710-H8T2TS1-T(668038),         --AR5710-H8T2TS1-T FRAME
              Add:fnameAR6710-L8T3TS1X2(668039),         --AR6710-L8T3TS1X2 FRAME
              Add:fnameAR6710-L8T3TS1X2-T(668040),       --AR6710-L8T3TS1X2-T FRAME
              Add:fnameRU-5G-101(668041),                --RU-5G-101 FRAME
        "

        REVISION    "202203070000Z"
           DESCRIPTION "V12.46,
              Add:fnameAirEngine9700-H(692401),
              Add:bnameAirEngine9700-H(692401),
              "
         
        REVISION    "202203041500Z"
           DESCRIPTION "V12.47,
              Add: fname8031S200-48T4X(537649), --S200-48T4X (48*10/100/1000BASE-T ports, 4*10GE SFP+ ports, AC power) for V2R21C10
              Add: fname8031S200-48P4X(537650), --S200-48P4X (48*10/100/1000BASE-T ports, 4*10GE SFP+ ports, PoE+, AC power) for V2R21C10
              Add: fname8031S200-32ST4X(537651), --S200-32ST4X (24*GE SFP ports, 8*10/100/1000BASE-T ports, 4*10GE SFP+ ports, AC power, front access) for V2R21C10
              Add: fname8031S200-24T4X-QA2(537652), --S200-24T4X-QA2 (24*10/100/1000BASE-T ports, 4*10GE SFP+ ports, AC power) for V2R21C10
              Add: fname8031S200-24P4X-A2(537653), --S200-24P4X-A2 (24*10/100/1000BASE-T ports, 4*10GE SFP+ ports, PoE+, AC power) for V2R21C10
              Add: bname8031S200-48T4X(537833), --S200-48T4X (48*10/100/1000BASE-T ports, 4*10GE SFP+ ports, AC power) for V2R21C10
              Add: bname8031S200-48P4X(537834), --S200-48P4X (48*10/100/1000BASE-T ports, 4*10GE SFP+ ports, PoE+, AC power) for V2R21C10
              Add: bname8031S200-32ST4X(537835), --S200-32ST4X (24*GE SFP ports, 8*10/100/1000BASE-T ports, 4*10GE SFP+ ports, AC power, front access) for V2R21C10
              Add: bname8031S200-24T4X-QA2(537836), --S200-24T4X-QA2 (24*10/100/1000BASE-T ports, 4*10GE SFP+ ports, AC power) for V2R21C10
              Add: bname8031S200-24P4X-A2(537837), --S200-24P4X-A2 (24*10/100/1000BASE-T ports, 4*10GE SFP+ ports, PoE+, AC power) for V2R21C10
              "

        REVISION    "202203040000Z"
           DESCRIPTION "V12.46,
              Add:bnameLSG7M48VX1E1(713494)
              Add:bnameLSG7M24VX1E1(713495)
              Add:bnameLSG7Y16SX1E0(713496)
              "

	   REVISION    "202203020000Z"
           DESCRIPTION "V12.45, 
		   Add:bnameLSG7SRUEX1C1(713490),  --S8700-6 main control unit E, supporting 1*100G QSFP28, 2*40G QSFP+, 4*25G SFP28, or 8*10G SFP+ ports,Enhanced
		   Add:bnameLSG7SRUEX1T1(713491),  --S8700-6 main control unit E, supporting 1*100G QSFP28, 2*40G QSFP+, 4*25G SFP28, or 8*10G SFP+ ports (TPM),Enhanced
		   Add:bnameLSG7SRUFX1C1(713492),  --S8700-10 main control unit F, supporting 1*100G QSFP28, 2*40G QSFP+, 4*25G SFP28, or 8*10G SFP+ ports,Enhanced
		   Add:bnameLSG7SRUFX1T1(713493),  --S8700-10 main control unit F, supporting 1*100G QSFP28, 2*40G QSFP+, 4*25G SFP28, or 8*10G SFP+ ports (TPM),Enhanced
	       "

	  REVISION    "202202260000Z"
	     DESCRIPTION "V12.44,
			Add: bnamePDC2K2S54-CF(16748775),
			Add: bnameFAN-240SM-B(16748776),
			Add: bnameFAN-480SM-B(16748777).
                         "

		 
	  REVISION    "202202251613Z"
	     DESCRIPTION "V12.43,
			Add: fnameFM5855S48T4S2Q(716818),
			Add: fnameFM6857S48S6CQ(716819),
			Add: bnameFM5855S48T4S2Q(716830),
			Add: bnameFM6857S48S6CQ(716831),
			"

       REVISION    "202202230000Z"
       DESCRIPTION "V12.42,                                      
            Add: bnameV921GPHCE(148756),         -- 4*GPON board of EA5801E-GP04-H1.
            Add: bnameV921MPCDE(148757),         -- control board of EA5801E-GP08-H2.
            Add: bnameV921MPCEE(148758),         -- control board of EA5801E-GP04-H1.
			Add: fnameEA5801EGP04H1(148528),     -- Backplane of the EA5801E-GP04-H1.
            "
       REVISION    "202202220000Z"
       DESCRIPTION "V12.41
            Add: fnameUSG6000E-E03(16716003),   -- Assembling Components,USG6000E-E03-AC,USG6000E-E03-AC,USG6000E-E03 AC Host(2*GE WAN+8*GE Combo+2*10GE SFP+,1 AC power)
            Add: fnameUSG6000E-E07(16716004),   -- Assembling Components,USG6000E-E07-AC,USG6000E-E07-AC,USG6000E-E07 AC Host(2*GE WAN+8*GE Combo+2*10GE SFP+,1 AC power)
            Add: fnameUSG6000E-E10(16716005),   -- Assembling Components,03027SYJ-001,8Gbypass,8Gbypass
            Add: fnameEudemon1000E_C5(16716006),   -- Assembling Components,Eudemon1000E-C5-AC,Eudemon1000E-C5-AC,Eudemon1000E-C5 AC Host(10GE(RJ45),2GE SFP+,2GB Memory,1*USB2.0)
            Add: fnameEudemon1000E_C8(16716007),   -- Assembling Components,03027SYJ-001,8Gbypass,8Gbypass
            Add: fnameAntiDDoS1908-K(16716008),   -- Assembling Components,AntiDDoS1908-K-AC,AntiDDoS1908-K-AC,AntiDDoS1908-K-AC-host(4*QSFP28 + 16*ZSFP+ + 8*SFP+ , 2 AC POWER)
            Add: fnameUSG6710F(16716009),   -- Assembling Components,USG6710F-AC,USG6710F-AC,USG6710F-AC-host(2*QSFP28 + 2*QSFP+ + 8*ZSFP+ + 20*SFP+ , 2 AC POWER)
            Add: fnameUSG6000F-E20(16716010),   -- Assembling Components,USG6685F-AC,USG6685F-AC,USG6685F-AC-host(8*GE COMBO + 4*GE RJ45 + 10*10GE SFP+ , 2AC POWER)
            Add: fnameUSG6000F-E15(16716011),   -- Assembling Components,USG6000F-E20-AC,USG6000F-E20-AC,USG6000F-E20 host(16*GE RJ45 + 12*GE SFP + 4*10GE SFP+ ,1AC POWER)
            Add: fnameUSG6000F-E10(16716012),   -- Assembling Components,USG6000F-E15-AC,USG6000F-E15-AC,USG6000F-E15 AC host(16*GE RJ45 + 12*GE SFP + 4*10GE SFP+ ,1AC POWER)
            Add: fnameUSG6000F-E8(16716013),   -- Assembling Components,USG6000F-E10-AC,USG6000F-E10-AC,USG6000F-E10 AC host(16*GE RJ45 + 12*GE SFP + 4*10GE SFP+ ,1AC POWER)
            Add: fnameUSG6000F-E6(16716014),   -- Assembling Components,USG6000F-E10-AC,USG6000F-E10-AC,USG6000F-E10 AC host(16*GE RJ45 + 12*GE SFP + 4*10GE SFP+ ,1AC POWER)
            Add: fnameUSG6000F-E4(16716015),   -- Assembling Components,USG6000F-E6-AC,USG6000F-E6-AC,USG6000F-E6 AC host(16*GE RJ45 + 12*GE SFP + 4*10GE SFP+ ,1AC POWER)
            Add: fnameUSG6000F-E2(16716016),   -- Assembling Components,USG6000F-E4-AC,USG6000F-E4-AC,USG6000F-E4 AC host(16*GE RJ45 + 12*GE SFP + 4*10GE SFP+ ,1AC POWER)
            Add: fnameUSG6000F-E1(16716017),   -- Assembling Components,USG6000F-E2-AC,USG6000F-E2-AC,USG6000F-E2 AC host(16*GE RJ45 + 12*GE SFP + 4*10GE SFP+ ,1AC POWER)
            Add: fnameProbe1005(16716018),   -- Assembling Components,Probe1005-AC,Probe1005-AC,Probe1005 host(8*GE COMBO + 4*GE RJ45 + 10*10GE SFP+ , 2 AC POWER)
            Add: fnameProbe1010(16716019),   -- Assembling Components,Probe1005-AC,Probe1005-AC,Probe1005 host(8*GE COMBO + 4*GE RJ45 + 10*10GE SFP+ , 2 AC POWER)
            Add: fnameProbe1020(16716020),   -- Assembling Components,Probe1020-AC,Probe1020-AC,Probe1020-AC-host(2*QSFP28 + 2*QSFP+ + 8*ZSFP+ + 20*SFP+ , 2 AC POWER)
            Add: fnameProbe1030(16716021),   -- Assembling Components,Probe1030-AC,Probe1030-AC,Probe1030-AC-host(4*QSFP28 + 16*ZSFP+ + 8*SFP+ , 2 AC POWER)
            Add: bnameAntiDDoS1908-K(16748736),    --FW Assembling Components,AntiDDoS1908-K-AC,AntiDDoS1908-K-AC,AntiDDoS1908-K-AC-host(4*QSFP28 + 16*ZSFP+ + 8*SFP+ , 2 AC POWER)
            Add: bnameUSG6710F(16748737),    --FW Assembling Components,USG6710F-AC,USG6710F-AC,USG6710F-AC-host(2*QSFP28 + 2*QSFP+ + 8*ZSFP+ + 20*SFP+ , 2 AC POWER)
            Add: bnameSRUA-E9KE-F4(16748739),    --FW Eudemon9000E-F4 main control unit A, supporting 1*100G QSFP28, 2*40G QSFP+, 4*25G SFP28, or 8*10G SFP+ ports
            Add: bnameSRUA-E9KE-F4-T(16748740),    --FW Eudemon9000E-F4 main control unit A, supporting 1*100G QSFP28, 2*40G QSFP+, 4*25G SFP28, or 8*10G SFP+ ports (HTM)
            Add: bnameSRUB-E9KE-F8(16748741),    --FW Eudemon9000E-F8 main control unit A, supporting 1*100G QSFP28, 2*40G QSFP+, 4*25G SFP28, or 8*10G SFP+ ports
            Add: bnameSRUB-E9KE-F8-T(16748742),    --FW Eudemon9000E-F8 main control unit A, supporting 1*100G QSFP28, 2*40G QSFP+, 4*25G SFP28, or 8*10G SFP+ ports (HTM)
            Add: bnameSRUA-ADS-F4(16748743),    --FW AntiDDoS12000-F4 main control unit A, supporting 1*100G QSFP28, 2*40G QSFP+, 4*25G SFP28, or 8*10G SFP+ ports
            Add: bnameSRUA-ADS-F4-T(16748744),    --FW AntiDDoS12000-F4 main control unit A, supporting 1*100G QSFP28, 2*40G QSFP+, 4*25G SFP28, or 8*10G SFP+ ports (HTM)
            Add: bnameSRUB-ADS-F8(16748745),    --FW AntiDDoS12000-F8 main control unit A, supporting 1*100G QSFP28, 2*40G QSFP+, 4*25G SFP28, or 8*10G SFP+ ports
            Add: bnameSRUB-ADS-F8-T(16748746),    --FW AntiDDoS12000-F8 main control unit A, supporting 1*100G QSFP28, 2*40G QSFP+, 4*25G SFP28, or 8*10G SFP+ ports (HTM)
            Add: bnameSRUA-IPS-F4(16748747),    --FW IPS12000-F4 main control unit A, supporting 1*100G QSFP28, 2*40G QSFP+, 4*25G SFP28, or 8*10G SFP+ ports
            Add: bnameSRUB-IPS-F8(16748748),    --FW IPS12000-F8 main control unit A, supporting 1*100G QSFP28, 2*40G QSFP+, 4*25G SFP28, or 8*10G SFP+ ports
            Add: bnameSPUF-USG-TP-02(16748749),    --FW USG12000-F Threat Protection Disposal Board-02
            Add: bnameSPUF-USG-TP-01(16748750),    --FW USG12000-F Threat Protection Disposal Board-01
            Add: bnameSPUF-IPS-02(16748751),    --FW IPS12000-F Processing Board-02
            Add: bnameSPUF-IPS-01(16748752),    --FW IPS12000-F Processing Board-01
            Add: bnameLPUA-4DQ(16748753),    --FW USG12000 LPUA-USG-4DQ
            Add: bnameLPUA-E-4DQ(16748754),    --FW Eudemon9000E LPUA-USG-4DQ
            Add: bnameLPUA-12CQ(16748755),    --FW Finished Board Unit,USG12000,LPUA-12CQ,12 Port 100GBase-QSFP28 Interface Card
            Add: bnameMPUC-USG-X4X8(16748756),    --FW USG12000-X4X8 MPUC Main Processing Unit
            Add: bnameMPUC-U-X4X8-T(16748757),    --FW USG12000-X4X8 MPUC Main Processing Unit-HTM
            Add: bnameMPUC-E9KE-X4X8(16748758),    --FW Eudemon9000E-X4X8 Main Processing Unit
            Add: bnameMPUC-E-X4X8-T(16748759),    --FW Eudemon9000E-X4X8 Main Processing Unit-HTM
            Add: bnameMPUC-ADS-X4X8(16748760),    --FW AntiDDoS12000-X4X8 Main Processing Unit
            Add: bnameMPUC-A-X4X8-T(16748761),    --FW AntiDDoS12000-X4X8 Main Processing Unit-HTM
            Add: bnameMPUC-IPS-X4X8(16748762),    --FW IPS12000-X4X8 Main Processing Unit
            Add: bnameUSG6000F-E20(16748763),    --FW Assembling Components,USG6685F-AC,USG6685F-AC,USG6685F-AC-host(8*GE COMBO + 4*GE RJ45 + 10*10GE SFP+ , 2AC POWER)
            Add: bnameUSG6000F-E15(16748764),    --FW Assembling Components,USG6000F-E20-AC,USG6000F-E20-AC,USG6000F-E20 host(16*GE RJ45 + 12*GE SFP + 4*10GE SFP+ ,1AC POWER)
            Add: bnameUSG6000F-E10(16748765),    --FW Assembling Components,USG6000F-E15-AC,USG6000F-E15-AC,USG6000F-E15 AC host(16*GE RJ45 + 12*GE SFP + 4*10GE SFP+ ,1AC POWER)
            Add: bnameUSG6000F-E8(16748766),    --FW Assembling Components,USG6000F-E10-AC,USG6000F-E10-AC,USG6000F-E10 AC host(16*GE RJ45 + 12*GE SFP + 4*10GE SFP+ ,1AC POWER)
            Add: bnameUSG6000F-E6(16748767),    --FW Assembling Components,USG6000F-E10-AC,USG6000F-E10-AC,USG6000F-E10 AC host(16*GE RJ45 + 12*GE SFP + 4*10GE SFP+ ,1AC POWER)
            Add: bnameUSG6000F-E4(16748768),    --FW Assembling Components,USG6000F-E6-AC,USG6000F-E6-AC,USG6000F-E6 AC host(16*GE RJ45 + 12*GE SFP + 4*10GE SFP+ ,1AC POWER)
            Add: bnameUSG6000F-E2(16748769),    --FW Assembling Components,USG6000F-E4-AC,USG6000F-E4-AC,USG6000F-E4 AC host(16*GE RJ45 + 12*GE SFP + 4*10GE SFP+ ,1AC POWER)
            Add: bnameUSG6000F-E1(16748770),    --FW Assembling Components,USG6000F-E2-AC,USG6000F-E2-AC,USG6000F-E2 AC host(16*GE RJ45 + 12*GE SFP + 4*10GE SFP+ ,1AC POWER)
            Add: bnameProbe1005(16748771),    --FW Assembling Components,Probe1005-AC,Probe1005-AC,Probe1005 host(8*GE COMBO + 4*GE RJ45 + 10*10GE SFP+ , 2 AC POWER)
            Add: bnameProbe1010(16748772),    --FW Assembling Components,Probe1010-AC,Probe1010-AC,Probe1010 host(8*GE COMBO + 4*GE RJ45 + 10*10GE SFP+ , 2 AC POWER)
            Add: bnameProbe1020(16748773),    --FW Assembling Components,Probe1020-AC,Probe1020-AC,Probe1020-AC-host(2*QSFP28 + 2*QSFP+ + 8*ZSFP+ + 20*SFP+ , 2 AC POWER)
            Add: bnameProbe1030(16748774),    --FW Assembling Components,Probe1030-AC,Probe1030-AC,Probe1030-AC-host(4*QSFP28 + 16*ZSFP+ + 8*SFP+ , 2 AC POWER)
           "



		REVISION    "202202180000Z"
        DESCRIPTION "V12.40
            Add: subbname8090DEVIG2D00LFXF74(275412),   -- 24-Port 10GBase LAN/WAN-SFP+ Flexible Card A(P480-A)
            Add: subbname8090DEVIG2D00E2NF70(275413),   -- 2-Port 100GBase-QSFP28 Flexible Card A(P480-A)
            Add: subbname8090DEVCR57LBXFG2(774067),   -- 12-Port 10GBase LAN/WAN-SFP+ Fixed Card
            Add: subbname8090DEVME0M0LEXFB75(774068),   -- 20-Port 10GBase LAN/WAN-SFP+ Flexible Card(BP485-E)
            Add: subbname8090DEVME0M0E2NFB74(774069),   -- 2-Port 50GBase/2-Port 100GBase-QSFP28 Flexible Card(BP485-E)
	    Add: subbname8090DEVCR57LAXECG0(774070),   -- 10-Port GE-SFP/10GE-SFP+ and 14-Port GE-SFP Fixed Card
	    Add: subbname8090DEVCR8D00E1NBC4(225912),      --1-Port 100GBase-QSFP28 Physical Interface Card(PIC)
            "
		
		REVISION    "202202170000Z"
        DESCRIPTION "V12.39
            Add: fnameCE6860ZQ(688245),     -- CE V3R22C00 added
            Add: fnameCE8850ZQ(688246),     -- CE V3R22C00 added
            Add: bnameCE6860ZQ(688478),     -- CE V3R22C00 added
            Add: bnameCE8850ZQ(688479),     -- CE V3R22C00 added
            "
		
		REVISION    "202202150000Z"
        DESCRIPTION "V12.37
            MODIFY: bnameSRUA-GX-F4,        -- bnameSRUA-USG-F4
            MODIFY: bnameSRUA-GX-F4-T,        -- bnameSRUA-USG-F4-T
            MODIFY: bnameSRUA-GX-F8,        -- bnameSRUA-USG-F8
            MODIFY: bnameSRUA-GX-F8-T,        -- bnameSRUA-USG-F8-T
            MODIFY: fnameUSG12004F,    -- fnameUSG12004-F
            MODIFY: fnameAntiDDoS12004F,    -- fnameAntiDDoS12004-F
            MODIFY: fnameIPS12004F,    --fnameIPS12004-F
            MODIFY: fnameUSG12008F,    -- fnameUSG12008-F
            MODIFY: fnameAntiDDoS12008F,    -- fnameAntiDDoS12008-F
            MODIFY: fnameIPS12008F,    --fnameIPS12008-F
            "
			
        REVISION    "202202140000Z"
        DESCRIPTION "V12.37
            Add: fnameNETENGINE-8100-M8(688890),        -- NETENGINE-8100-M8 (fnameNETENGINE-8100-M8)
            Add: fnameNETENGINE-8100-M8-AC(688892),     -- NETENGINE-8100-M8-AC (fnameNETENGINE-8100-M8-AC)
            Add: fnameNETENGINE-8100-M8-DC(688891),     -- NETENGINE-8100-M8-DC (fnameNETENGINE-8100-M8-DC)
            Add: fnameNETENGINE-8100-M14(688893),       -- NETENGINE-8100-M14 (fnameNETENGINE-8100-M14)
            Add: fnameNETENGINE-8100-M14-4AC(688894),    -- NETENGINE-8100-M14-4AC (fnameNETENGINE-8100-M14-4AC)
            Add: fnameNETENGINE-8100-M14-DC(688895),    -- NETENGINE-8100-M14-DC (fnameNETENGINE-8100-M14-DC)
            Add: virent8090DEVCR8DIPU1T212(800101),    --V8R21C00 CR8DIPU1T212(SBOM) Integrated Network Processing Unit (IPUA-1T2)
            Add: virent8090DEVCR8DIPU1T211(800102),    --V8R21C00 CR8DIPU1T211(SBOM) Integrated Network Processing Unit (IPUA-1T2)
            "

		REVISION    "202202110000Z"
        DESCRIPTION "V12.36,
            Add: virent8090DEVCR8PM1ABAS3(688485),     --V8R21C00 CR8PM1ABAS3(SBOM) NetEngine 8000 M1A, DC Power,Port Capacity 16*10GE+12*GE(o)+4*GE(e)
			Add: virentTPXM01HSTA00(229533),           -- V8R22C00 for TPXM01HSTA00(SBOM) PTN 91A-F DC Power,with 3*10G/GE/FE(o),7*GE/FE(o),4*GE/FE(e)
            "

	REVISION    "202202070000Z"
        DESCRIPTION "V12.35,
            Add: bnameH835XPUB(156104),   -- Master board of MA582xS
            "

		REVISION    "202201270000Z"
        DESCRIPTION "V12.34,
            Add: bnameH905MPLB(148761),         -- control board of MA5800.
            Add: bnameH905GPHF(156027),         -- 16 GPON board of MA5800.
            Add: bnameH905XEHD(156029),         -- 8*XG EPON board of MA5800.
            "

        REVISION    "202201220000Z"
        DESCRIPTION "V12.33
            Add: virent8090DEVCR5DMPUX8674(782504),   -- V8R21C10 for CR5DMPUX8674(SBOM) Main Processing Unit B112(32G Memory)
            Add: virent8090DEVCX6DMPUX8673(908549),   -- V8R21C10 for CX6DMPUX8673(SBOM) Main Processing Unit B112(32G Memory)
            Add: virent8090DEVCX6DMPUX8614(602552),   -- V8R21C10 for CX6DMPUX8614(SBOM) Main Processing Unit B112A(32G Memory)
            Add: virent8090DEVTNRDMPUX8673(429158),   -- V8R21C10 for TNRDMPUX8673(SBOM) Main Processing Unit B112(32G Memory)
            Add: virent8090DEVME0DMPUX8674(640056),   -- V8R21C10 for ME0DMPUX8674(SBOM) Main Processing Unit B112(32G Memory)
            Add: virent8090DEVME0DMPUX8675(898252),   -- V8R21C10 for ME0DMPUX8675(SBOM) Main Processing Unit B112A(32G Memory)
            "

        REVISION    "202201210000Z"
        DESCRIPTION "V12.32
            Add: virent600DEVCR5D0IPU2TC1(688478),    --V8R12C00 NE40E-X2-M14 CR5D0IPU2TC1(SBOM), M14
            Add: virent600DEVCR5D0IPU2TC2(688479),    --V8R12C00 NE40E-X2-M14 CR5D0IPU2TC2(SBOM), M14
            Add: virent600DEVCR5DIPU1T2C3(688480),    --V8R12C00 NE40E-X2-M14 CR5DIPU1T2C3(SBOM), M14
            Add: virent600DEVCR5DIPU1T2C4(688481),    --V8R12C00 NE40E-X2-M14 CR5DIPU1T2C4(SBOM), M14
            Add: virent600DEVTNRD0IPU2TC1(688482),    --V8R12C00 PTN6900-2-M14 TNRD0IPU2TC1(SBOM), M14
            Add: virent600DEVTNRDIPU1T2C3(688483),    --V8R12C00 PTN6900-2-M14 TNRDIPU1T2C3(SBOM), M14
            Add: virent8090DEVCR5D0SRUAK70(689003),   -- V8R21C10 for CR5D0SRUAK70(SBOM) Switch and Route Processing Unit A112(SRUA-2T-F, 32G Memory)
            Add: virent8090DEVCR5D0SRUAK71(689004),   -- V8R21C10 for CR5D0SRUAK71(SBOM) Switch and Route Processing Unit A112A(SRUA-2TA-F, 32G Memory)
            Add: virent8090DEVCX6D0SRUAK70(689005),   -- V8R21C10 for CX6D0SRUAK70(SBOM) Switch and Route Processing Unit A112(SRUA-2T-F, 32G Memory)
            Add: virent8090DEVTNRD0SRUAK70(689006),   -- V8R21C10 for TNRD0SRUAK70(SBOM) Switch and Route Processing Unit A112(SRUA-2T-F, 32G Memory)
            Add: virent8090DEVIG2D0SRUAK71(689007),   -- V8R21C10 for IG2D0SRUAK71(SBOM) Switch and Route Processing Unit A112A(SRUA-2TA-F, 32G Memory)
            "

		REVISION "202201180000Z" 
        DESCRIPTION "V13.31			
			Add: bnameCE6881H48T6CQ(688460),			  -- CE V3R22C00,CloudEngine 6800,CE6881H-48T6CQ
			Add: bnameCE6881H48T6CQK(688461),			  -- CE V3R22C00,CloudEngine 6800,CE6881H-48T6CQ-K
			Add: bnameCE6820H48S6CQK(688462),			  -- CE V3R22C00,CloudEngine 6800,CE6820H-48S6CQ-K
			Add: bnameCE6881H48S6CQK(688463),			  -- CE V3R22C00,CloudEngine 6800,CE6881H-48S6CQ-K
			Add: bnameCE6863H48S6CQK(688464),			  -- CE V3R22C00,CloudEngine 6800,CE6863H-48S6CQ-K
			Add: bnameCE6820S48S6CQ(688465),			  -- CE V3R22C00,CloudEngine 6800,CE6820S-48S6CQ					    
			Add: fnameCE6881H48T6CQ(688229),			  -- CE V3R22C00,CloudEngine 6800,CE6881H-48T6CQ
			Add: fnameCE6881H48T6CQK(688230),			  -- CE V3R22C00,CloudEngine 6800,CE6881H-48T6CQ-K
			Add: fnameCE6820H48S6CQK(688231),			  -- CE V3R22C00,CloudEngine 6800,CE6820H-48S6CQ-K
			Add: fnameCE6881H48S6CQK(688232),			  -- CE V3R22C00,CloudEngine 6800,CE6881H-48S6CQ-K
			Add: fnameCE6863H48S6CQK(688233),			  -- CE V3R22C00,CloudEngine 6800,CE6863H-48S6CQ-K
			Add: fnameCE6820S48S6CQ(688234),			  -- CE V3R22C00,CloudEngine 6800,CE6820S-48S6CQ			
		    Add: bnameCEMPUDHALF3E(688466),               -- CE V3R22C00,CloudEngine Finished Board Unit
            Add: bnameCEMPUDFULL3E(688467),               -- CE V3R22C00,CloudEngine Finished Board Unit
            Add: bnameCESFU16DH1E(688468),                -- CE V3R22C00,CloudEngine Finished Board Unit
            Add: bnameCESFU16DL1E(688469),                -- CE V3R22C00,CloudEngine Finished Board Unit
            Add: bnameCESFU08DH1E(688470),                -- CE V3R22C00,CloudEngine Finished Board Unit
            Add: bnameCESFU08DL1E(688471),                -- CE V3R22C00,CloudEngine Finished Board Unit
            Add: bnameCESFU04DH1E(688472),                -- CE V3R22C00,CloudEngine Finished Board Unit
            Add: bnameCESFU04DL1E(688473),                -- CE V3R22C00,CloudEngine Finished Board Unit
            Add: bnameCESFU04DL1EK(688474),               -- CE V3R22C00,CloudEngine Finished Board Unit
			Add: bnameCESFU04DH1EK(688475),               -- CE V3R22C00,CloudEngine Finished Board Unit
			Add: bnameCESFU08DL1EK(688476),               -- CE V3R22C00,CloudEngine Finished Board Unit
			Add: bnameCESFU08DH1EK(688477),               -- CE V3R22C00,CloudEngine Finished Board Unit
		    "

        REVISION    "202201140001Z"
        DESCRIPTION "V12.30
            Add: fnameHG-FM-CPE-03-AC(229524), -- V8R22C00 for HG-FM-CPE-03 chassis
            Add: fnameNETENGINE-A850-M-AC(229525), -- V8R22C00 for NETENGINE-A850-M-AC chassis
            Add: fnameHG-FM-CPE-01-AC(229526), -- V8R22C00 for HG-FM-CPE-01-AC chassis
            Add: fnameNETENGINE-A813-M-AC(229527), -- V8R22C00 for NETENGINE-A813-M-AC chassis
            Add: fnamePTN91A-F-AC(229528), -- V8R22C00 for PTN91A-F-AC chassis
            Add: virentCP8PHST1MA02(229523), -- V8R21C00 for CP8PHST1MA02(SBOM) NetEngine A810 M AC System (10*GE/FE(o), 8*GE/FE(e))
            Add: virentHGFM0HOSTC00(229529), -- V8R22C00 for HGFM0HOSTC00(SBOM) HG-FM CPE-03 AC Power,with 2*10GE Fine Granularity Unit(o),4*10GE/GE/FE(o),4*GE/FE(o),8*GE/FE(e)
            Add: virentCP8PHST5MA01(229530), -- V8R22C00 for CP8PHST5MA01(SBOM) NetEngine A850 M AC System (4*GE/FE(o)+2*GE(o)+8*GE/FE(e)+5G(dual SIM))
            Add: virentHGFM0HOSTA00(229531), -- V8R22C00 for HGFM0HOSTA00(SBOM) HG-FM CPE-01 AC Power,with 5G module ,6*GE/FE(o),8*GE/FE(e)
            Add: virentCP8PHST1MA04(229532), -- V8R22C00 for CP8PHST1MA04(SBOM) NetEngine A813 M AC System (6*GE/FE(o)+8*GE/FE(e))
            "

        REVISION    "202201120001Z"
        DESCRIPTION "V12.29
            Add: bnamePTN7900TPA1FGU(229648),    --TPA1FGU, Fine Granularity Unit Functional Board
			"

        REVISION    "202201120000Z"
        DESCRIPTION "V12.28
            Add:subbname8090DEVANND001EN114(226001),      --1 Channel 100G Base QSFP28 High Speed Interface Board
            Add:virent8090DEVCR8D0IPU2TC5(285692),   -- V8R21C10 for CR8D0IPU2TC5(SBOM) Integrated Network Processing Unit (IPU-2T-C)
            Add:virent8090DEVCR8D0IPU2TC6(867257),   -- V8R21C10 for CR8D0IPU2TC6(SBOM) Integrated Network Processing Unit (IPUA-2T-C)
            Add:virent8090DEVTNRD0IPU2TC3(469452),   -- V8R21C10 for TNRD0IPU2TC3(SBOM) Integrated Network Processing Unit (IPU-2T-C)
            Add:virent8090DEVCR5D0IPU2TC5(983150),   -- V8R21C10 for CR5D0IPU2TC5(SBOM) Integrated Network Processing Unit (IPU-2T-C)
            Add:virent8090DEVCR8D0IPU2TE1(634699),   -- V8R21C10 for CR8D0IPU2TE1(SBOM) Integrated Network Processing Unit (IPUA-2T-C)
            "

        REVISION    "202201120000Z"
        DESCRIPTION "V12.27
            Add:virentCP8PHST10A06(229524),    -- V8R21C10 for CP8PHST10A06(SBOM) NetEngine A811 AC System (10*GE/FE(o)+8*GE/FE(e))
            Add:virent8090DEVCP8PHST20A04(525129),    -- V8R21C10 for CP8PHST20A04(SBOM) NetEngine A821, CP8PHST20A04, NetEngine A821 AC System (2*10GE/GE/FE+8*GE/FE(o)+8*GE/FE(e))
            "

	REVISION "202201110000Z" 
        DESCRIPTION "V12.26
	    Add: fnameAirEngine5761-11EI(692399),            -- WLAN R22C00 New AP
	    Add: fnameAirEngine5762-16W(692400),            -- WLAN R22C00 New AP
	    Add: bnameAirEngine5761-11EI(692399),            -- WLAN R22C00 New AP
	    Add: bnameAirEngine5762-16W(692400),            -- WLAN R22C00 New AP
	    "

		REVISION "202201100000Z" 
        DESCRIPTION "V12.25		
			Add: bnameCE687048S6CQEIA(688459),            -- CE V2R22C00,CloudEngine 6800,CE6870-48S6CQ-EI-A
		    Add: fnameCE687048S6CQEIA(688228),            -- CE V2R22C00,CloudEngine 6800,CE6870-48S6CQ-EI-A
            Add: bnameFM8850E32CQEI(716829),              -- FM V2R22C00 FM6800,FM8850E-32CQ-EI
			Add: fnameFM8850E32CQEI(716817),              -- FM V2R22C00 FM6800,FM8850E-32CQ-EI
		    "
		
        REVISION    "202201050000Z"
        DESCRIPTION "V12.24
            Add:virent8090DEVCR8DIPU1T2CE(549612),   -- V8R21C10 for CR8DIPU1T2CE(SBOM) Integrated Network Processing Unit (IPU-1T2-CN)
            Add:virent8090DEVTNRDIPU1T2C6(256325),   -- V8R21C10 for TNRDIPU1T2C6(SBOM) Integrated Network Processing Unit (IPU-1T2-CN)
            Add:virent8090DEVCR5DIPU1T2CB(412532),   -- V8R21C10 for CR5DIPU1T2CB(SBOM) Integrated Network Processing Unit (IPU-1T2-CN)
            Add:virent8090DEVCX6DISUFM311(178864),   -- V8R21C10 for CX6DISUFM311(SBOM) Flexible Card Line Processing Unit(ISUF-483B)
			Add:virent8090DEVME0D0LFXFB71(333415),   -- V8R21C10 for ME0D0LFXFB71(SBOM) 24-Port 10GBase LAN/WAN-SFP+ Broadband Service Unit Integrated(BSUI-245A)
			Add:virent8090DEVME0D0LFXFA71(368093),   -- V8R21C10 for ME0D0LFXFA71(SBOM) 24-Port 10GBase LAN/WAN-SFP+ Multi Service Unit Integrated(MSUI-245A)
			"		 
		 
        REVISION    "202112291000Z"
        DESCRIPTION "V12.23
            Add:virent8090DEVCR5DSFUIT351(562188),    -- V8R21C10 for CR5DSFUIT351(SBOM) NE5000E CCC-A 3.2T Cluster Central Switch Fabric Unit (SFUI-3T2-C2)
            Add:virent8090DEVCR5DSFUIT363(562189),    -- V8R21C10 for CR5DSFUIT363(SBOM) NE5000E-20 3.2T CLC Integrated Switch Fabric Unit for Multi-Chassis (SFUI-3T2-M2)
            "


        REVISION    "202112290000Z"
        DESCRIPTION "V12.22
            Add:virent600DEVCR8DIPU1T2CG(326481),    --V8R21C10 NetEngine-8000-M8 CR8DIPU1T2CG(SBOM), M8
            Add:virent600DEVCR8DIPU1T2CH(326417),    --V8R21C10 NetEngine-8000-M8 CR8DIPU1T2CH(SBOM), M8
            Add:virent600DEVCR8DIPU480C7(326102),    --V8R21C10 NetEngine-8000-M8 CR8DIPU480C7(SBOM), M8
            Add:virent600DEVTNRDIPU1T2C7(426587),    --V8R21C10 PTN6900-2-M8C TNRDIPU1T2C7(SBOM), M8
            Add:virent600DEVTNRDIPU480C3(426512),    --V8R21C10 PTN6900-2-M8C TNRDIPU480C3(SBOM), M8
            "

		REVISION    "202112250000Z"
        DESCRIPTION "V12.21
            Add:virent8090DEVCR5DVSUIK07D(962214),   -- V8R21C10 for CR5DVSUIK07D(SBOM) Integrated Service Unit 401(VSUI-401A-E)
            Add:virent8090DEVCR5DVSUIK07C(580249),   -- V8R21C10 for CR5DVSUIK07C(SBOM) Integrated Service Unit 401(VSUI-401-E)
            Add:virent8090DEVCR5DVSUIK07B(509102),   -- V8R21C10 for CR5DVSUIK07B(SBOM) Integrated Service Unit 401(VSUI-401A)
            Add:virent8090DEVCR5DVSUIK07A(927310),   -- V8R21C10 for CR5DVSUIK07A(SBOM) Integrated Service Unit 401(VSUI-401)
            Add:virent8090DEVME0DVSUIK07A(117254),   -- V8R21C10 for ME0DVSUIK07A(SBOM) Integrated Service Unit 401(VSUI-401A)
            Add:virent8090DEVIG2D00SPUG0C(125719),   -- V8R21C10 for IG2D00SPUG0C(SBOM) High Performance X8A&X16A Service Processing Unit-SPUGA-S,with HW Service Inspection Gateway Software
            Add:virent8090DEVIG2D00SPUG0D(176245),   -- V8R21C10 for IG2D00SPUG0D(SBOM) High Performance X8A&X16A Enhanced Service Processing Unit-SPUGEA-S,with HW Service Inspection Gateway Software
            Add:virent600DEVCR8P0BKP03C2(688900),    -- V8R21C10 for CR8P0BKP03C2(SBOM) Integration Processing Unit
            Add:virent600DEVCR8P0BKP03C3(688901),    -- V8R21C10 for CR8P0BKP03C3(SBOM) Integration Processing Unit
            Add:virent8090DEVCR9D0SFUT480(570049),   -- V8R21C10 for CR9D0SFUT480(SBOM) NE9000-20 Switch Fabric Unit for Single Chassis(SFU4T-B)
            Add:virent8090DEVCR9D0SFUT280(564907),   -- V8R21C10 for CR9D0SFUT280(SBOM) NE9000-8 Switch Fabric Unit for Single Chassis(SFU2T-A)
            "
		
        REVISION    "202112110000Z"
        DESCRIPTION "V12.20
            Modify: bnameLPUF-U-2CQ-24XS    (16748719),    --00FF90AF to bnameLPUF-U-2CQ-12XS    (16748719),    --00FF90AF
           Modify: bnameLPUF-E-2CQ-24XS    (16748720),    --00FF90B0  tobnameLPUF-E-2CQ-12XS    (16748720),    --00FF90B0
           Modify: bnameLPUF-I-2CQ-24XS    (16748721),    --00FF90B1 to bnameLPUF-I-2CQ-12XS    (16748721),    --00FF90B1
            "

        REVISION    "202112080000Z"
        DESCRIPTION "V12.19
            Add: bnamePDC2K2S54-DF(713488),    --2200W DC Power Module(Front to Back, Power panel side intake) for V600R021C10
            Add: bnamePAC3KS54-DF(713489),    --2500W/3000W AC&240VDC Power Module (Front to Back, Power panel side intake) for V600R021C0
            Delete: subnamePDC2K2S54-DF(536823),    --2200W DC Power Module(Front to Back, Power panel side intake) for V600R021C10
            Delete: subnamePAC3KS54-DF(536824),    --2500W/3000W AC&240VDC Power Module (Front to Back, Power panel side intake) for V600R021C0
            "
    
        REVISION    "202112061000Z"
        DESCRIPTION "V12.18
            Add:subbname8090DEVANND001EV105(225999),    --1 Channel 50G Base QSFP28 High Speed Interface Board
            Add:subbname8090DEVANND001EV106(226000),    --1 Channel 50G Base QSFP28 High Speed Interface Board
            Add:virent8090DEVCR8DIPU480C8(107344),      -- V8R21C10 for CR8DIPU480C8(SBOM) Integrated Network Processing Unit (IPUA-480-BN)
            Add:virent8090DEVCR8DIPU800CJ(203627),      -- V8R21C10 for CR8DIPU800CJ(SBOM) Integrated Network Processing Unit (IPUA-800-BN)
            "
        
        REVISION    "202112060000Z"
        DESCRIPTION "V12.17
            Modify: virent8090DEVCR5DLPUFME74(759171),   -- V8R21C10 for CR5DLPUFME74(SBOM) Flexible Card Line Processing Unit E(LPUF-485A-E)
            "
        
        REVISION    "202112021700Z"
        DESCRIPTION "V12.16
            Add: fnameAirEngine5761-10W(692375),          -- WLAN R21C00 New AP
            Add: fnameAirEngine5761-10WD(692376),         -- WLAN R21C00 New AP
            Add: fnameAirEngine5761S-10W(692377),         -- WLAN R21C00 New AP
            Add: fnameAP5761S-10(692378),                 -- WLAN R21C00 New AP
            Add: fnameAP5761S-10W(692379),                -- WLAN R21C00 New AP
            Add: fnameAirEngine5762-12SW(692380),         -- WLAN R21C01 New AP
            Add: fnameAirEngine5762S-12SW(692381),        -- WLAN R21C01 New AP
            Add: fnameAirEngine5762-12(692383),           -- WLAN R21C01 New AP
            Add: fnameAirEngine5762S-12(692384),          -- WLAN R21C01 New AP
            Add: fnameAirEngine5762S-11(692385),          -- WLAN R21C01 New AP
            Add: fnameAirEngine5762-15HW(692386),         -- WLAN R21C01 New AP
            Add: fnameAirEngine5762-13W(692387),          -- WLAN R21C01 New AP
            Add: fnameAirEngine5762S-13W(692388),         -- WLAN R21C01 New AP
            Add: fnameAirEngine5762S-11SW(692389),        -- WLAN R21C01 New AP
            Add: fnameAP163(692390),                      -- WLAN R21C01 New AP
            Add: fnameAP165(692391),                      -- WLAN R21C01 New AP
            Add: fnameAP263(692392),                      -- WLAN R21C01 New AP
            Add: fnameAP363(692393),                      -- WLAN R21C01 New AP
            Add: fnameAP365(692394),                      -- WLAN R21C01 New AP
            Add: fnameAP9700D-M1(692395),                 -- WLAN R21C00 New AP
            Add: fnameAirEngine6761-22T(692396),          -- WLAN R21C10 New AP
            Add: fnameAirEngine5761-12(692397),           -- WLAN R21C10 New AP
            Add: fnameAirEngine9700-S(692398),            -- WLAN Yunshan R21C10 New AC
            Add: bnameAirEngine5761-10W(692375),          -- WLAN R21C00 New AP
            Add: bnameAirEngine5761-10WD(692376),         -- WLAN R21C00 New AP
            Add: bnameAirEngine5761S-10W(692377),         -- WLAN R21C00 New AP
            Add: bnameAP5761S-10(692378),                 -- WLAN R21C00 New AP
            Add: bnameAP5761S-10W(692379),                -- WLAN R21C00 New AP
            Add: bnameAirEngine5762-12SW(692380),         -- WLAN R21C01 New AP
            Add: bnameAirEngine5762S-12SW(692381),        -- WLAN R21C01 New AP
            Add: bnameAirEngine5762-12(692383),           -- WLAN R21C01 New AP
            Add: bnameAirEngine5762S-12(692384),          -- WLAN R21C01 New AP
            Add: bnameAirEngine5762S-11(692385),          -- WLAN R21C01 New AP
            Add: bnameAirEngine5762-15HW(692386),         -- WLAN R21C01 New AP
            Add: bnameAirEngine5762-13W(692387),          -- WLAN R21C01 New AP
            Add: bnameAirEngine5762S-13W(692388),         -- WLAN R21C01 New AP
            Add: bnameAirEngine5762S-11SW(692389),        -- WLAN R21C01 New AP
            Add: bnameAP163(692390),                      -- WLAN R21C01 New AP
            Add: bnameAP165(692391),                      -- WLAN R21C01 New AP
            Add: bnameAP263(692392),                      -- WLAN R21C01 New AP
            Add: bnameAP363(692393),                      -- WLAN R21C01 New AP
            Add: bnameAP365(692394),                      -- WLAN R21C01 New AP
            Add: bnameAP9700D-M1(692395),                 -- WLAN R21C00 New AP
            Add: bnameAirEngine6761-22T(692396),          -- WLAN R21C10 New AP
            Add: bnameAirEngine5761-12(692397),           -- WLAN R21C10 New AP
            Add: bnameAirEngine9700-S(692398),            -- WLAN Yunshan R21C10 New AC
            "

        REVISION    "202111271100Z"
        DESCRIPTION "V12.15
            Add: bnameSIC-1LTE4-CN(668143),            --SIC-1LTE4-CN Lpu Control Unit
            Add: bnameSIC-1LTE4-EA(668144),            --SIC-1LTE4-EA Lpu Control Unit
            "
            
        REVISION    "202111270000Z"
        DESCRIPTION "V12.14
            Modify: virent8090DEVCR8D0MPUA8C5(932387),    -- V1R21C10 for CR8D0MPUA8C5(SBOM) NetEngine 8100 Main Processing Unit A8A(MPUA8A)
            Modify:virent8090DEVCR8D0MPUA5C5(688557),     -- V8R13C00 for CR8D0MPUA5C5(SBOM) NetEngine 8100 Main Processing Unit A5A(MPUA5A)
            "
        
        REVISION    "202111230000Z"
        DESCRIPTION "V12.13
            Add: fnameEA5801SGP16H1(148525),        --  Backplane of the EA5801S-GP16-H1.
            Add: bnameV931MPBBE(148746),            --  control board of EA5801S-GP16-H1.
            Add: bnameV931GPHFE(148747),            --  16*GPON board of EA5801-GP16-H1.
            Add: bnameH901CGPD(148748),             --  8*XG combo board of MA5800.
            Add: bnameH901FGHFE(148749),            --  16*XG/G GPON combo board of EA5800.
            Add: bnameH907CGHF(156024),             --  16*XG/G GPON combo board of MA5800.
            Add: bnameH907CGUF(156025),             --  16*XG/G GPON combo board of MA5800.
            "

        REVISION "202111180000Z" 
        DESCRIPTION "V12.12
            Add: virent8090DEVCR5DLPUFM378(914342),   -- V8R21C10 for CR5DLPUFM378(SBOM) Flexible Card Line Processing Unit(LPUF-485-CM, enable slot 0 by default)
        "
        
        REVISION    "202111170000Z"
        DESCRIPTION "V12.11
            Modify: bnameLSG7X48PX1E0(713487),  --48-port 10GBASE-X interface Optical/electrical composite line card (SFP+)->48-port 100M/1G/10GBASE-X  PoE++ interface card (SFP+,PoE++)
            "

        REVISION    "202111160000Z"
        DESCRIPTION "V12.10
            Add: subnamePAC600S12-EB(536820),    --600W AC Power Module(Back to Front, Power panel side exhaust) for V600R021C10
            Add: subnameFAN-240SM-B(536821),    --single-layer fan module with two fans for V600R021C10
            Add: subnameFAN-480SM-B(536822),    --single-layer fan module with four fans for V600R021C10
            Add: subnamePDC2K2S54-DF(536823),    --2200W DC Power Module(Front to Back, Power panel side intake) for V600R021C10
            Add: subnamePAC3KS54-DF(536824),    --2500W/3000W AC&240VDC Power Module (Front to Back, Power panel side intake) for V600R021C0
            "

        REVISION    "202111151100Z"
        DESCRIPTION "V12.09,
          Add: subbname8090DEVCX6D0E2NBA12(983715),   -- 2-Port 100GBase-QSFP28 Flexible Card A(S480-A)
          Add: subbname8090DEVME0M0E2NFB72(700917),   -- 2-Port 100GBase-QSFP28 Flexible Card H(BP400-H)
          Add: subbname8090DEVME0M0E2NFB73(975301),   -- 2-Port 50GBase/2-Port 100GBase-QSFP28 Flexible Card(BP485)
          Add: subbname8090DEVCR57E1NBG2(704702),   -- 1-Port 100GBase-QSFP28 Fixed Card
          Add: subbname8090DEVCR57LBXFL1(644732),   -- 12-port 10GBase LAN/WAN-SFP+ Fixed Card
          Add: subbname8090DEVCR57LFXFM0(774065),   -- 24-Port 10GBase LAN/WAN-SFP+ Fixed Card
          Add: subbname8090DEVCR57E2NBE1(275411),   -- 2-Port 100GBase-QSFP28 Fixed Card A
          "

        REVISION    "202111151100Z"
        DESCRIPTION "V12.08,
		  Add:fname8031S5731-S24T4X(537307), --S5731-S24T4X (24*10/100/1000BASE-T ports, 4*10GE SFP+ ports, without power module)for v2r21c10
		  Add:fname8031S5731S-S24T4X-A(537308), --S5731S-S24T4X Bundle (24*10/100/1000BASE-T ports, 4*10GE SFP+ ports, 1*AC power)for v2r21c10
		  Add:fname8031S5731-S24P4X(537310), --S5731-S24P4X (24*10/100/1000BASE-T ports, 4*10GE SFP+ ports, PoE+, without power module)for v2r21c10
		  Add:fname8031S5731S-S24P4X-A(537311), --S5731S-S24P4X  Bundle(48*10/100/1000BASE-T ports, 4*10GE SFP+ ports, PoE+, 1*AC power)for v2r21c10
		  Add:fname8031S5731-S48P4X(537316), --S5731-S48P4X (48*10/100/1000BASE-T ports, 4*10GE SFP+ ports, PoE+, without power module)for v2r21c10
		  Add:fname8031S5731S-S48P4X-A(537317), --S5731S-S48P4X Bundle(48*10/100/1000BASE-T ports, 4*10GE SFP+ ports, PoE+, 1*AC power)for v2r21c10
		  Add:fname8031S5331-S48T4X(537634), --S5331-S48T4X (48*10/100/1000BASE-T ports, 4*10GE SFP+ ports, without power module)for v2r21c10
		  Add:fname8031S5331-S24T4X(537637), --S5331-S24T4X (24*10/100/1000BASE-T ports, 4*10GE SFP+ ports, without power module)for v2r21c10
		  Add:fname8031S5731-S48T4X-A(537638), --S5731-S48T4X-A (48*10/100/1000BASE-T ports, 4*10GE SFP+ ports, AC power)for v2r21c10
		  Add:fname8031S5731S-S48T4X-A1(537639), --S5731S-S48T4X-A1 (48*10/100/1000BASE-T ports, 4*10GE SFP+ ports, AC power)for v2r21c10
		  Add:fname8031S5331-S48T4X-A(537640), --S5331-S48T4X-A (48*10/100/1000BASE-T ports, 4*10GE SFP+ ports, AC power)for v2r21c10
		  Add:fname8031S5731-S24T4X-A(537641), --S5731-S24T4X-A (24*10/100/1000BASE-T ports, 4*10GE SFP+ ports, AC power)for v2r21c10
		  Add:fname8031S5731S-S24T4X-A1(537642), --S5731S-S24T4X-A1 (24*10/100/1000BASE-T ports, 4*10GE SFP+ ports, AC power)for v2r21c10
		  Add:fname8031S5731-S24T4X-D(537643), --S5731-S24T4X-D (24*10/100/1000BASE-T ports, 4*10GE SFP+ ports, DC power)for v2r21c10
		  Add:fname8031S5331-S24T4X-A(537644), --S5331-S24T4X-A (24*10/100/1000BASE-T ports, 4*10GE SFP+ ports, AC power,front access)for v2r21c10
		  Add:fname8031S5331-S24T4X-D(537645), --S5331-S24T4X-D (24*10/100/1000BASE-T ports, 4*10GE SFP+ ports, DC power,front access)for v2r21c10
		  Add:fname8031S5731-S48P4X-A(537646), --S5731-S48P4X Bundle(48*10/100/1000BASE-T ports, 4*10GE SFP+ ports, PoE+,single power, 1*AC power)for v2r21c10
		  Add:fname8031S5331-S48P4X(537647), --S5331-S48P4X (48*10/100/1000BASE-T ports, 4*10GE SFP+ ports, PoE+, without power module)for v2r21c10
		  Add:fname8031S5331-S24P4X(537648), --S5331-S24P4X (24*10/100/1000BASE-T ports, 4*10GE SFP+ ports, PoE+, without power module)for v2r21c10
		  Add:fname8031S5731S-S48P4X-A1(537632), --S5731S-S48T4X Bundle(48*10/100/1000BASE-T ports, 4*10GE SFP+ ports, PoE+,single power, 1*AC power)for v2r21c10
		  Add:bname8031S5731-S24T4X(537491), --S5731-S24T4X (24*10/100/1000BASE-T ports, 4*10GE SFP+ ports, without power module)for v2r21c10
		  Add:bname8031S5731S-S24T4X-A(537492), --S5731S-S24T4X Bundle (24*10/100/1000BASE-T ports, 4*10GE SFP+ ports, 1*AC power)for v2r21c10
		  Add:bname8031S5731-S24P4X(537494), --S5731-S24P4X (24*10/100/1000BASE-T ports, 4*10GE SFP+ ports, PoE+, without power module)for v2r21c10
		  Add:bname8031S5731S-S24P4X-A(537495), --S5731S-S24P4X  Bundle(48*10/100/1000BASE-T ports, 4*10GE SFP+ ports, PoE+, 1*AC power)for v2r21c10
		  Add:bname8031S5731-S48T4X(537497), --S5731-S48T4X (48*10/100/1000BASE-T ports, 4*10GE SFP+ ports, without power module)for v2r21c10
		  Add:bname8031S5731S-S48T4X-A(537498), --S5731S-S48T4X Bundle(48*10/100/1000BASE-T ports, 4*10GE SFP+ ports, 1*AC power)for v2r21c10
		  Add:bname8031S5731-S48P4X(537500), --S5731-S48P4X (48*10/100/1000BASE-T ports, 4*10GE SFP+ ports, PoE+, without power module)for v2r21c10
		  Add:bname8031S5731S-S48P4X-A(537501), --S5731S-S48P4X Bundle(48*10/100/1000BASE-T ports, 4*10GE SFP+ ports, PoE+, 1*AC power)for v2r21c10
		  Add:bname8031S5731S-S48P4X-A1(537816), --S5731S-S48T4X Bundle(48*10/100/1000BASE-T ports, 4*10GE SFP+ ports, PoE+,single power, 1*AC power)for v2r21c10
		  Add:bname8031S5331-S48T4X(537818), --S5331-S48T4X (48*10/100/1000BASE-T ports, 4*10GE SFP+ ports, without power module)for v2r21c10
		  Add:bname8031S5731-S48T4X-A(537822), --S5731-S48T4X-A (48*10/100/1000BASE-T ports, 4*10GE SFP+ ports, AC power)for v2r21c10
		  Add:bname8031S5731S-S48T4X-A1(537823), --S5731S-S48T4X-A1 (48*10/100/1000BASE-T ports, 4*10GE SFP+ ports, AC power)for v2r21c10
		  Add:bname8031S5331-S48T4X-A(537824), --S5331-S48T4X-A (48*10/100/1000BASE-T ports, 4*10GE SFP+ ports, AC power)for v2r21c10
		  Add:bname8031S5731-S24T4X-A(537825), --S5731-S24T4X-A (24*10/100/1000BASE-T ports, 4*10GE SFP+ ports, AC power)for v2r21c10
		  Add:bname8031S5731S-S24T4X-A1(537826), --S5731S-S24T4X-A1 (24*10/100/1000BASE-T ports, 4*10GE SFP+ ports, AC power)for v2r21c10
		  Add:bname8031S5731-S24T4X-D(537827), --S5731-S24T4X-D (24*10/100/1000BASE-T ports, 4*10GE SFP+ ports, DC power)for v2r21c10
		  Add:bname8031S5331-S24T4X-A(537828), --S5331-S24T4X-A (24*10/100/1000BASE-T ports, 4*10GE SFP+ ports, AC power,front access)for v2r21c10
		  Add:bname8031S5331-S24T4X-D(537829), --S5331-S24T4X-D (24*10/100/1000BASE-T ports, 4*10GE SFP+ ports, DC power,front access)for v2r21c10
		  Add:bname8031S5731-S48P4X-A(537830), --S5731-S48P4X Bundle(48*10/100/1000BASE-T ports, 4*10GE SFP+ ports, PoE+,single power, 1*AC power)for v2r21c10
		  Add:bname8031S5331-S48P4X(537831), --S5331-S48P4X (48*10/100/1000BASE-T ports, 4*10GE SFP+ ports, PoE+, without power module)for v2r21c10
		  Add:bname8031S5331-S24P4X(537832), --S5331-S24P4X (24*10/100/1000BASE-T ports, 4*10GE SFP+ ports, PoE+, without power module)for v2r21c10
          "

        REVISION    "202111101100Z"
        DESCRIPTION "V12.07,
          Add: bnameH901MPSG(148740),       --  control board of MA5800-X2.
          Add: bnameH901MPSFE(148741),      --  control board of EA5800-X2.
          Add: subbnameH901CPCG(148523),     --  Clock subboard of MA5800-X2 H901MPSG.
          "

        REVISION    "202111101030Z"
        DESCRIPTION "V12.06,
          Add: fname8031S5731-H24HB4XZ(537630), --S5731-H24HB4XZ(20*Hybrid GE SFP ports, 4*Hybrid 10GE SFP+ ports, 4*10GE SFP+ ports, 1*expansion slot, PoE++, without power module) for V2R21C10
          Add: fname8031S5731S-H24HB4XZ-A(537631), --S5731S-H24HB4XZ Bundle(20*Hybrid GE SFP ports, 4*Hybrid 10GE SFP+ ports, 4*10GE SFP+ ports, 1*expansion slot, PoE++, 1*AC power) for V2R21C10
          Add: bname8031S5731-H24HB4XZ(537814), --S5731-H24HB4XZ(20*Hybrid GE SFP ports, 4*Hybrid 10GE SFP+ ports, 4*10GE SFP+ ports, 1*expansion slot, PoE++, without power module) for V2R21C10
          Add: bname8031S5731S-H24HB4XZ-A(537815), --S5731S-H24HB4XZ Bundle(20*Hybrid GE SFP ports, 4*Hybrid 10GE SFP+ ports, 4*10GE SFP+ ports, 1*expansion slot, PoE++, 1*AC power) for V2R21C10 
          "
        REVISION    "202111091635Z"
        DESCRIPTION "V12.05,
          Add: fname8031S5731-H48HB4XZ(537628), --S5731-H48HB4XZ(44*Hybrid GE SFP ports, 4*Hybrid 10GE SFP+ ports, 4*10GE SFP+ ports, 1*expansion slot, PoE++, without power module) for V2R21C10
          Add: fname8031S5731S-H48HB4XZ-A(537629), --S5731S-H48HB4XZ Bundle(44*Hybrid GE SFP ports, 4*Hybrid 10GE SFP+ ports, 4*10GE SFP+ ports, 1*expansion slot, PoE++, 1*AC power) for V2R21C10
          Add: bname8031S5731-H48HB4XZ(537812), --S5731-H48HB4XZ(44*Hybrid GE SFP ports, 4*Hybrid 10GE SFP+ ports, 4*10GE SFP+ ports, 1*expansion slot, PoE++, without power module) for V2R21C10
          Add: bname8031S5731S-H48HB4XZ-A(537813), --S5731S-H48HB4XZ Bundle(44*Hybrid GE SFP ports, 4*Hybrid 10GE SFP+ ports, 4*10GE SFP+ ports, 1*expansion slot, PoE++, 1*AC power) for V2R21C10
          "
		 
        REVISION "202111080000Z"
        DESCRIPTION "V12.04
          Add: virent8090DEVME0DBSUFC871(659391),   -- V8R21C10 for ME0DBSUFC871(SBOM) Flexible Card Broadband Service Unit(BSUF-200A,2 sub-slots)
          Add: virent8090DEVME0DBSUFM075(498559),   -- V8R21C10 for ME0DBSUFM075(SBOM) Flexible Card Broadband Service Unit(BSUF-245,2 sub-slots)
          Add: virent8090DEVME0DMSUFF071(795655),   -- V8R21C10 for ME0DMSUFF071(SBOM) Flexible Card Multi Service Unit(MSUF-245,2 sub-slots)
          Add: virent8090DEVME0DMSUFF072(587637),   -- V8R21C10 for ME0DMSUFF072(SBOM) Flexible Card Multi Service Unit(MSUF-245A,2 sub-slots)
          Add: virent8090DEVCR5DLPUF5271(719830),   -- V8R21C10 for CR5DLPUF5271(SBOM) Flexible Card Line Processing Unit(LPUF-55A,2 sub-slots)
          Add: virent8090DEVCR5DLPUFE07F(769998),   -- V8R21C10 for CR5DLPUFE07F(SBOM) Flexible Card Line Processing Unit(LPUF-200A-E)
          Add: virent8090DEVCR5DLPUFF072(613299),   -- V8R21C10 for CR5DLPUFF072(SBOM) Flexible Card Line Processing Unit(LPUF-245)
          Add: virent8090DEVCR5DLPUFF073(841172),   -- V8R21C10 for CR5DLPUFF073(SBOM) Flexible Card Line Processing Unit(LPUF-245A)
          Add: virent8090DEVCR5DLPUFF07G(878564),   -- V8R21C10 for CR5DLPUFF07G(SBOM) Flexible Card Line Processing Unit(LPUF-245-E)
          Add: virent8090DEVCR5DLPUFF07H(430465),   -- V8R21C10 for CR5DLPUFF07H(SBOM) Flexible Card Line Processing Unit(LPUF-245A-E)
          Add: virent8090DEVCR5DLPUFF379(177565),   -- V8R21C10 for CR5DLPUFF379(SBOM) 10-Port GE-SFP/10GE-SFP+ and 14-Port GE-SFP Flexible Card Line Processing Unit(LPUI-245-CM, 4*10GE+20*GE by default, one sub-slot for flexible card)
          Add: virent8090DEVCR5DLPUFF37K(530105),   -- V8R21C10 for CR5DLPUFF37K(SBOM) 10-Port GE-SFP/10GE-SFP+ and 14-Port GE-SFP Flexible Card Line Processing Unit(LPUI-245A-CM, 4*10GE+20*GE by default, one sub-slot for flexible card)
          Add: virent8090DEVME0DBSUFM077(131436),   -- V8R21C10 for ME0DBSUFM077(SBOM) Flexible Card Broadband Service Unit(BSUF-485,2 sub-slots)
          Add: virent8090DEVME0DBSUFM078(294389),   -- V8R21C10 for ME0DBSUFM078(SBOM) Flexible Card Broadband Service Unit(BSUF-485A,2 sub-slots)
          Add: virent8090DEVME0DMSUFM072(352083),   -- V8R21C10 for ME0DMSUFM072(SBOM) Flexible Card Multi Service Unit(MSUF-485,2 sub-slots)
          Add: virent8090DEVCR5DLPUFM073(499637),   -- V8R21C10 for CR5DLPUFM073(SBOM) Flexible Card Line Processing Unit(LPUF-485)
          Add: virent8090DEVCR5DLPUFM074(815725),   -- V8R21C10 for CR5DLPUFM074(SBOM) Flexible Card Line Processing Unit(LPUF-485A)
          Add: virent8090DEVCR5DLPUFME73(137819),   -- V8R21C10 for CR5DLPUFME73(SBOM) Flexible Card Line Processing Unit E(LPUF-485-E)
          Add: virent8090DEVCR5DLPUFME74(759171),   -- V8R21C10 for CR5DLPUFME74(SBOM) Flexible Card Line Processing Unit E(LPUF-485-E)
          "

        REVISION "202111040000Z"
        DESCRIPTION "V12.03
            Add: virent8090DEVCR8DSFUI4TC8(240310),   -- V8R21C10 for CR8DSFUI4TC8(SBOM) NetEngine 8100 X8 4Tbps Switch Fabric Unit(SFUIA-4T-E)
            Add: virent8090DEVIG2DMPUX8673(710465),   -- V8R21C10 for IG2DMPUX8673(SBOM) Main Processing Unit B11A(32G Memory)
            Add: virent8090DEVIG2D0SRUAI70(131840),   -- V8R21C10 for IG2D0SRUAI70(SBOM) Main Processing Unit A18A(SRUA-1TA-F, 32G Memory)
            Add: virent8090DEVIG2DSFUIT07C(700319),   -- V8R21C10 for IG2DSFUIT07C(SBOM) 1Tbps Switch Fabric Unit M(SFUI-1TA-M)
            Add: virent8090DEVIG2DSFUIT07F(581443),   -- V8R21C10 for IG2DSFUIT07F(SBOM) 1Tbps Switch Fabric Unit M(SFUI-1TA-N)
            Add: virent8090DEVIG2DLPUFM070(581444),   -- V8R21C10 for IG2DLPUFM070(SBOM) Flexible Card Line Processing Unit(LPUF-480)
        "
        
        REVISION    "202111020000Z"
        DESCRIPTION "V12.02
                    Add: subnamePAC600S56-CB(536819),    --600W AC&240V DC Power Module (Back to Front,Power panel side exhaust) for V2R21C10
                "

        REVISION    "202111010000Z"
        DESCRIPTION "V12.01
                    Add:bnameH902ACSA(148745),         -- Access Edge Computing board of MA5800.
                "

    REVISION "202110280000Z" 
        DESCRIPTION "V12.00
            Add: virent8090DEVCP8PHST20A02(525128),   -- V8R21C10 for CP8PHST20A02(SBOM) NetEngine A821, CP8PHST20A02, NetEngine A821 AC System (6*10GE/GE/FE+4*GE/FE(o), 8*GE/FE(e), Default 2*10GE/GE/FE+8*GE/FE(o)+8*GE/FE(e))
            Add: virent8090DEVCP8PHST2EA00(439707),   -- V8R21C10 for CP8PHST2EA00(SBOM) NetEngine A821 E, CP8PHST2EA00, NetEngine A821 E AC Chassis(A) (6*10GE/GE/FE+4*GE/FE(o), 8*GE/FE(e), Default 2*10GE/GE/FE(o)+8*GE/FE(o)+8*GE/FE(e))
            Add: virent8090DEVCP8PHST2EA01(856064),   -- V8R21C10 for CP8PHST2EA01(SBOM) NetEngine A821 E, CP8PHST2EA01, NetEngine A821 E AC Chassis (6*10GE/GE/FE+4*GE/FE(o), 8*GE/FE(e), Default 2*10GE/GE/FE(o)+8*GE/FE(o)+8*GE/FE(e))
            Add: virent8090DEVCR8DIPU800CG(888880),   -- V8R21C10 for CR8DIPU800CG(SBOM) Integrated Network Processing Unit (IPU-800-BN)
            Add: virent8090DEVCR8DIPU800CH(434493),   -- V8R21C10 for CR8DIPU800CH(SBOM) Integrated Network Processing Unit (IPUA-800-BN)
            Add: fnameNETENGINE-A821-AC(226372),       -- V8R21C10 for NETENGINE-A821-AC chassis
            Add: fnameNETENGINE-A821-E-AC(226374),     -- V8R21C10 for NETENGINE-A821-E-AC chassis
        "	
	REVISION    "202110260000Z"
        DESCRIPTION "V11.99,
		        Add:bnameCEMPUDFULL2E(688455),               --
				Add:bnameCEMPUDHALF2E(688456),               --
				Add:bnameCEMPUDF2EK(688457),                 --
				Add:bnameCEMPUDH2EK(688458),                 --
				Modify:bnameCEMPUFHALF1E(688406),            -- Finished Board Unit,CE16800,CE-MPUF-HALF1E,CE16800 Main Processing Unit F (half-width)
				Modify:bnameCEMPUFFULL1E(688407),            -- Finished Board Unit,CE16800,CE-MPUF-FULL1E,CE16800 Main Processing Unit F (full-width)
                Modify:bnameCEMPUDFULL2(688431),             -- Finished Board Unit,CE16800,CE-MPUD-FULL2,CE16800 Main Processing Unit G (full-width)
				Modify:bnameCEMPUDHALF2(688432),             -- Finished Board Unit,CE16800,CE-MPUD-HALF2,CE16800 Main Processing Unit G (half-width)
				Modify:bnameCEMPUDF2K(688433),               -- Finished Board Unit,CE16800,CE-MPUD-F2K,CE16800 Main Processing Unit G-FK (full-width)
				Modify:bnameCEMPUDH2K(688434),               -- Finished Board Unit,CE16800,CE-MPUD-H2K,CE16800 Main Processing Unit G-HK (half-width)
				Del:bnameCEL36CQFD2G(688435),              -- Finished Board Unit,CloudEngine 16800,CEL36CQFD-G,36-port 100GE interface card (FD2-G, QSFP28)
				Del:bnameCEL36CQFD2-GK(688436),             -- Finished Board Unit,CloudEngine 16800,CEL36CQFD-GK,36-port 100GE interface card (FD2-GK, QSFP28)
				Del:fnameCE6863E48S6CQK(688228),           -- Assembling Components,CE6863-48S6CQ-K, switch (48*25GE SFP28, 6*100GE QSFP28, without fan and power modules)
				Del:bnameCE6863E48S6CQK(688441),           -- Assembling Components,CE6863-48S6CQ-K,switch (48*25GE SFP28, 6*100GE QSFP28, without fan and power modules)				
                "

	REVISION    "202110210000Z"
        DESCRIPTION "V11.96,
                Add:subbname8090DEVNetEngineA821E(225998),      --CARD NetEngine A821 E
                Add:subbname8090DEVANND16E10000(225996),        --16 Channels E1 Interface Board(PIC,75ohm/120ohm)
                Add:subbname8090DEVANND00EX4S04(225997),        --4 Channels 10GE FlexE Optical Interface Board(SFP+)
                "

	REVISION    "202110190000Z"
        DESCRIPTION "V11.97,
                Add: subbname8090DEVCR5D00LBXF73(561699),        --12-Port 10GBase LAN/WAN-SFP+ Flexible Card(P245)
                Add: subbname8090DEVME0M0LEXFB72(561700),        --20-Port 10GBase LAN/WAN-SFP+ Flexible Card H(BP400-H)
                Add: subbname8090DEVCR5D0LAXFH71(561701),        --10-Port 10GBase LAN/WAN-SFP+ Flexible Card H(P240A-H)
                Add: subbname8090DEVCR5D0LAXFE72(561702),        --10-Port 10GBase LAN/WAN-SFP+ Flexible Card E(P245-E)
                Add: subbname8090DEVCX6D0EFGFA13(561703),        --24-Port 100/1000Base-X-SFP Flexible Card A(S240A-A)
                Add: subbname8090DEVCX6D0LBXFA13(561704),        --12-Port 10GBase LAN/WAN-SFP+ Flexible Card A(S240A-A)
                Add: subbname8090DEVCR5D00E2NF74(203899),      -- 2-Port 50GBase/2-Port 100GBase-QSFP28 Flexible Card A(P485-A)
                Add: subbname8090DEVCR5DE2VE1N73(986205),   -- 2-Port 50GBase/1-Port 100GBase-QSFP28 FlexE Flexible Card (P245)
                Add: subbname8090DEVCX6DE2VE1N11(177058),   -- 2-Port 50GBase/1-Port 100GBase-QSFP28 FlexE Flexible Card (S240A-A)
                Add: subbname8090DEVME0D00L1NB72(689388),   -- 2-Port 50GBase/1-Port 100GBase-QSFP28 Flexible Card(BP245)
                Add: subbname8090DEVCR5D0EFGFH71(729209),   -- 24-Port 1000Base-X-SFP Flexible Card H(P51A-H)
                Add: subbname8090DEVCR5D0EFGFA72(204664),   -- 24-Port 100/1000Base-X-SFP Flexible Card(P55)
                Add: subbname8090DEVCR5D0EFGFE72(257371),   -- 24-Port 1000Base-X-SFP Flexible Card E(P245-E)
                Add: subbname8090DEVCR5D00E1ND76(231975),   -- 1-Port 100GBase-QSFP28 Flexible Card A(P240A-A)
                Add: subbname8090DEVCR5D00E1ND78(905397),   -- 1-Port 100GBase-QSFP28 Flexible Card A(P245-A)
                Add: subbname8090DEVCX6D0E1NBA11(632384),   -- 1-Port 100GBase-QSFP28 Flexible Card A(S240A-A)
                Add: subbname8090DEVME0D0EFGFH7I(260956),   -- 24-Port 1000Base-X-SFP Flexible Card H(BP51A-H)
                Add: subbname8090DEVME0D0EFGFE7F(913970),   -- 24-Port 1000Base-X-SFP Flexible Card E(BP245-E)
                Add: subbname8090DEVME0D0LBXXB7J(160367),   -- 12-Port 10GBase LAN/WAN-SFP+ Flexible Card(BP245-E)
                Add: subbname8090DEVME0D0E1NDB73(535050),   -- 1-Port 100GBase-QSFP28 Flexible Card(BP240A)
                Add: subbname8090DEVME0D0E1NDB72(519111),   -- 1-Port 100GBase-QSFP28 Flexible Card(BP245)
                Add: subbname8090DEVME0M0LEXFB74(941707),   -- 20-Port 10GBase LAN/WAN-SFP+ Flexible Card(BP485)
                Add: subbname8090DEVME0D0LAXFH7I(632930),   -- 10-Port 10GBase LAN/WAN-SFP+ Flexible Card H(BP240A-H)
                Add: subbname8090DEVME0D0LAXFB7I(601206),   -- 10-Port 10GBase LAN/WAN-SFP+ Flexible Card E(BP245-E)
                Add: subbname8090DEVCR5D00LFXF77(971370),   -- 24-Port 10GBase LAN/WAN-SFP+ Flexible Card A(P485-A)
                Add: subbname8090DEVCR5D0LBXFE7F(976431),   -- 12-Port 10GBase LAN/WAN-SFP+ Flexible Card E(P245-E)
                Add: subbname8090DEVCR5DE2VE1N72(576762),   -- 2-Port 50GBase/1-Port 100GBase-QSFP28 FlexE Flexible Card (P245-E)
                Add: subbname8090DEVME0D00L1NB71(864407),   -- 2-Port 50GBase/1-Port 100GBase-QSFP28 Flexible Card(BP245-E)
                Add: subbname8090DEVCR5D00E1ND75(469730),   -- 1-Port 100GBase-QSFP28 Flexible Card(P245)
                Add: subbname8090DEVCR5D00E1ND77(145911),   -- 1-Port 100GBase-QSFP28 Flexible Card E(P245-E)
                Add: subbname8090DEVME0D00E1ND75(239749),   -- 1-Port 100GBase-QSFP28 Flexible Card E(BP245-E)
                Add: subbname8090DEVCR5D0EFGFA74(673606),   -- 24-Port 100/1000Base-X-SFP Flexible Card A(P245-A)
                Add: subbname8090DEVME0D0EFGFB7J(209459),   -- 24-Port 100/1000Base-X-SFP Flexible Card(BP245)
                Add: subbname8090DEVCR5D00LBXF74(872589),   -- 12-Port 10GBase LAN/WAN-SFP+ Flexible Card A(P245-A)
                Add: subbname8090DEVME0D0LBXXB7I(987604),   -- 12-Port 10GBase LAN/WAN-SFP+ Flexible Card(BP245)
                Add: virent8090DEVME0DBSUFM076(385871),   -- V8R21C10 for ME0DBSUFM076(SBOM) Flexible Card Broadband Service Unit(BSUF-480A,2 sub-slots)
                Add: virent8090DEVME0DBSUFK072(682199),   -- V8R21C10 for ME0DBSUFK072(SBOM) Flexible Card Broadband Service Unit(BSUF-400A,2 sub-slots)
                "
				
	REVISION    "202110150000Z"
        DESCRIPTION "V11.96,
                Add: bnamePTN7900TPA5EY8(229647),    --TPA5EY8, 8*25GE Ethernet Service Processing Board
                "

	REVISION    "202110130000Z"
        DESCRIPTION "V11.95,
                Add: fname8031S5731-S48S4X-A(537568),  --S5731-S48S4X-A(48*GE SFP ports, 4*10GE SFP+ ports, AC power, front access) for V2R21C01
                Add: fname8031S5731S-S48S4X-A1(537569),  --S5731S-S48S4X-A1(48*GE SFP ports, 12*10GE SFP+ ports, AC power, front access) for V2R21C01
                Add: fname8031S5331-S48S4X-A(537570),  --S5331-S48S4X-A(48*GE SFP ports, 4*10GE SFP+ ports, AC power, front access) for V2R21C01
                Add: fname8031S5331-S48S4X-D(537571),  --S5331-S48S4X-D(48*GE SFP ports, 4*10GE SFP+ ports, DC power, front access) for V2R21C01
                Add: fname8031S5731-S48S4X(537572),  --S5731-S48S4X(48*GE SFP ports,  4*10GE SFP+ ports, without power module) for V2R21C01
                Add: fname8031S5731S-S48S4X-A(537573),  --S5731S-S48S4X-A(48*GE SFP ports,  4*10GE SFP+ ports, with AC power supply) for V2R21C01
                Add: fname8031S5331-S48S4X(537574),  --S5331-S48S4X(48*GE SFP ports,  4*10GE SFP+ ports, without power module) for V2R21C01
                Add: fname8031S5731-S32ST4X-A(537575),  --S5731-S32ST4X-A(8*10/100/1000BASE-T ports, 24*GE SFP ports, 4*10GE SFP+ ports, AC power, front access) for V2R21C01
                Add: fname8031S5731S-S32ST4X-A1(537576),  --S5731S-S32ST4X-A1(8*10/100/1000BASE-T ports, 24*GE SFP ports, 4*10GE SFP+ ports, AC power, front access) for V2R21C01
                Add: fname8031S5731-S32ST4X-D(537577),  --S5731-S32ST4X-D(8*10/100/1000BASE-T ports, 24*GE SFP ports, 4*10GE SFP+ ports, DC power, front access) for V2R21C01
                Add: fname8031S5331-S32ST4X-A(537578),  --S5331-S32ST4X-A(8*10/100/1000BASE-T ports, 24*GE SFP ports, 4*10GE SFP+ ports, AC power, front access) for V2R21C01
                Add: fname8031S5331-S32ST4X-D(537579),  --S5331-S32ST4X-D(8*10/100/1000BASE-T ports, 24*GE SFP ports, 4*10GE SFP+ ports, DC power, front access) for V2R21C01
                Add: fname8031S5731-S32ST4X(537580),  --S5731-S32ST4X(8*10/100/1000BASE-T ports, 24*GE SFP ports, 4*10GE SFP+ ports, without power module) for V2R21C01
                Add: fname8031S5731S-S32ST4X-A(537581),  --S5731S-S32ST4X-A(8*10/100/1000BASE-T ports, 24*GE SFP ports, 4*10GE SFP+ ports, with AC power supply) for V2R21C01
                Add: fname8031S5331-S32ST4X(537582),  --S5331-S32ST4X(8*10/100/1000BASE-T ports, 24*GE SFP ports, 4*10GE SFP+ ports, without power module) for V2R21C01
                Add: fname8031S5700W-S32ST4X1(537624),  --S5700W-S32ST4X1 (24*GE SFP ports, 8*10/100/1000BASE-T ports, 4*10GE SFP+ ports, without power module) for V2R21C01
                Add: bname8031S5731-S48S4X-A(537752),  --S5731-S48S4X-A(48*GE SFP ports, 4*10GE SFP+ ports, AC power, front access) for V2R21C01
                Add: bname8031S5731S-S48S4X-A1(537753),  --S5731S-S48S4X-A1(48*GE SFP ports, 12*10GE SFP+ ports, AC power, front access) for V2R21C01
                Add: bname8031S5331-S48S4X-A(537754),  --S5331-S48S4X-A(48*GE SFP ports, 4*10GE SFP+ ports, AC power, front access) for V2R21C01
                Add: bname8031S5331-S48S4X-D(537755),  --S5331-S48S4X-D(48*GE SFP ports, 4*10GE SFP+ ports, DC power, front access) for V2R21C01
                Add: bname8031S5731-S48S4X(537756),  --S5731-S48S4X(48*GE SFP ports,  4*10GE SFP+ ports, without power module) for V2R21C01
                Add: bname8031S5731S-S48S4X-A(537757),  --S5731S-S48S4X-A(48*GE SFP ports,  4*10GE SFP+ ports, with AC power supply) for V2R21C01
                Add: bname8031S5331-S48S4X(537758),  --S5331-S48S4X(48*GE SFP ports,  4*10GE SFP+ ports, without power module) for V2R21C01
                Add: bname8031S5731-S32ST4X-A(537759),  --S5731-S32ST4X-A(8*10/100/1000BASE-T ports, 24*GE SFP ports, 4*10GE SFP+ ports, AC power, front access) for V2R21C01
                Add: bname8031S5731S-S32ST4X-A1(537760),  --S5731S-S32ST4X-A1(8*10/100/1000BASE-T ports, 24*GE SFP ports, 4*10GE SFP+ ports, AC power, front access) for V2R21C01
                Add: bname8031S5731-S32ST4X-D(537761),  --S5731-S32ST4X-D(8*10/100/1000BASE-T ports, 24*GE SFP ports, 4*10GE SFP+ ports, DC power, front access) for V2R21C01
                Add: bname8031S5331-S32ST4X-A(537762),  --S5331-S32ST4X-A(8*10/100/1000BASE-T ports, 24*GE SFP ports, 4*10GE SFP+ ports, AC power, front access) for V2R21C01
                Add: bname8031S5331-S32ST4X-D(537763),  --S5331-S32ST4X-D(8*10/100/1000BASE-T ports, 24*GE SFP ports, 4*10GE SFP+ ports, DC power, front access) for V2R21C01
                Add: bname8031S5731-S32ST4X(537764),  --S5731-S32ST4X(8*10/100/1000BASE-T ports, 24*GE SFP ports, 4*10GE SFP+ ports, without power module) for V2R21C01
                Add: bname8031S5731S-S32ST4X-A(537765),  --S5731S-S32ST4X-A(8*10/100/1000BASE-T ports, 24*GE SFP ports, 4*10GE SFP+ ports, with AC power supply) for V2R21C01
                Add: bname8031S5331-S32ST4X(537766),  --S5331-S32ST4X(8*10/100/1000BASE-T ports, 24*GE SFP ports, 4*10GE SFP+ ports, without power module) for V2R21C01
                Add: bname8031S5700W-S32ST4X1(537808),  --S5700W-S32ST4X1 (24*GE SFP ports, 8*10/100/1000BASE-T ports, 4*10GE SFP+ ports, without power module) for V2R21C01
                Add:subnameS7Q02001(536818),           --2-port 40GE QSFP+ interface card for V2R21C01
                "
	REVISION    "202110110000Z"
        DESCRIPTION "V11.94
                Add: virent8090DEVCR5DLPUFF07F(675265),   -- V8R21C10 for CR5DLPUFF07F(SBOM) Flexible Card Line Processing Unit(LPUF-240A-E)
                Add: virent8090DEVCX6DISUFF011(157329),   -- V8R21C10 for CX6DISUFF011(SBOM) Flexible Card Integrated Service Unit(ISUF-240A)
				Add: virent8090DEVME0DBSUF5270(133753)   -- V8R21C10 for ME0DBSUF5270(SBOM) Flexible Card Broadband Service Unit(BSUF-55A,2 sub-slots)
                "

	REVISION    "202110090000Z"
        DESCRIPTION "V11.93
                Add: bnameWSIC-8GE-T-V2(668139),           --WSIC-8GE-T-V2 Lpu Control Unit
                Add: bnameWSIC-4GE-C-V2(668139),           --WSIC-4GE-C-V2 Lpu Control Unit
				Add: bnameSIC-NR-102-V2(668139),           --SIC-NR-102-V2 Lpu Control Unit
                "

        REVISION    "202109230000Z"
        DESCRIPTION "V11.92
                Add: virent8090DEVCR8D00EINBC1(564886),   -- V8R21C10 for CR8D00EINBC1(SBOM) 32-Port 100GBase-QSFP28 Integrated Line Processing Unit CM(LPUI-3T2A-CM)
                Del: bnameANND00CXPA01(229301),           -- ATN 980C,ANN1CXPA10,System Control,Cross-connect and Multi-protocol Process Unit with 320G
                "

        REVISION    "202109200000Z"
        DESCRIPTION "V11.91
                Add:bnameANND00CXPA01(229301),         --ATN 980C,ANN1CXPA10,System Control,Cross-connect and Multi-protocol Process Unit with 320G 
                "

		REVISION    "202109190000Z"
        DESCRIPTION "V11.90
                   Add: fnameUSG6603F-C(16715972),
                   Add: fnameUSG6620F-K-AC(16715973),
                   Add: fnameAntiDDoS1905-K-AC(16715974),
                   Add: fnameUSG6650F-K-AC(16715975),
                   Add: fnameIPS6610FD-K-AC(16715976),
                   Add: fnameUSG12004-K-AC(16715977),
                   Add: fnameUSG6725F-AC(16715978),
                   Add: fnameIPS6655F-AC(16715979),
                   Add: fnameAntiDDoS1908-AC(16715980),
                   Add: fnameUSG6715F-AC(16715981),
                   Add: fnameUSG6710F-K-AC(16715982),
                   Add: fnameEudemon1000E-F125-AC(16715983),
                   Add: fnameEudemon1000E-F125-DC(16715984),
                   Add: fnameUSG6685F-AC(16715985),
                   Add: fnameEudemon1000E-F85-AC(16715986),
                   Add: fnameEudemon1000E-F85-DC(16715987),
                   Add: fnameEudemon1000E-F55-DC(16715988),
                   Add: fnameEudemon1000E-F35-DC(16715989),
                   Add: fnameEudemon1000E-F25-DC(16715990),
                   Add: fnameEudemon1000E-F15-DC(16715991),
                   Add: fnameIPS6620F-K-AC(16715992),
                   Add: fnameUSG12004F(16715993),
                   Add: fnameEudemon9000E-F4(16715994),
                   Add: fnameAntiDDoS12004F(16715995),
                   Add: fnameIPS12004F(16715996),
                   Add: fnameUSG12008F(16715997),
                   Add: fnameEudemon9000E-F8(16715998),
                   Add: fnameAntiDDoS12008F(16715999),
                   Add: fnameIPS12008F(16716000),
                   Add: fnameEudemon1000E-F205-AC(16716001),
                   Add: fnameEudemon1000E-F205-DC(16716002),
                   Add: bnameUSG6620F-K-AC(16748691),
                   Add: bnameAntiDDoS1905-K-AC(16748692),
                   Add: bnameUSG6650F-K-AC(16748693),
                   Add: bnameIPS6610FD-K-AC(16748694),
                   Add: bnameIPS6610F-K-AC(16748695),
                   Add: bnameSPUB-E9KE-02-L(16748696),
                   Add: bnameUSG6725F-AC(16748697),
                   Add: bnameIPS6655F-AC(16748698),
                   Add: bnameAntiDDoS1908-AC(16748699),
                   Add: bnameUSG6715F-AC(16748700),
                   Add: bnameUSG6710F-K-AC(16748701),
                   Add: bnameEudemon1000E-F125-AC(16748702),
                   Add: bnameEudemon1000E-F125-DC(16748703),
                   Add: bnameUSG6685F-AC(16748704),
                   Add: bnameEudemon1000E-F85-AC(16748705),
                   Add: bnameEudemon1000E-F85-DC(16748706),
                   Add: bnameEudemon1000E-F55-DC(16748707),
                   Add: bnameEudemon1000E-F35-DC(16748708),
                   Add: bnameEudemon1000E-F25-DC(16748709),
                   Add: bnameEudemon1000E-F15-DC(16748710),
                   Add: bnameIPS6620F-K-AC(16748711),
                   Add: bnameSRUA-GX-F4(16748712),
                   Add: bnameSRUA-GX-F4-T(16748713),
                   Add: bnameSRUB-GX-F8(16748714),
                   Add: bnameSRUB-GX-F8-T(16748715),
                   Add: bnameLPUF-USG-24XS(16748716),
                   Add: bnameLPUF-E9KE-24XS(16748717),
                   Add: bnameLPUF-IPS-24XS(16748718),
                   Add: bnameLPUF-U-2CQ-24XS(16748719),
                   Add: bnameLPUF-E-2CQ-24XS(16748720),
                   Add: bnameLPUF-I-2CQ-24XS(16748721),
                   Add: bnameSPUF-USG-03(16748722),
                   Add: bnameSPUF-USG-02(16748723),
                   Add: bnameSPUF-USG-01(16748724),
                   Add: bnameSPUF-USG-TP-03(16748725),
                   Add: bnameSPUF-E9KE-03(16748726),
                   Add: bnameSPUF-E9KE-02(16748727),
                   Add: bnameSPUF-E9KE-01(16748728),
                   Add: bnameSPUF-E9KE-TP-03(16748729),
                   Add: bnameSPUF-ADS-03(16748730),
                   Add: bnameSPUF-ADS-02(16748731),
                   Add: bnameSPUF-ADS-01(16748732),
                   Add: bnameSPUF-IPS-03(16748733),
                   Add: bnameEudemon1000E-F205(16748734),
                   Add: bnameEudemon1000E-F205(16748735),
                "
		
		REVISION    "202109130000Z"
        DESCRIPTION "V11.89
				   Add: subbname8090DEVCR57L8XEDG0(225993),        --8-Port GE-SFP/10GE-SFP+ and 16-Port GE-SFP Unflexible Card(P243)
                   Add: subbname8090DEVCR57LFXFJ4(225992),         --24-Port 10GBase LAN/WAN-SFP+ MACsec Unflexible Card(P483)
                   Add: subbname8090DEVCR8D00E1NBC2(225994),       --2-Port 50GBase/1-Port 100GBase-QSFP28 FlexE MACsec Physical Interface Card(PIC)
                   Add: subbname8090DEVCR8D000DE1C2(225995),        --16-Port E1 Physical Interface Card(PIC,75ohm/120ohm)
                "
		
		REVISION    "202109080000Z"
        DESCRIPTION "V11.88
				   Add: fnameEA5801EGP08H2(148524),    --  Backplane of the EA5801E-GP08-H2.
				   Add: bnameH901MPLGE(148743),        --  control board of EA5800.
				   Add: bnameV921GPHDE(148744),        --  8*GPON board of EA5801E-GP08-H2.
				   Add: bnameH905OXHD(156021),         --  8*10GE P2P board of MA5800.
                   Add: bnameH903XSHFE(156022),        --  16*10G XGS-PON board of EA5800.
				   Add: bnameH905NXED(156023),         --  8*Port ETH board of MA5800.			   
                "
				
        REVISION    "202109070000Z"
        DESCRIPTION "V11.87,
                Add:bnameLSS3X16SA1E0(659763), --16-port 10GBASE-X interface card(SC,SFP+) for v2r21c01
                Add:bnameLSS3X32SA1E0(659764), --32-port 10GBASE-X interface card(SC,SFP+) for v2r21c01 
                "
		REVISION    "202108310000Z"
        DESCRIPTION "V11.86,
                    Add: bnameH901DQHF(148739),            --  DQ ODN OAI board of MA5800 and EA5800.
                    "

		REVISION    "202108240000Z"
        DESCRIPTION "V11.85,
				Add:bnameAR6710-L50T2X4(668135),           --AR6710-L50T2X4 Main Control Unit
				Add:bnameAR6710-L50T2X4-T(668136),         --AR6710-L50T2X4-T Main Control Unit
				Add:bnameAR6710-L26T2X4(668137),           --AR6710-L26T2X4 Main Control Unit
				Add:bnameAR6710-L26T2X4-T(668138),         --AR6710-L26T2X4-T Main Control Unit
				Add:bnameAR502H-5G-CN(668139),             --AR502H-5G-CN Main Control Unit
				Add:fnameAR6710-L50T2X4(668032),           --AR6710-L50T2X4 FRAME
				Add:fnameAR6710-L50T2X4-T(668033),         --AR6710-L50T2X4-T FRAME
				Add:fnameAR6710-L26T2X4(668034),           --AR6710-L26T2X4 FRAME
				Add:fnameAR6710-L26T2X4-T(668035),         --AR6710-L26T2X4-T FRAME
				Add:fnameAR502H-5G-CN(668036),   	       --AR502H-5G-CN FRAME"

        REVISION    "202108121930Z"
        DESCRIPTION "V11.84,
                Add:bnameLSS7X16SS100(663720), --16-port 10GBASE-X interface card(SC,SFP+) for v2r21c01
                Add:bnameLSS7X32SS100(663721), --32-port 10GBASE-X interface card(SC,SFP+) for v2r21c01 
                "
		REVISION    "202108101130Z"
        DESCRIPTION "V11.83,
                Modify:fnameNETENGINE-8000E-M14-Z(688886),      -- NETENGINE-8000E-M14-Z (fnameNETENGINE-8000E-M14-Z)
                Add:fnameNETENGINE-8000E-M14-Z-DC(688887),  -- NETENGINE-8000E-M14-Z-DC (fnameNETENGINE-8000E-M14-Z-DC)
                Add:fnameNETENGINE-8000E-M14-Z-2AC(688888),  -- NETENGINE-8000E-M14-Z-2AC (fnameNETENGINE-8000E-M14-Z-2AC)
                Add:virent8090DEVCR8DIPU1T2Z0(917063),   -- V8R21C10 for CR8DIPU1T2Z0(SBOM) Integrated Network Processing Unit (IPU-1T2-Z)
                "
		REVISION    "202108091730Z"
        DESCRIPTION "V11.82,
                Add:bnameLST7MPUEC000(700563), --S12700E main control unit EC for v2r21c01
                Add:bnameLSS3MCUD0001(659761), --S9303 main control unit D for v2r21c01
                Add:bnameLSS3SRUHX101(659762), --S9306/S9312 main control unit H(X1) for v2r21c01          
                Add:bnameLST3MPUEC000(659760), --S9300X main control unit EC for v2r21c01
                Add:bnameLSS7MCUD0001(663718), --S7703 main control unit D for v2r21c01
                Add:bnameLSS7SRUHX101(663719), --S7706/S7712 main control unit H(X1) for v2r21c01    
                "
		REVISION    "202108090000Z"
        DESCRIPTION "V11.81,
                Add: fname8031S5735S-H24S4X-MA(537627),  --S5735S-H24S4X-M bundle (24*GE SFP ports, 4*10GE SFP+ ports, 1*AC power module) for V2R21C01
                Add: bname8031S5735S-H24S4X-MA(537811),  --S5735S-H24S4X-M bundle (24*GE SFP ports, 4*10GE SFP+ ports, 1*AC power module) for V2R21C01
                "
		REVISION    "202108050000Z"
        DESCRIPTION "V11.80,
                    Add:bnameH905MPLA(148742),                --  control board of MA5800-X17.
                    "

		REVISION    "202108032000Z"
        DESCRIPTION "V11.79,                 					
				     Del:bnameFM98D8DQ(716829),				
				     Del:fnameFM98D8DQ(716817),
					 Add:subbnameFM98D8DQ(716806)
                    "					
        REVISION    "202108010000Z"
        DESCRIPTION "V11.78,
                Add: fname8031S6735-S48X6C(537583), --S6735-S48X6C(48 10 Gig SFP+,6 100 Gig QSFP28 interface,with 1 interface slot,without power module) for V2R21C01
                Add: fname8031S6735S-S48X6C-A(537584),  --S6735S-S48X6C Bundle(48 10 Gig SFP+,6 100 Gig QSFP28 interface,with 1 interface slot,with 600W AC power supply) for V2R21C01
                Add: fname8031S6735-S24X6C(537585),  --S6735-S24X6C Bundle(48 10 Gig SFP+,2 100 Gig QSFP28 interface,with 1 interface slot,without power module) for V2R21C01
                Add: fname8031S6735S-S24X6C-A(537586),  --S6735S-S24X6C Bundle(24 10 Gig SFP+,6 100 Gig QSFP28 interface,with 1 interface slot,with 600W AC power supply) for V2R21C01
                Add: fname8031S6735-S48X6C(537583), --S6735-S48X6C(48 10 Gig SFP+,6 100 Gig QSFP28 interface,with 1 interface slot,without power module) for V2R21C01
                Add: fname8031S6735S-S48X6C-A(537584),  --S6735S-S48X6C Bundle(48 10 Gig SFP+,6 100 Gig QSFP28 interface,with 1 interface slot,with 600W AC power supply) for V2R21C01
                Add: fname8031S6735-S24X6C(537585),  --S6735-S24X6C Bundle(48 10 Gig SFP+,2 100 Gig QSFP28 interface,with 1 interface slot,without power module) for V2R21C01
                Add: fname8031S6735S-S24X6C-A(537586),  --S6735S-S24X6C Bundle(24 10 Gig SFP+,6 100 Gig QSFP28 interface,with 1 interface slot,with 600W AC power supply) for V2R21C01
                "

        REVISION    "202107310000Z"
        DESCRIPTION "V11.77,
                Add: fname8031S5735-L8T4S-QA2(537587),   --S5735-L8T4S-QA2 (8*10/100/1000BASE-T ports, 4*GE SFP ports, AC power) for V2R21C01
                Add: fname8031S5735S-L8T4S-QA2(537588),  --S5735S-L8T4S-QA2 (8*10/100/1000BASE-T ports, 4*GE SFP ports, AC power) for V2R21C01
                Add: fname8031S300-8T4S-QA2(537589),     --S300-8T4S-QA2 (8*10/100/1000BASE-T ports, 4*GE SFP ports, AC power) for V2R21C01
                Add: fname8031S5735S-L8T4S-MA2(537590),  --S5735S-L8T4S-MA2 (8*10/100/1000BASE-T ports, 4*GE SFP ports, AC power) for V2R21C01
                Add: fname8031S1730S-S8T4S-QA2(537591),  --S1730S-S8T4S-QA2 (8*10/100/1000BASE-T ports, 4*GE SFP ports, AC power) for V2R21C01
                Add: fname8031S200-8T4S-QA2(537592),     --S200-8T4S-QA2 (8*10/100/1000BASE-T ports, 4*GE SFP ports, AC power) for V2R21C01
                Add: fname8031S5735-L8P4S-QA2(537593),   --S5735-L8P4S-QA2 (8*10/100/1000BASE-T ports, 4*GE SFP ports, PoE+, AC power) for V2R21C01
                Add: fname8031S5735S-L8P4S-QA2(537594),  --S5735S-L8P4S-QA2 (8*10/100/1000BASE-T ports, 4*GE SFP ports, PoE+, AC power) for V2R21C01
                Add: fname8031S300-8P4S-QA2(537595),     --S300-8P4S-QA2 (8*10/100/1000BASE-T ports, 4*GE SFP ports, PoE+, AC power) for V2R21C01
                Add: fname8031S5735S-L8P4S-MA2(537596),  --S5735S-L8P4S-MA2 (8*10/100/1000BASE-T ports, 4*GE SFP ports, PoE+, AC power) for V2R21C01
                Add: fname8031S1730S-S8P4S-QA2(537597),  --S1730S-S8P4S-QA2 (8*10/100/1000BASE-T ports, 4*GE SFP ports, PoE+, AC power) for V2R21C01
                Add: fname8031S200-8P4S-QA2(537598),     --S200-8P4S-QA2 (8*10/100/1000BASE-T ports, 4*GE SFP ports, PoE+, AC power) for V2R21C01
                Add: fname8031S5735-L24T4X-QA2(537599),  --S5735-L24T4X-QA2 (24*10/100/1000BASE-T ports, 4*10GE SFP+ ports, AC power) for V2R21C01
                Add: fname8031S5735S-L24T4X-QA2(537600), --S5735S-L24T4X-QA2 (24*10/100/1000BASE-T ports, 4*10GE SFP+ ports, AC power) for V2R21C01
                Add: fname8031S1730S-S24T4X-QA2(537601), --S1730S-S24T4X-QA2 (24*10/100/1000BASE-T ports, 4*10GE SFP+ ports, AC power) for V2R21C01
                Add: fname8031S5735-L24T4S-QA2(537602),  --S5735-L24T4S-QA2 (24*10/100/1000BASE-T ports, 4*GE SFP ports, AC power) for V2R21C01
                Add: fname8031S5735S-L24T4S-QA2(537603), --S5735S-L24T4S-QA2 (24*10/100/1000BASE-T ports, 4*GE SFP ports, AC power) for V2R21C01
                Add: fname8031S5735S-L24T4S-MA2(537604), --S5735S-L24T4S-MA2 (24*10/100/1000BASE-T ports, 4*GE SFP ports, AC power) for V2R21C01
                Add: fname8031S1730S-S24T4S-QA2(537605), --S1730S-S24T4S-QA2 (24*10/100/1000BASE-T ports, 4*GE SFP ports, AC power) for V2R21C01
                Add: fname8031S300-24T4S-QA2(537606),    --S300-24T4S-QA2 (24*10/100/1000BASE-T ports, 4*GE SFP ports, AC power) for V2R21C01
                Add: fname8031S200-24T4S-QA2(537607),    --S200-24T4S-QA2 (24*10/100/1000BASE-T ports, 4*GE SFP ports, AC power) for V2R21C01
                Add: fname8031S5735-L24P4X-A2(537610),   --S5735-L24P4X-A2 (24*10/100/1000BASE-T ports, 4*10GE SFP+ ports, PoE+, AC power) for V2R21C01
                Add: fname8031S5735S-L24P4X-A2(537611),  --S5735S-L24P4X-A2 (24*10/100/1000BASE-T ports, 4*10GE SFP+ ports, PoE+, AC power) for V2R21C01
                Add: fname8031S1730S-S24P4X-A2(537612),  --S1730S-S24P4X-A2 (24*10/100/1000BASE-T ports, 4*10GE SFP+ ports, PoE+, AC power) for V2R21C01
                Add: fname8031S5735-L24P4S-A2(537613),   --S5735-L24P4S-A2 (24*10/100/1000BASE-T ports, 4*GE SFP ports, PoE+, AC power) for V2R21C01
                Add: fname8031S5735S-L24P4S-A2(537614),  --S5735S-L24P4S-A2 (24*10/100/1000BASE-T ports, 4*GE SFP ports, PoE+, AC power) for V2R21C01
                Add: fname8031S5735S-L24P4S-MA2(537615), --S5735S-L24P4S-MA2 (24*10/100/1000BASE-T ports, 4*GE SFP ports, PoE+, AC power) for V2R21C01
                Add: fname8031S1730S-S24P4S-A2(537616),  --S1730S-S24P4S-A2 (24*10/100/1000BASE-T ports, 4*GE SFP ports, PoE+, AC power) for V2R21C01
                Add: fname8031S300-24P4S-A2(537617),     --S300-24P4S-A2 (24*10/100/1000BASE-T ports, 4*GE SFP ports, PoE+, AC power) for V2R21C01
                Add: fname8031S200-24P4S-A2(537618),     --S200-24P4S-A2 (24*10/100/1000BASE-T ports, 4*GE SFP ports, PoE+, AC power) for V2R21C01
                Add: fname8031S5735-S24T4X-X(537625),    --S5735-S24T4X-X (24*10/100/1000BASE-T ports, 4*10GE SFP+ ports, without power module) for V2R21C01
                Add: fname8031S5735S-S24T4X-XA(537626),  --S5735S-S24T4X-XA (24*10/100/1000BASE-T ports, 4*10GE SFP+ ports, 1*60W AC power module) for V2R21C01
                "

	REVISION "202107300000Z" 
        DESCRIPTION "V11.76
             Add: virent8090DEVCR8D0MPUA4C1(682999),    -- V1R21C10 for CR8D0MPUA4C1(SBOM) NetEngine 8000 Main Processing Unit A4A(MPUA4A)
             Add: virent8090DEVCR8D0MPUA4C0(706130),    -- V1R21C10 for CR8D0MPUA4C0(SBOM) NetEngine 8000 Main Processing Unit A4(MPUA4)
             Add: virent8090DEVCR8D0MPUA5C1(159477),    -- V1R21C10 for CR8D0MPUA5C1(SBOM) NetEngine 8000E Main Processing Unit A5A(MPUA5A)
             Add: virent8090DEVCR8D0MPUA8C5(932387),    -- V1R21C10 for CR8D0MPUA8C5(SBOM) NetEngine 8000S Main Processing Unit A8A(MPUA8A)
             Add: virent8090DEVCR8D0MPUA6C0(852150),    -- V1R21C10 for CR8D0MPUA6C0(SBOM) NetEngine 8000 Main Processing Unit A6(MPUA6)
             Add: virent8090DEVCR8D0MPUA6C1(517911),    -- V1R21C10 for CR8D0MPUA6C1(SBOM) NetEngine 8000 Main Processing Unit A6A(MPUA6A)
             Add: virent8090DEVCR8D0MPUA7C4(736463),    -- V1R21C10 for CR8D0MPUA7C4(SBOM) NetEngine 8000E Main Processing Unit A7A(MPUA7A)
             Add: virent8090DEVCR8D0MPUA6C2(329596),    -- V8R21C10 for CR8D0MPUA6C2(SBOM) NetEngine 8000 Main Processing Unit A6B(MPUA6B)
             Add: virent8090DEVCR8D0MPUA4C2(517066),    -- V8R21C10 for CR8D0MPUA4C2(SBOM) NetEngine 8000 Main Processing Unit A4B(MPUA4B)
        "

        REVISION "202107290000Z" 
        DESCRIPTION "V11.75
            Add: virent8090DEVCR8DIPU480C5(112043),   -- V8R21C00 for CR8DIPU480C5(SBOM) Integrated Network Processing Unit (IPU-480-BN)
            Add: subbname8090DEVCR5D0LBXFM71(225991), --12-Port 10GBase LAN/WAN-SFP+ FlexE/MACsec Flexible Card (P243)
        "
	   	REVISION    "202107280000Z"
        DESCRIPTION "V11.74,
               Add: bnamePTN7900TPD2FH8R(229645),   --TPD2FH8R, 8*100GE Packet Flexible Ethernet Service Processing Board
               Add: bnamePTN7900TPD2FHD4R(229646),    --TPD2FHD4R, 4*200GE Flexible Ethernet Service Processing Board
                "
	   
       REVISION "202107220000Z" 
        DESCRIPTION "V11.73
            Add: virent8090DEVCR5DLPUF5374(513967),   -- V8R21C00 for CR5DLPUF5374(SBOM) Flexible Card Line Processing Unit(LPUF-53A)
            Add: virent8090DEVCR5DLPUF5375(433904),   -- V8R21C00 for CR5DLPUF5375(SBOM) Flexible Card Line Processing Unit(LPUF-53)
            Add: virent8090DEVCR5DLPUFF377(655297),   -- V8R21C00 for CR5DLPUFF377(SBOM) 8-Port GE-SFP/10GE-SFP+ and 16-Port GE-SFP Flexible Card Line Processing Unit(LPUI-243A-CM, Enable 8*100M+16*GE by default, Supporting one sub-slot for flexible card)
            Add: virent8090DEVCR5DLPUFF378(467374),   -- V8R21C00 for CR5DLPUFF378(SBOM) 8-Port GE-SFP/10GE-SFP+ and 16-Port GE-SFP Flexible Card Line Processing Unit(LPUI-243-CM, Enable 8*100M+16*GE by default, Supporting one sub-slot for flexible card)
        "
        REVISION    "202107202000Z"
        DESCRIPTION "V11.72,
                Add: fname8031S5700W-S24P4X1(537619), --S5700W-S24P4X1 (24*10/100/1000BASE-T ports,4*10GE SFP+ ports,PoE+, without power module) for V2R21C00
                Add: fname8031S5700W-S48P4X1(537620), --S5700W-S48P4X1 (48*10/100/1000BASE-T ports,4*10GE SFP+ ports,PoE+,without power module) for V2R21C00
                Add: fname8031S6700W-S24X6Q1(537621), --S6700W-S24X6Q1 (24*10GE SFP+ ports, 6*40GE QSFP ports, without power module) for V2R21C00
                Add: fname8031S5700W-L24T4X-A1(537622), --S5700W-L24T4X-A1 (24*10/100/1000BASE-T ports, 4*10GE SFP+ ports, AC power) for V2R21C00
                Add: fname8031S5700W-L48T4X-A1(537623), --S5700W-L48T4X-A1 (48*10/100/1000BASE-T ports, 4*10GE SFP+ ports, AC power) for V2R21C00
                Add: bname8031S5700W-S24P4X1(537803), --S5700W-S24P4X1 (24*10/100/1000BASE-T ports,4*10GE SFP+ ports,PoE+, without power module) for V2R21C00
                Add: bname8031S5700W-S48P4X1(537804), --S5700W-S48P4X1 (48*10/100/1000BASE-T ports,4*10GE SFP+ ports,PoE+,without power module) for V2R21C00
                Add: bname8031S6700W-S24X6Q1(537805), --S6700W-S24X6Q1 (24*10GE SFP+ ports, 6*40GE QSFP ports, without power module) for V2R21C00
                Add: bname8031S5700W-L24T4X-A1(537806), --S5700W-L24T4X-A1 (24*10/100/1000BASE-T ports, 4*10GE SFP+ ports, AC power) for V2R21C00
                Add: bname8031S5700W-L48T4X-A1(537807), --S5700W-L48T4X-A1 (48*10/100/1000BASE-T ports, 4*10GE SFP+ ports, AC power) for V2R21C00
                "

       REVISION    "202107172000Z"
        DESCRIPTION "V11.71,                 
					 Add:bnameFM88684CEI(716828),	
				     Add:bnameFM98D8DQ(716829),
					 Add:fnameFM88684CEI(716816),
				     Add:fnameFM98D8DQ(716817)
                    "					

       REVISION    "202107142000Z"
        DESCRIPTION "V11.70,
                     Add:bnameH901FGHF(156020),       --  16*XG/G GPON combo board of MA5800.
                     Add:bnameV932NXSC(148738),       --  4*GE board of MA5801S-GP16-S1.
                    "
		REVISION    "202107132000Z" 
        DESCRIPTION "V11.69
                Add: virent8090DEVCR8DSFU14TC0(689000),          -- V1R21C10 for CR8DSFU14TC0(SBOM) NetEngine 8000 X16 14.4Tbps Switch Fabric Unit(SFUI-14T4-C)
                Add: virent8090DEVCR8DSFU14TC1(689001),          -- V1R21C10 for CR8DSFU14TC1(SBOM) NetEngine 8000 X16 14.4Tbps Switch Fabric Unit(SFUIA-14T4-C)
                Add: virent8090DEVCR8DSFU14TC2(689002),          -- V1R21C10 for CR8DSFU14TC2(SBOM) NetEngine 8000E X16 Switch Fabric Unit(SFUIA-C)
                Add: fnameNETENGINE-8000E-X16-DC(688566),        --Quidway fnameNETENGINE-8000E-X16-DC for V1R21C10
                Add: fnameNETENGINE-8000E-X16-HVDC(688567),      --Quidway fnameNETENGINE-8000E-X16-HVDC for V1R21C10
                Add: fnameNETENGINE-8000-M14-Z(688886),          -- NETENGINE-8000-M14-Z (fnameNETENGINE-8000-M14-Z)
                "

		REVISION    "202107131945Z"
        DESCRIPTION "V11.68,
                Add: subbname8090DEVNetEngineA811M(225988),     --CARD NetEngine A811 M
                Add: subbname8090DEVNetEngineA811(225989),      --CARD NetEngine A811
                "
		 
		REVISION    "202107121945Z"
        DESCRIPTION "V11.67,
             Add: bnameCEL36CQFD2G(688435),                 -- Finished Board Unit,CloudEngine 16800,CEL36CQFD-E,36-port 100GE interface card (FD2-G, QSFP28)
             Add: bnameCEL36CQFD2-GK(688436),               -- Finished Board Unit,CloudEngine 16800,CEL36CQFD-E,36-port 100GE interface card (FD2-GK, QSFP28)
             Add: bnameCEL36CQFDA(688437),                  -- Finished Board Unit,CloudEngine 16800,CEL36CQFD-A,36-port 100GE interface card (FD-A, QSFP28)
             Add: bnameCE8850E64CQ(688438),                 -- Assembling Components,CE8800,CE8850E-64CQ-B,CE8850E-64CQ Switch(64-Port 100GE QSFP28,2*AC Power Module,3*FAN Box,Port-side Intake)
			 Add: fnameCE8850E64CQ(688227),                 -- Assembling Components,CE8800,CE8850E-32CQ-EI-F,CE8850E-32CQ-EI Switch(32-Port 100GE QSFP28,1-Port 10GE SFP+,2*AC Power Module,2*FAN Box,Port-side Exhaust)
             Add: bnameCESFU08GA(688439),                   --
             Add: bnameCESFU16GA(688440),                   --
             Add: bnameCE6863E48S6CQK(688441),              -- Assembling Components,CE6863E-48S6CQ-K,CE6863E-48S6CQ-K,CE6863E-48S6CQ switch (48*25GE SFP28, 6*100GE QSFP28, without fan and power modules)
             Add: fnameCE6863E48S6CQK(688228),              -- Assembling Components,CE6863E-48S6CQ-K,CE6863E-48S6CQ-K,CE6863E-48S6CQ switch (48*25GE SFP28, 6*100GE QSFP28, without fan and power modules)
			 Add: bnameCESFU04JPK(688442),                 -- Finished Board Unit,CE16800,CE-SFU04J-PK,CE16804 Switch Fabric Unit J-PK
             Add: bnameCESFU04HPK(688443),                 -- Finished Board Unit,CE16800,CE-SFU04H-PK,CE16804 Switch Fabric Unit H-PK
             Add: bnameCESFU08JPK(688444),                 -- Finished Board Unit,CE16800,CE-SFU08J-PK,CE16808 Switch Fabric Unit J-PK
             Add: bnameCESFU08HPK(688445),                 -- Finished Board Unit,CE16800,CE-SFU08H-PK,CE16808 Switch Fabric Unit H-PK 
             Add: bnameCESFU16JPK(688446),                 -- Finished Board Unit,CE16800,CE-SFU16J-PK,CE16816 Switch Fabric Unit J-PK
             Add: bnameCEL48XSFDEK(688447),                -- Finished Board Unit,CloudEngine 16800,CEL48XSFD-EK,48-port 10GE interface card (FD-EK, SFP+)
             Add: bnameCEL24LQFDEK(688448),                -- Finished Board Unit,CloudEngine 16800,CEL24LQFD-EK,24-port 40GE interface card (FD-EK, QSFP+)
             Add: bnameCEL36LQFDEK(688449),                -- Finished Board Unit,CloudEngine 16800,CEL36LQFD-EK,36-port 40GE interface card (FD-EK, QSFP+)
             Add: bnameCEL18CQFDEK(688450),                -- Finished Board Unit,CloudEngine 16800,CEL18CQFD-EK,18-Port 100GE Interface Card (FD-EK, QSFP28)
             Add: bnameCEL36CQFDEK(688451),                -- Finished Board Unit,CloudEngine 16800,CEL36CQFD-EK,36-port 100GE interface card (FD-EK, QSFP28)                    
             Add: bnameCEL24LQFDE(688452),                 -- Finished Board Unit,CloudEngine 16800,CEL24LQFD-E,24-port 40GE interface card (FD-E, QSFP+)
             Add: bnameCEL36LQFDE(688453),                 -- Finished Board Unit,CloudEngine 16800,CEL36LQFD-E,36-port 40GE interface card (FD-E, QSFP+)
             Add: bnameCEL36CQFDE(688454),                 -- Finished Board Unit,CloudEngine 16800,CEL36CQFD-E,36-port 100GE interface card (FD-E, QSFP28) 
             "
			 
        REVISION    "202107061945Z"
        DESCRIPTION "V11.66,
                Add: fname8031S5735-L8P4S-QA1(537567), --S5735-L8P4S-QA1 (8*10/100/1000BASE-T ports, 4*GE SFP ports, PoE+, AC power, Fanless) for V2R21C00
                Add: bname8031S5735-L8P4S-QA1(537751), --S5735-L8P4S-QA1 (8*10/100/1000BASE-T ports, 4*GE SFP ports, PoE+, AC power, Fanless) for V2R21C00
                "
        REVISION    "202107060000Z"
        DESCRIPTION "V11.65,
               Add: bnamePTN7900TPD3FHD4R(229641),   --TPD3FHD4R, 4*200GE Packet Flexible Ethernet Service Processing Board
               Add: bnamePTN7900TPA7FHD2B(229642),    --TPA7FHD2B, 2*200GE Flexible Ethernet Service Processing Board
               Add: bnamePTN7900TPA7FHD1B(229643),    --TPA7FHD1B, 1*200GE Packet Service Processing Board
               Add: bnamePTN7900TPA7FH2B(229644),    --TPA7FH2B, 2*100GE Flexible Ethernet Service Processing Board
                "

	REVISION    "202107060000Z"
        DESCRIPTION "V11.64,
               Add: fnameNETENGINE-8000E-M8(688880),        -- NETENGINE-8000E-M8 (fnameNETENGINE-8000E-M8)
               Add: fnameNETENGINE-8000E-M8-AC(688882),     -- NETENGINE-8000E-M8-AC (fnameNETENGINE-8000E-M8-AC)
               Add: fnameNETENGINE-8000E-M8-DC(688881),     -- NETENGINE-8000E-M8-DC (fnameNETENGINE-8000E-M8-DC)
               Add: fnameNETENGINE-8000E-M14(688883),       -- NETENGINE-8000E-M14 (fnameNETENGINE-8000E-M14)
               Add: fnameNETENGINE-8000E-M14-AC(688884),    -- NETENGINE-8000E-M14-AC (fnameNETENGINE-8000E-M14-AC)
               Add: fnameNETENGINE-8000E-M14-DC(688885),    -- NETENGINE-8000E-M14-DC (fnameNETENGINE-8000E-M14-DC)
               Modify: virent8090DEVCR8DIPU1T2CD(800010),    --V8R21C00 CR8DIPU1T2CD(SBOM) Integrated Network Processing Unit (IPUA-1T2-BN)
               Modify: virent8090DEVCR8DIPU480C6(800009),    --V8R21C00 CR8DIPU480C6(SBOM) Integrated Network Processing Unit (IPUA-480-B)
                "

        REVISION "202107050000Z" 
        DESCRIPTION "V11.63
                Add: virentCP8PHST1MA00(229514),           -- V8R21C00 for CP8PHST1MA00(SBOM) NetEngine A811 M AC System (10*GE/FE(o), 8*GE/FE(e))
                Add: virentCP8PHST10A03(229520),           -- V8R21C00 for CP8PHST10A03(SBOM) NetEngine A811 AC System (10*GE/FE(o), 8*GE/FE(e))
                Add: virentHGFM0HOSTB00(229522),           -- V8R21C00 for HGFM0HOSTB00(SBOM) HG-FM CPE-02 AC Power,with 6*GE/FE(o),8*GE/FE(e)
                Add: fnameNETENGINE-A811-M-AC(229516),     -- V8R21C00 for NETENGINE-A811-M-AC chassis
                Add: fnameNETENGINE-A811-AC(229519),       -- V8R21C00 for NETENGINE-A811-AC chassis
                Add: fnameHG-FM-CPE-02-AC(229521),         -- V8R21C00 for HG-FM-CPE-02 chassis
                "
        REVISION "202107030000Z" 
        DESCRIPTION "V11.62
                Add: fname8031S6730-H48X6C-TV2(537563), --S6730-H48X6C-TV2(48*10GE SFP+ ports, 6*40GE QSFP28 ports, optional license for upgrade to 6*100GE QSFP28, without power module) for V6R21C10(TPM)
                Add: fname8031S6730-H24X6C-TV2(537564), --S6730-H24X6C-TV2(24*10GE SFP+ ports, 6*40GE QSFP28 ports, optional license for upgrade to 6*100GE QSFP28, without power module) for V6R21C10(TPM)
                Add: fname8031S6730-H48Y6C-V2(537565),  --S6730-H48Y6C-V2(48*25GE SFP28 ports, 6*100GE QSFP28 ports, without power module) for V6R21C10
                Add: fname8031S6730-H48Y6C-TV2(537566), --S6730-H48Y6C-TV2(48*25GE SFP28 ports, 6*100GE QSFP28 ports, without power module) for V6R21C10(TPM)
                Add: bname8031S6730-H48X6C-TV2(537747), --S6730-H48X6C-TV2(48*10GE SFP+ ports, 6*40GE QSFP28 ports, optional license for upgrade to 6*100GE QSFP28, without power module) for V6R21C10(TPM)
                Add: bname8031S6730-H24X6C-TV2(537748), --S6730-H24X6C-TV2(24*10GE SFP+ ports, 6*40GE QSFP28 ports, optional license for upgrade to 6*100GE QSFP28, without power module) for V6R21C10(TPM)
                Add: bname8031S6730-H48Y6C-V2(537749),  --S6730-H48Y6C-V2(48*25GE SFP28 ports, 6*100GE QSFP28 ports, without power module) for V6R21C10
                Add: bname8031S6730-H48Y6C-TV2(537750), --S6730-H48Y6C-TV2(48*25GE SFP28 ports, 6*100GE QSFP28 ports, without power module) for V6R21C10(TPM)
                Modify: bnameLSG7X24BX1E0(713479),      --LSG7G24SX1E0 -> LSG7X24BX1E0, --20-port 100/1000BASE-X (SFP), 4-port 100M/1G/10G (SFP/SFP+) interface card
                Add: bnameLSG7X48PX1E0(713487),         --48-port 10GBASE-X interface Optical/electrical composite line card (SFP+)
                "
		
		REVISION    "202106290000Z"
        DESCRIPTION "V11.61,
				Add: bnameCEMPUGFULL(688431),                 -- Finished Board Unit,CE16800,CE-MPUG-FULL,CE16800 Main Processing Unit G (full-width)				
				Add: bnameCEMPUGHALF(688432),                -- Finished Board Unit,CE16800,CE-MPUG-HALF,CE16800 Main Processing Unit G (half-width)
				Add: bnameCEMPUGFK(688433),                  -- Finished Board Unit,CE16800,CE-MPUG-FK,CE16800 Main Processing Unit G-FK (full-width)
				Add: bnameCEMPUGHK(688434),                  -- Finished Board Unit,CE16800,CE-MPUG-HK,CE16800 Main Processing Unit G-HK (half-width)
				Modify: subbnameCE98D8DQ(688145),       -- Manufactured Board,CE98D8DQ
                "
		
        REVISION    "202106231024Z"
        DESCRIPTION "V11.60,
                Add: virent8090DEVCR5DEDVE8N72(688680),   -- V8R21C00 for CR5DEDVE8N72(SBOM) 16-Port 50G/8-Port 100GBase-QSFP28 FlexE Integrated Line Processing Unit L(LPUI-1T2-L)
                Add: virent8090DEVME0DMSUFT078(688681),   -- V8R21C00 for ME0DMSUFT078(SBOM) Flexible Card Multi Service Unit(MSUF-1T2,2 sub-slots)
                Add: virent8090DEVME0DMSUFT079(688682),   -- V8R21C00 for ME0DMSUFT079(SBOM) Flexible Card Multi Service Unit(MSUF-1T2A,2 sub-slots)
                "
        REVISION    "202106221024Z"
        DESCRIPTION "V11.59,
                Add: fname8031S5735-L8T4X-IA1(537557), --S5735-L8T4X-IA1 (8*10/100/1000BASE-T ports, 4*10GE SFP+ ports, AC power) for V2R21C00
                Add: fname8031S5735-L8P4X-IA1(537558), --S5735-L8P4X-IA1 (8*10/100/1000BASE-T ports, 4*10GE SFP+ ports, PoE+, AC power) for V2R21C00
                Add: fname8031S5735-L24T4X-IA1(537559), --S5735-L24T4X-IA1 (24*10/100/1000BASE-T ports, 4*10GE SFP+ ports, AC power) for V2R21C00
                Add: fname8031S5735-L8T4S-QA1(537560), --S5735-L8T4S-QA1 (8*10/100/1000BASE-T ports, 4*GE SFP ports, AC power, Fanless) for V2R21C00
                Add: fname8031S5735-L24T4X-QA1(537561), --S5735-L24T4X-QA1 (24*10/100/1000BASE-T ports, 4*10GE SFP+ ports, AC power, Fanless) for V2R21C00
                Add: fname8031S5735-L24T4S-QA1(537562), --S5735-L24T4S-QA1 (24*10/100/1000BASE-T ports, 4*GE SFP ports, AC power, Fanless) for V2R21C00

                "
		
		REVISION "202106220000Z" 
        DESCRIPTION "V11.58
            Add: subbname8090DEVNetEngineA820M(225987),     --CARD NetEngine A820 M
        "
        
        REVISION "202106210000Z" 
        DESCRIPTION "V11.57
            Add: virentCP8PHST2MA00(229515),           -- V8R21C00 for CP8PHST2MA00(SBOM) NetEngine A820 M AC System (2*10GE+8*GE/FE(o)+8*GE/FE(e))
            Add: fnameNETENGINE-A820-M-AC(229518),       -- V8R21C00 for NETENGINE-A820-M chassis
        "
        REVISION "202106160000Z" 
        DESCRIPTION "V11.56
            Add: virent8090DEVCR5DLPUFME72(539127),   -- V8R21C00 for CR5DLPUFME72(SBOM) Flexible Card Line Processing Unit E(LPUF-480-E)
            Add: virent8090DEVCR5DLPUFM376(914342),   -- V8R21C00 for CR5DLPUFM376(SBOM) 24-Port GE-SFP/10GE-SFP+ Flexible Card Line Processing Unit(LPUI-483A-CM, Enable 12*10GE+12*GE by default, Supporting one sub-slot for flexible card)
            Add: virent8090DEVCR5DLPUFM377(948922),   -- V8R21C00 for CR5DLPUFM377(SBOM) 24-Port GE-SFP/10GE-SFP+ Flexible Card Line Processing Unit(LPUI-483-CM, Enable 12*10GE+12*GE by default, Supporting one sub-slot for flexible card)
        "
        
        REVISION    "202106150000Z"
        DESCRIPTION "V11.55, "

        
		 REVISION "202106120000Z" 
         DESCRIPTION "V11.54		
			Add: bnameCEL48XSFD-A(688427),                -- Finished Board Unit,CloudEngine 16800,CEL48XSFD-A,48-Port 10GE Interface Card (FD-A, SFP+)8)
		        Add: fnameCE6881H48S6CQ(688218),              -- Assembling Components,CloudEngine 6800,CE6881H-48S6CQ-F,CE6881H-48S6CQ-F switch (48*10G SFP+, 6*100G QSFP28, 2*AC power modules, 4*fan modules, port-side exhaust)
                        Add: bnameCE6881H48S6CQ(688428),              -- Assembling Components,CloudEngine 6800,CE6881H-48S6CQ-F,CE6881H-48S6CQ-F switch (48*10G SFP+, 6*100G QSFP28, 2*AC power modules, 4*fan modules, port-side exhaust)
			Add: fnameCE6863H48S6CQ(688225),              -- Assembling Components,CE6863H-48S6CQ-F,CE6863H-48S6CQ-F,CE6863H-48S6CQ-F switch (48*25GE SFP28, 6*100GE QSFP28, 2*AC power modules, 4*fan modules, port-side exhaust)
			Add: bnameCE6863H48S6CQ(688429),              -- Assembling Components,CE6863H-48S6CQ-F,CE6863H-48S6CQ-F,CE6863H-48S6CQ-F switch (48*25GE SFP28, 6*100GE QSFP28, 2*AC power modules, 4*fan modules, port-side exhaust)
			Add: fnameCE8850E32CQ(688226),                -- Assembling Components,CE8800,CE8850E-32CQ-EI-F,CE8850E-32CQ-EI Switch(32-Port 100GE QSFP28,1-Port 10GE SFP+,2*AC Power Module,2*FAN Box,Port-side Exhaust)
			Add: bnameCE8850E32CQ(688430),                -- Assembling Components,CE8800,CE8850E-32CQ-EI-F,CE8850E-32CQ-EI Switch(32-Port 100GE QSFP28,1-Port 10GE SFP+,2*AC Power Module,2*FAN Box,Port-side Exhaust)
		"

		REVISION "202106090000Z" 
         DESCRIPTION "V11.53
            Add: subbname8090DEVCR5D08CWDM70(564529),      --8-Channel CWDM Multiplexing &amp; Demultiplexing (1471/1491/1511/1531/1551/1571/1591/1611nm) Physical Interface Card(PIC)
            Add: subbname8090DEVCARDATN910CF(333111),      --CARD ATN910C-F
            Add: subbname8090DEVCARDETN500F(225669),       --CARD ETN500-F
            Add: subbname8090DEVCARDATN905(225666),        --CARD ATN 905
            Add: subbname8090DEVCARDATN910C-E(333112),     --CARD ATN 910C-E
            Add: subbname8090DEVCARDNE05E-SR(225670),      --CARD NE05E-SR
        "			
				
         REVISION "202106070000Z" 
         DESCRIPTION "V11.53
            Add: virent8090DEVTPSM0HOSTA1(249599),    -- V8R21C00 for TPSM0HOSTA1(SBOM)
            Add: virent8090DEVTPSM0HOSTD0(249699),    -- V8R21C00 for TPSM0HOSTD0(SBOM)
            Add: virent8090DEVTPSM0HOSTB1(249799),    -- V8R21C00 for TPSM0HOSTB1(SBOM)
            Add: virent8090DEVTND1MD1A(249899),       -- V8R21C00 for TND1MD1A(SBOM)
            Add: virent8090DEVCR5DLPUFF373(567862),   -- V8R21C00 for CR5DLPUFF373(SBOM)
            Add: virent8090DEVCR5DLPUFF372(567861),   -- V8R21C00 for CR5DLPUFF372(SBOM)
            Add: virent8090DEVCR57LPU2TE(675817),      -- V8R21C00 for CR57LPU2TE(SBOM)
        "				

         REVISION "202106040000Z" 
         DESCRIPTION "V11.52
           Add: fname8031S6730-H48X6C-V2(537540), --S6730-H48X6C-V2(48*10GE SFP+ ports, 6*40GE QSFP28 ports, optional license for upgrade to 6*100GE QSFP28, without power module) for V6R21C00
           Add: fname8031S6730-H24X6C-V2(537541), --S6730-H24X6C-V2(24*10GE SFP+ ports, 6*40GE QSFP28 ports, optional license for upgrade to 6*100GE QSFP28, without power module) for V6R21C00
           Add: bname8031S6730-H48X6C-V2(537724), --S6730-H48X6C-V2(48*10GE SFP+ ports, 6*40GE QSFP28 ports, optional license for upgrade to 6*100GE QSFP28, without power module) for V6R21C00
           Add: bname8031S6730-H24X6C-V2(537725), --S6730-H24X6C-V2(24*10GE SFP+ ports, 6*40GE QSFP28 ports, optional license for upgrade to 6*100GE QSFP28, without power module) for V6R21C00
        "
		
         REVISION    "202106040000Z"
         DESCRIPTION "V11.51,
            Add: fnameAirEngine6761-21(692368),   --WLAN R20C10 new AP ENUM_ 
            Add: fnameAirEngine5761R-11(692369),  --WLAN R20C10 new AP ENUM_
            Add: fnameAirEngine5761RS-11(692370), --WLAN R20C10 new AP ENUM_
            Add: fnameAirEngine5761R-11E(692371), --WLAN R20C10 new AP ENUM_
            Add: fnameAirEngine6761S-21(692372),  --WLAN R20C10 new AP ENUM_
            Add: fnameAirEngine5761S-12(692373),  --WLAN R20C10 new AP ENUM_
            Add: fnameAirEngine5761S-13(692374),  --WLAN R20C10 new AP ENUM_
            Add: bnameAirEngine6761-21(692368),   --WLAN R20C10 new AP ENUM_ 
            Add: bnameAirEngine5761R-11(692369),  --WLAN R20C10 new AP ENUM_
            Add: bnameAirEngine5761RS-11(692370), --WLAN R20C10 new AP ENUM_
            Add: bnameAirEngine5761R-11E(692371), --WLAN R20C10 new AP ENUM_
            Add: bnameAirEngine6761S-21(692372),  --WLAN R20C10 new AP ENUM_
            Add: bnameAirEngine5761S-12(692373),  --WLAN R20C10 new AP ENUM_
            Add: bnameAirEngine5761S-13(692374),  --WLAN R20C10 new AP ENUM_
            "

        REVISION    "202106030000Z"
        DESCRIPTION "V11.50,
                Add: fname8031CX600-X3A-E(532051),          -- Quidway CX600-3A PRO Carrier Switch
                Add: fname8031CX600-X3ADO-E(532052),        -- Quidway CX600-3ADO PRO Carrier Switch
                Add: fname8090NE40E-X3A-E(562050),          -- Quidwy Ne40E-3A PRO FRAME,
                Add: fnameME60-X3A-E(159788),               -- Quidway ME60-X3A-400G FRAME
                Add: fnamePTN6900-3A-E(229410),             --Integrated Chassis Components (PTN 6900-3A-400G)
                "
        REVISION    "202106010000Z"
        DESCRIPTION "V11.49,
                Add: bnamePTN7900TPD1FH8R(229628),   --TPD1FH8R, 8*100GE Packet Flexible Ethernet Service Processing Board
                Add: bnamePTN7900TPD7FH8(229629),    --TPD7FH8, 8*100GE Flexible Ethernet Service Processing Board
                Add: bnamePTN7900TPA7FV8(229630),    --TPA7FV8, 8*50GE Flexible Ethernet Service Processing Board
                Add: bnamePTN7900TPA7FH4(229631),    --TPA7FH4, 4*100GE Flexible Ethernet Service Processing Board
                Add: bnamePTN7900TPA7FV4(229632),    --TPA7FV4, 4*50GE  Flexible Ethernet Service Processing Board
                Add: bnamePTN7900TPA7FH2(229633),    --TPA7FH2, 2*100GE Flexible Ethernet Service Processing Board
                Add: bnamePTN7900TPD1FHD4R(229634),  --TPD1FHD4R, 4*200GE Flexible Ethernet Service Processing Board
                Add: bnamePTN7900TPD7FHD4(229635),   --TPD7FHD4, 4*200GE Flexible Ethernet Service Processing Board
                Add: bnamePTN7900TPA7FHD2(229636),   --TPA7FHD2, 2*200GE Flexible Ethernet Service Processing Board
                Add: bnamePTN7900TPA7FHD1(229637),   --TPA7FHD1, 1*200GE Packet Service Processing Board
                Add: bnamePTN7900TPA7EY16(229638),   --TPA7EY16, 16*25GE Ethernet Service Processing Board
                Add: bnamePTN7900TPA7EX16S(229639),  --TPA7EX16S, 16*10GE Ethernet Service Processing Board
                Add: bnamePTN7900TPA7EY8(229640),    --TPA7EY8, 8*25GE Ethernet Service Processing Board
                "

        REVISION    "202105280000Z"
        DESCRIPTION "V11.48,		  
               Add:bnameCESFU04GA(688426),                 -- Finished Board Unit,CE16800,CE-SFU04G-A,CE16804 Switch Fabric Unit G-A				   
	           "
	   
       
				
	    REVISION    "202105181800Z"
        DESCRIPTION "V11.47,		
			   Add: bnameFML18CQFD(716826),    -- FML18CQ-FD  board  
			   Add: bnameFM6865E48S8CQ(716827), --FM6865E-48S8CQ
			   Add: fnameFM6865E48S8CQ(716815). -- FM6865E-48S8CQ       
                "
        
		REVISION    "202105151520Z"
        DESCRIPTION "V11.46,
               Add: fnameNETENGINE-8000E-M8(688880),        -- NETENGINE-8000E-M8 (fnameNETENGINE-8000E-M8)
               Add: fnameNETENGINE-8000E-M8-AC(688882),     -- NETENGINE-8000E-M8-AC (fnameNETENGINE-8000E-M8-AC)
               Add: fnameNETENGINE-8000E-M8-DC(688881),     -- NETENGINE-8000E-M8-DC (fnameNETENGINE-8000E-M8-DC)
               Add: fnameNETENGINE-8000E-M14(688883),       -- NETENGINE-8000E-M14 (fnameNETENGINE-8000E-M14)
               Add: fnameNETENGINE-8000E-M14-AC(688884),    -- NETENGINE-8000E-M14-AC (fnameNETENGINE-8000E-M14-AC)
               Add: fnameNETENGINE-8000E-M14-DC(688885),    -- NETENGINE-8000E-M14-DC (fnameNETENGINE-8000E-M14-DC)
               Add: virent8090DEVCR8DIPU1T2CD(800010),       --V8R21C00 CR8DIPU1T2CD(SBOM) Integrated Network Processing Unit (IPUA-1T2-BN)
               Add: virent8090DEVCR8DIPU480C6(800009),    --V8R21C00 CR8DIPU480C6(SBOM) Integrated Network Processing Unit (IPUA-480-B)
                "
        REVISION    "202105061024Z"
        DESCRIPTION "V11.45,
               Add: fname8031S5735S-H24T4X-A(537542), --S5735S-H24T4X bundle(24*10/100/1000BASE-T ports, 4*10GE SFP+ ports, 1*AC power module) for V2R20C30
               Add: fname8031S5735S-H48T4X-A(537543), --S5735S-H48T4X bundle (48*10/100/1000BASE-T ports, 4*10GE SFP+ ports, 1*AC power module) for V2R20C30
               Add: fname8031S5735S-H24U4X-A(537544), --S5735S-H24U4X bundle (24*10/100/1000BASE-T ports, 4*10GE SFP+ ports, PoE++, 1*AC power module) for V2R20C30
               Add: fname8031S5735S-H48U4X-A(537545), --S5735S-H48U4X bundle (48*10/100/1000BASE-T ports, 4*10GE SFP+ ports, PoE++, 1*AC power module) for V2R20C30
               Add: fname8031S5735S-H24S4X-A(537546), --S5735S-H24S4X bundle (24*GE SFP ports, 4*10GE SFP+ ports, 1*AC power module) for V2R20C30
               Add: fname8031S5735S-H48S4X-A(537547), --S5735S-H48S4X bundle (48*GE SFP ports, 4*10GE SFP+ ports, 1*AC power module) for V2R20C30
               Add: fname8031S5735S-H48S4XC-A(537548), --S5735S-H48S4XC bundle (48*GE SFP ports, 4*10GE SFP+ ports, 1*expansion slot, 1*AC power module) for V2R20C30
               Add: fname8031S5735R-8P4S(537549), --S5735R-8P4S (8*10/100/1000BASE-T ports, 4*GE SFP ports, PoE+, AC power) for V2R20C30
               Add: fname8031S5735R-24T4X(537550), --S5735R-24T4X (24*10/100/1000BASE-T ports, 4*10GE SFP+ ports, AC power) for V2R20C30
               Add: fname8031S5735R-24T4S(537551), --S5735R-24T4S (24*10/100/1000BASE-T ports, 4*GE SFP ports, AC power) for V2R20C30
               Add: fname8031S5735R-24P4X(537552), --S5735R-24P4X (24*10/100/1000BASE-T ports, 4*10GE SFP+ ports, PoE+, AC power) for V2R20C30
               Add: fname8031S5735R-24P4S(537553), --S5735R-24P4S (24*10/100/1000BASE-T ports, 4*GE SFP ports, PoE+, AC power) for V2R20C30
               Add: fname8031S5735R-48T4S(537554), --S5735R-48T4S (48*10/100/1000BASE-T ports, 4*GE SFP ports, AC power) for V2R20C30
               Add: fname8031S5736-S48S4X-A(537555), --S5736-S48S4X-A base (48*GE SFP ports, optional RTU upgrade to 10G, 4*10GE SFP+ ports, AC power supply, front access) for V2R20C30
               Add: fname8031S5736-S48S4X-D(537556), --S5736-S48S4X-D base (48*GE SFP ports, optional RTU upgrade to 10G, 4*10GE SFP+ ports, DC power supply, front access) for V2R20C30
               Add: bname8031S5735S-H24T4X-A(537726), --S5735S-H24T4X bundle(24*10/100/1000BASE-T ports, 4*10GE SFP+ ports, 1*AC power module) for V2R20C30
               Add: bname8031S5735S-H48T4X-A(537727), --S5735S-H48T4X bundle (48*10/100/1000BASE-T ports, 4*10GE SFP+ ports, 1*AC power module) for V2R20C30
               Add: bname8031S5735S-H24U4X-A(537728), --S5735S-H24U4X bundle (24*10/100/1000BASE-T ports, 4*10GE SFP+ ports, PoE++, 1*AC power module) for V2R20C30
               Add: bname8031S5735S-H48U4X-A(537729), --S5735S-H48U4X bundle (48*10/100/1000BASE-T ports, 4*10GE SFP+ ports, PoE++, 1*AC power module) for V2R20C30
               Add: bname8031S5735S-H24S4X-A(537730), --S5735S-H24S4X bundle (24*GE SFP ports, 4*10GE SFP+ ports, 1*AC power module) for V2R20C30
               Add: bname8031S5735S-H48S4X-A(537731), --S5735S-H48S4X bundle (48*GE SFP ports, 4*10GE SFP+ ports, 1*AC power module) for V2R20C30
               Add: bname8031S5735S-H48S4XC-A(537732), --S5735S-H48S4XC bundle (48*GE SFP ports, 4*10GE SFP+ ports, 1*expansion slot, 1*AC power module) for V2R20C30
               Add: bname8031S5735R-8P4S(537733), --S5735R-8P4S (8*10/100/1000BASE-T ports, 4*GE SFP ports, PoE+, AC power) for V2R20C30
               Add: bname8031S5735R-24T4X(537734), --S5735R-24T4X (24*10/100/1000BASE-T ports, 4*10GE SFP+ ports, AC power) for V2R20C30
               Add: bname8031S5735R-24T4S(537735), --S5735R-24T4S (24*10/100/1000BASE-T ports, 4*GE SFP ports, AC power) for V2R20C30
               Add: bname8031S5735R-24P4X(537736), --S5735R-24P4X (24*10/100/1000BASE-T ports, 4*10GE SFP+ ports, PoE+, AC power) for V2R20C30
               Add: bname8031S5735R-24P4S(537737), --S5735R-24P4S (24*10/100/1000BASE-T ports, 4*GE SFP ports, PoE+, AC power) for V2R20C30
               Add: bname8031S5735R-48T4S(537738), --S5735R-48T4S (48*10/100/1000BASE-T ports, 4*GE SFP ports, AC power) for V2R20C30
               Add: bname8031S5736-S48S4X-A(537739), --S5736-S48S4X-A base (48*GE SFP ports, optional RTU upgrade to 10G, 4*10GE SFP+ ports, AC power supply, front access) for V2R20C30
               Add: bname8031S5736-S48S4X-D(537740), --S5736-S48S4X-D base (48*GE SFP ports, optional RTU upgrade to 10G, 4*10GE SFP+ ports, DC power supply, front access) for V2R20C30
                "
        REVISION    "202104291024Z"
        DESCRIPTION "V11.44,
               Add: virent8090DEVCR5DSFUIT27R(350117),   -- V8R21C00 for CR5DSFUIT27R(SBOM) 2Tbps Switch Fabric Unit P(SFUI-2TA-P)
               Add: virent8090DEVCX6DSFUIT27G(809173),   -- V8R21C00 for CX6DSFUIT27G(SBOM) 2Tbps Switch Fabric Unit P(SFUI-2T-P)
               Add: virent8090DEVTNRDSFUIT27Q(388472),   -- V8R21C00 for TNRDSFUIT27Q(SBOM) 2Tbps Switch Fabric Unit P(SFUI-2T-P)
               Add: virent8090DEVCR5DSFUITD73(194560),   -- V8R21C00 for CR5DSFUITD73(SBOM) 2Tbps Switch Fabric Unit Q(SFUI-2TA-Q)
               Add: virent8090DEVCX6DSFUIT270(977102),   -- V8R21C00 for CX6DSFUIT270(SBOM) 2Tbps Switch Fabric Unit Q(SFUI-2T-Q)
               Add: virent8090DEVTNRDSFUIT270(895279),   -- V8R21C00 for TNRDSFUIT270(SBOM) 2Tbps Switch Fabric Unit Q(SFUI-2T-Q)
               Add: virent8090DEVCR5DSRUAD271(973375),   -- V8R21C00 for CR5DSRUAD271(SBOM) Switch and Route Processing Unit A132A(32G Memory)
               Add: virent8090DEVCX6D0SRUAD72(841680),   -- V8R21C00 for CX6D0SRUAD72(SBOM) Switch and Route Processing Unit A132(32G Memory)
               Add: virent8090DEVTNRD0SRUAD72(744977),   -- V8R21C00 for TNRD0SRUAD72(SBOM) Switch and Route Processing Unit A132(32G Memory)
                "
        REVISION    "202104261500Z"
        DESCRIPTION "V11.43,
                Add: bnameLSS3MCUA1000(659743), --S9303 main control unit A1 for v2r21c00
                Add: bnameLSS7MCUA1000(663700), --S7703 main control unit A1 for v2r21c00
                "

        REVISION    "202104260000Z"
        DESCRIPTION "V11.42, "
        
        REVISION    "202104210000Z"
        DESCRIPTION "V11.41,
                Add: lanVPort(809),                   -- LAN virtual port of bord.
                Add: otnPort(810),                    -- physical port of otn board.
                "

        REVISION    "202104190000Z"
        DESCRIPTION "V11.40, "	

        REVISION    "202104160000Z"
        DESCRIPTION "V11.38,
                Modify: virent8090DEVCR5DLPUFT360(562186),    -- V8R21C00 for CR5DLPUFT360(SBOM) 3.2T Flexible Card Line Processing Unit CM(NE5000E LPUF-3T2-CM,2 sub-slots)
                Add: virent8090DEVCR5DSFUIT26J(562187),    -- V8R21C00 for CR5DSFUIT26J(SBOM) NE5000E-20 1.6T CLC Integrated Switch Fabric Unit for Multi-Chassis (SFUI-1T6-M)
                "				
        REVISION    "202104130000Z"
        DESCRIPTION "V11.38,
                Add: virent8090DEVCR5DLPUFM375(365445),   -- V8R21C00 for CR5DLPUFM375(SBOM) Flexible Card Line Processing Unit(LPUF-483-E-CM, enable slot 0 by default)
                Add: virent8090DEVME0DBSUFM073(425568),   -- V8R21C00 for ME0DBSUFM073(SBOM) Flexible Card Broadband Service Unit(BSUF-483-E,2 sub-slots)
                "
        REVISION    "202104100000Z"
        DESCRIPTION "V11.37,
                Add: virentANND01CXPA01(225663),         -- V8R13C00 for ANND01CXPA01(SBOM) ATN 980C,ANN2CXPA10,System Control,Cross-connect and Multi-protocol Process Unit with 800G
                Add: virent8090DEVME0DVSUF8072(161609),         -- V8R21C00 for ME0DVSUF8072(SBOM) Flexible Card Versatile Service Unit 80(VSUF-80-T)
                "
        REVISION    "202104060000Z"
        DESCRIPTION "V11.36,
                Modify: virent8090DEVCR8D00EENBCE(688669),    -- V8R21C00 for CR8D00EENBCE(SBOM) 20-Port 100GBase-QSFP28 MACsec Integrated Line Processing Unit CM(LPUI-2TA-CM)
                Modify: virent8090DEVCR8D00EENBCF(688670),    -- V8R21C00 for CR8D00EENBCF(SBOM) 20-Port 100GBase-QSFP28 MACsec Integrated Line Processing Unit CM(LPUI-2T-CM)
                Modify: virent8090DEVCR8D00EENBCB(688671),    -- V8R21C00 for CR8D00EENBCB(SBOM) 20-Port 100GBase-QSFP28 MACsec Integrated Line Processing Unit L CM(LPUI-2TA-L-CM)
                Modify: virent8090DEVCR8D00EENBCG(688672),    -- V8R21C00 for CR8D00EENBCG(SBOM) 20-Port 100GBase-QSFP28 MACsec Integrated Line Processing Unit L CM(LPUI-2T-L-CM)
                "
        REVISION    "202103310000Z"
        DESCRIPTION "V11.35,
                Add: fnameMA5801SGP16S1(148520),      --  Backplane of the MA5801S-GP16-S1.
                Add: fnameMA5801GP08H2(148521),       --  Backplane of the MA5801-GP08-H2.
                Add: bnameV931GPSF(148733),           --  16*GPON board of MA5801S-GP16-S1.
                Add: bnameV921GPHD(148734),           --  8*GPON board of MA5801-GP08-H2.
                "

        REVISION    "202103310000Z"
        DESCRIPTION "V11.34,
               Add: virent8090DEVCR5DLPUFT360(562186),
                "
		
		REVISION    "202103290000Z"
        DESCRIPTION "V11.33,
				Add:bnameAR720(668121),           --AR720 Main Control Unit
				Add:bnameAR730(668122),           --AR730 Main Control Unit
				Add:bnameSRU-60H(668123),         --SRU-60H Main Control Unit
				Add:bnameSRU-80H(668124),         --SRU-80H Main Control Unit
				Add:bnameAR611-S(668125),         --AR611-S Main Control Unit
				Add:bnameAR611W-S(668126),        --AR611W-S Main Control Unit
				Add:bnameAR303(668127),           --AR303 Main Control Unit
				Add:bnameAR303W(668128),          --AR303W Main Control Unit
				Add:bnameAR6121EC-S(668129),      --AR6121EC-S Main Control Unit
				Add:bnameAR6121E-S(668130),       --AR6121E-S Main Control Unit
				Add:bnameAR6140E-S(668131),       --AR6140E-S Main Control Unit
				Add:bnameSRG1311(668132),         --SRG1311 Main Control Unit
				Add:bnameSRG1340E(668133),        --SRG1340E Main Control Unit
				Add:bnameAR611(668134),           --AR611 Main Control Unit
				Modify:bnameSRU10-FusionCube(668112) --SRU10-FusionCube Main Control Unit to bnameAR10(668112),   --AR10 Main Control Unit
				Add:fnameAR720(668018),           --AR720 FRAME
				Add:fnameAR730(668019),           --AR730 FRAME
				Add:fnameAR6280C-S(668020),       --AR6280C-S FRAME
				Add:fnameAR6300C-S(668021),       --AR6300C-S FRAME
				Add:fnameAR611-S(668022),         --AR611-S FRAME
				Add:fnameAR611W-S(668023),   	  --AR611W-S FRAME
				Add:fnameAR303(668024),           --AR303 FRAME
				Add:fnameAR303W(668025),   	      --AR303W FRAME
				Add:fnameAR6121EC-S(668026),   	  --AR6121EC-S FRAME
				Add:fnameAR6121E-S(668027),   	  --AR6121E-S FRAME
				Add:fnameAR6140E-S(668028),   	  --AR6140E-S FRAME
				Add:fnameSRG1311(668029),   	  --SRG1311 FRAME
				Add:fnameSRG1340E(668030),   	  --SRG1340E FRAME
				Add:fnameAR611(668031),   	      --AR611 FRAME
				Modify:fnameSRU10-FusionCube(668009) --SRU10-FusionCube FRAME to fnameAR10(668009),   --AR10 FRAME
				Modify:bnameAR6140E-S(668100),    --AR6140E-S Main Control Unit to bnameAR6140H-S(668100),    --AR6140H-S Main Control Unit
				Modify:fnameAR6140E-S(667998),    --AR6140E-S FRAME to fnameAR6140H-S(667998),    --AR6140H-S FRAME"
					
        REVISION    "202103290000Z"
        DESCRIPTION "V11.32,
                Add: bnameLSS7M24VX6E0(663709), --24-port 100M/1G/2.5G/5G/10G and 24-port 100M/1G interface card (X6E,RJ45,PoE++) for v2r21c00
                Add: bnameLSS3M24VX6E0(659753), --24-port 100M/1G/2.5G/5G/10G and 24-port 100M/1G interface card (X6S,RJ45,PoE++) for v2r21c00
                Add: bnameLSS7M24VX6S0(663710), --24-port 100M/1G/2.5G/5G/10G and 24-port 100M/1G interface card (X6S,RJ45,PoE++) for v2r21c00
                Add: bnameLSS7G48VX6E00(663711), --48-port 100/1000BASE-T interface card (X6E,RJ45,PoE++) for v2r21c00
                Add: bnameLSS7G48VX6EK0(663712), --48-port 100/1000BASE-T interface card (AK,RJ45,PoE++) for v2r21c00
                Add: bnameLSS7M24BX6E0(663713), --24-port 100M/1G/2.5G/5G/10G and 24-port 100M/1G interface card (X6E,RJ45) for v2r21c00
                Add: bnameLSS7M24BX6EK0(663714), --24-port 100M/1G/2.5G/5G/10G and 24-port 100M/1G interface card (AK,RJ45) for v2r21c00
                Add: bnameLST7M24BX6E0(700557), --24-port 100M/1G/2.5G/5G/10G and 24-port 100M/1G interface card (X6E,RJ45) for v2r21c00
                Add: bnameLST7M24BX6EK0(700558), --24-port 100M/1G/2.5G/5G/10G and 24-port 100M/1G interface card (AK,RJ45) for v2r21c00
                Add: bnameLST3M24BX6E0(659754), --24-port 100M/1G/2.5G/5G/10G and 24-port 100M/1G interface card (X6E,RJ45) for v2r21c00
                Add: bnameLSS7M24BX6S0(663715), --24-port 100M/1G/2.5G/5G/10G and 24-port 100M/1G interface card (X6S,RJ45) for v2r21c00
                Add: bnameLSS7G48TX6E0(663716), --48-port 100/1000BASE-T interface card (X6E,RJ45) for v2r21c00
                Add: bnameLSS3G48TX6E0(659755), --48-port 100/1000BASE-T interface card (X6E,RJ45) for v2r21c00
                Add: bnameLST7G48TX6E0(700559), --48-port 100/1000BASE-T interface card (X6E,RJ45) for v2r21c00
                Add: bnameLST3G48TX6E0(659756), --48-port 100/1000BASE-T interface card (X6E,RJ45) for v2r21c00
                Add: bnameLST7G48TX6S0(700560), --48-port 100/1000BASE-T interface card (X6S,RJ45) for v2r21c00
                Add: bnameLST3G48TX6S0(659757), --48-port 100/1000BASE-T interface card (X6S,RJ45) for v2r21c00
                Add: subnamePDC1000S56-CB(536817),    --POE1000W DC Power Module (Back to Front, Power panel side exhaust) for v2r21c00
                    "

        REVISION    "202103290000Z"
        DESCRIPTION "V11.31,
                bnameLSS3L12QX6E0(659758), --12-port 40GE QSFP+ inferface card (X6E,QSFP28) for v2r21c00
                bnameLST3L12QX6E0(659759), --12-port 40GE QSFP+ inferface card (X6E,QSFP28) for v2r21c00
                bnameLST7L12QX6E0(700561), --12-port 40GE QSFP+ inferface card (X6E,QSFP28) for v2r21c00
                bnameLST7L12QX6EK0(700562), --12-port 40GE QSFP+ inferface card (AK,QSFP28) for v2r21c00
                bnameLSS7L12QX6E0(663717), --12-port 40GE QSFP+ inferface card (X6E,QSFP28) for v2r21c00
                    "

        REVISION    "202103260000Z"
        DESCRIPTION "V11.30,
                    Add: fnameMA5801FL16H1(148523),       --  Backplane of the MA5801-FL16-H1.
                    Add: bnameV921MPCB(148737),           --  control board of MA5801-FL16-H1.
                    Add: fnameMA5801CG16H1(148522),       --  Backplane of the MA5801-CG16-H1.
                    Add: bnameV921CGHF(148735),           --  16*GPON board of MA5801-CG16-H1.
                    "

        REVISION    "202103230000Z"
        DESCRIPTION "V11.29
                   Add:virent8090DEVCR5D0MPUB974(688673),    -- V8R21C00 for CR5D0MPUB974(SBOM) Main Processing Unit B92A(32G Memory)
                   Add:virent8090DEVCR5D0MPUB975(688674),    -- V8R21C00 for CR5D0MPUB975(SBOM) Main Processing Unit B92(32G Memory)
                   Add:virent8090DEVME0D0MPUB974(688675),    -- V8R21C00 for ME0D0MPUB974(SBOM) Main Processing Unit B92A(32G Memory)
                   Add:virent8090DEVME0D0MPUB975(688676),    -- V8R21C00 for ME0D0MPUB975(SBOM) Main Processing Unit B92(32G Memory)
                   Add:virent8090DEVTNRD0MPUB975(688677),    -- V8R21C00 for TNRD0MPUB975(SBOM) Main Processing Unit B92(32G Memory)
                   Add:virent8090DEVCX6D0MPUB974(688678),    -- V8R21C00 for CX6D0MPUB974(SBOM) Main Processing Unit B92A(32G Memory)
                   Add:virent8090DEVCX6D0MPUB975(688679)    -- V8R21C00 for CX6D0MPUB975(SBOM) Main Processing Unit B92(32G Memory)
                    "

        REVISION    "202103230000Z"
        DESCRIPTION "V11.28
                    Add:fnameUSG6501E-C-O,
                    Add:fnameUSG6502E-C-O,
                    Add:fnameUSG6503E-C-O,
                    Add:fnameUSG6585E-O-AC,
                    Add:fnameUSG6575E-B-O-AC,
                    Add:fnameUSG6603F-C,
                    Add:bnameSPUB-USG-01,
                    Add:bnameSPUB-USG-02,
                    Add:bnameSPUB-USG-TP-01,
                    Add:bnameSPUB-USG-TP-02,
                    Add:bnameSPUB-E9KE-01,
                    Add:bnameSPUB-E9KE-02,
                    Add:bnameSPUB-E9KE-TP-01,
                    Add:bnameSPUB-E9KE-TP-02,
                    Add:bnameSPUB-IPS-01,
                    Add:bnameSPUB-IPS-02,
                    Add:bnameSPUB-ADS-01,
                    Add:bnameSPUB-ADS-02,
                    Add:bnameUSG6603F-C-AC,
                    Add:subbnameSPCB-USG-01,
                    Add:subbnameSPCB-USG-02,
                    Add:subbnameSPCB-USG-TP-01,
                    Add:subbnameSPCB-USG-TP-02,
                    Add:subbnameSPCB-E9KE-01,
                    Add:subbnameSPCB-E9KE-02,
                    Add:subbnameSPCB-E9KE-TP-01,
                    Add:subbnameSPCB-E9KE-TP-02,
                    Add:subbnameSPCB-IPS-01,
                    Add:subbnameSPCB-IPS-02,
                    Add:subbnameSPCB-ADS-01,
                    Add:subbnameSPCB-ADS-02,
					"

		REVISION    "202103190000Z"
        DESCRIPTION "V11.27,
            Add: bnameH903OXEG(156012),         --  24*10GE board of MA5800.
            Add: bnameH901OTHF(148728),         --  DN_ODN board of MA5800.
            Add: subbnameH901OTD2(148521),      --  OTDR subboard of MA5800 H901OTHF.
			Del: bnameV923NXHCE(148731),        --  4*10GE/GE board of EA5801E-GP16.
        "

	   REVISION    "202103170000Z"
       DESCRIPTION "V11.26,
               Add:virent8090DEVCR5D0SRUAE73(688650),    -- V8R13C00 for CR5D0SRUAE73(SBOM) Switch and Route Processing Unit A141(SRUA-1T-E, 32G Memory)
               Add:virent8090DEVCX6D0SRUAI72(688651),    -- V8R13C00 for CX6D0SRUAI72(SBOM) Switch and Route Processing Unit A141(SRUA-1T-E, 32G Memory)
               Add:virent8090DEVTNRD0SRUAI72(688652),    -- V8R13C00 for TNRD0SRUAI72(SBOM) Switch and Route Processing Unit A141(SRUA-1T-E, 32G Memory)
               Add:virent8090DEVCX6D0SRUAI12(688653),    -- V8R13C00 for CX6D0SRUAI12(SBOM) Switch and Route Processing Unit A141A(SRUA-1TA-E, 32G Memory)
               Add:virent8090DEVME0D0SRUAH72(688654),    -- V8R13C00 for ME0D0SRUAH72(SBOM) Switch and Route Processing Unit A19A(SRUA-480A-H, 32G Memory)
               Add:virent8090DEVME0D0SRUAH73(688655),    -- V8R13C00 for ME0D0SRUAH73(SBOM) Switch and Route Processing Unit A19(SRUA-480-H, 32G Memory)
               Add:virent8090DEVME0D0SRUAI72(688656),    -- V8R13C00 for ME0D0SRUAI72(SBOM) Switch and Route Processing Unit A141(SRUA-1T-E, 32G Memory)
               Add:virent8090DEVME0D0SRUAI73(688657),    -- V8R13C00 for ME0D0SRUAI73(SBOM) Switch and Route Processing Unit A141A(SRUA-1TA-E, 32G Memory)
               Add:virent8090DEVCR5D0SRUAJ70(688658),    -- V8R13C00 for CR5D0SRUAJ70(SBOM) Switch and Route Processing Unit A19A(SRUA-480A-H, 32G Memory)
               Add:virent8090DEVCR5D0SRUAJ71(688659),    -- V8R13C00 for CR5D0SRUAJ71(SBOM) Switch and Route Processing Unit A19(SRUA-480-H, 32G Memory)
               Add:virent8090DEVCX6D0SRUAH72(688660),    -- V8R13C00 for CX6D0SRUAH72(SBOM) Switch and Route Processing Unit A19(SRUA-480-H, 32G Memory)
               Add:virent8090DEVTNRD0SRUAH72(688661),    -- V8R13C00 for TNRD0SRUAH72(SBOM) Switch and Route Processing Unit A19(SRUA-480-H, 32G Memory)
               Add:virent8090DEVCX6D0SRUAH12(688662),    -- V8R13C00 for CX6D0SRUAH12(SBOM) Switch and Route Processing Unit A19A(SRUA-480A-H, 32G Memory)
               Add:virent8090DEVCR5DVSUFK0K3(688663),    -- V8R13C00 for CR5DVSUFK0K3(SBOM) Integrated Service Unit 400(VSUI-400-K)
               Add:virent8090DEVCX6D0MPUB911(688664),    -- V8R13C00 for CX6D0MPUB911(SBOM) Main Processing Unit B91A(32G Memory)
               Add:virent8090DEVME0D0MPUB971(688665),    -- V8R13C00 for ME0D0MPUB971(SBOM) Main Processing Unit B91(32G Memory)
               Add:virent8090DEVME0DSFUIM07K(688666),    -- V8R13C00 for ME0DSFUIM07K(SBOM) 480Gbps Switch Fabric Unit N(SFUI-480A-N)
               Add:virent8090DEVME0DSFUIM07L(688667),    -- V8R13C00 for ME0DSFUIM07L(SBOM) 480Gbps Switch Fabric Unit N(SFUI-480-N)
               Add:virent8090DEVCX6DISUFT012(688668),    -- V8R13C00 for CX6DISUFT012(SBOM) Flexible Card Integrated Service Unit(ISUF-1TA)
	   "	
	   REVISION    "202103130000Z"
       DESCRIPTION "V11.25,
		   Add: virent8090DEVCR8DVSUPA0C0(676993),    -- V8R21C00 for CR8DVSUPA0C0(SBOM) Integrated Service Card VSUP-100
		   Add: virent8090DEVCR8DVSUPA0C1(676994),    -- V8R21C00 for CR8DVSUPA0C1(SBOM) Integrated Service Card VSUPA-100					 		   
	   "	
	   REVISION    "202103120000Z"
       DESCRIPTION "V11.24,
           Add: bnameFML36CQFD1(716825),         -- 
		   Add: bnameCE588248T4S(688422),        -- Assembling Components,CloudEngine 6800,CE6866-48S8CQ-F,CE6865E-48S8CQ-F switch (48*25G SFP28, 8*100G QSFP28, 2*AC power modules, 4*fan modules, port-side exhaust)
		   Add: fnameCE588248T4S(688223),        -- Assembling Components,CloudEngine 6800,CE6866-48S8CQ-F,CE6865E-48S8CQ-F switch (48*25G SFP28, 8*100G QSFP28, 2*AC power modules, 4*fan modules, port-side exhaust)
		   Add: subbnameCE98D8DQD(688145),       -- Manufactured Board,CE98D8DQD		  
		   Add: bnameCEL36LQFDA(688423),         -- Finished Board Unit,CloudEngine 16800,CEL36LQFD-A,36-Port 40GE Interface Card (FD-A, QSFP+)
		   Add: bnameCESFU04FA(688424),          -- Finished Board Unit,CE16800,CESFU04F-A,CE16804 Switch Fabric Unit F-A
		   Add:bnameCESFU08FA(688425),          -- Finished Board Unit,CE16800,CESFU08F-A,CE16808 Switch Fabric Unit F-A						 		   
	   "
      
       REVISION    "202103110000Z"
       DESCRIPTION "V11.23, "

       REVISION    "202103090000Z"
       DESCRIPTION "V11.22, "

        REVISION    "202103080000Z"
        DESCRIPTION "V11.20
                     Add: virent8090DEVCR5DSFUIT350(562183),    -- V8R21C00 for CR5DSFUIT350(SBOM) NE5000E CCC-A 3.2T Cluster Central Switch Fabric Unit (SFUI-3T2-C)
                     Add: virent8090DEVCR5DSFUIT361(562184),    -- V8R21C00 for CR5DSFUIT361(SBOM) NE5000E-20 3.2T CLC Integrated Switch Fabric Unit for Multi-Chassis (SFUI-3T2-M)
                     Add: virent8090DEVCR5DSFUIT360(562185),    -- V8R21C00 for CR5DSFUIT360(SBOM) NE5000E-20 3.2T CLC Switch Fabric Unit for Single Chassis(SFU-3T2-S)
                     Add: virent8090DEVCR5D0MPUA950(567024),   --NE5000E V8R21C00 for NetEngine5000E CCC-A Cluster Central Main Processing Unit A9
                     Add: virent8090DEVCR5D0MPUA951(567025),   --NE5000E V8R21C00 for NetEngine5000E CCC-A Cluster Central Main Processing Unit A9
		 "

        REVISION    "202103050000Z"
        DESCRIPTION "V11.19
                    Add:bnameH901ACSA(148549),         -- Access Edge Computing board of MA5800.
                    Add:bnameH903XGLF(156013),         -- 16*XG GPON board of MA5800.
                    Add:bnameH903CSHFE(156014),        -- 16*XGS GPON and GPON combo board of EA5800.
                    Add:bnameH903FLHFE(156015),        -- 16*flex-PON board of EA5800.
                    Add:bnameH903GPHFE(156016),        -- 16*GPON board of EA5800.
                    Add:bnameH903XEHF(156017),         -- 16*10G EPON board of MA5800.
                    Add:bnameH903GPSF(156018),         -- 16*GPON board of MA5800.
                    Add:bnameH903XSHF(156019),         -- 16*10G XGS-PON board of MA5800.
                "

       REVISION    "202103030000Z"
       DESCRIPTION "V11.19,
           Add: fnameCE5855F48T4S2Q(688219),         -- 
		   Add: fnameCE6857F48S6CQ(688220),          -- 
		   Add: fnameCE6857F48T6CQ(688221),          -- 
		   Add: fnameCE6863E48S6CQ(688222),          -- 
		   Add: fnameFM686548S8CQSI(716814),         --
		   Add: bnameCE5855F48T4S2Q(688412),         -- 
		   Add: bnameCE6857F48S6CQ(688413),          -- 
		   Add: bnameCE6857F48T6CQ(688414),          -- 
		   Add: bnameCE6863E48S6CQ(688415),          -- 
		   Add: bnameCESFU16JX(688416),              -- Finished Board Unit,CE16800,CE-SFU16J-X,CE16816 Switch Fabric Unit J-X
		   Add: bnameCESFU08JX(688417),              -- Finished Board Unit,CE16800,CE-SFU08J-X,CE16808 Switch Fabric Unit J-X
		   Add: bnameCESFU08GE(688418),              -- Finished Board Unit,CloudEngine 16800,CE-SFU08G-E,CE16808 Switch Fabric Unit G-E
		   Add: bnameCEL18CQFDE(688419),             -- Finished Board Unit, CloudEngine 16800, CEL48CQHG-P, 48-port 100GE interface card (HG-P, QSFP28) (CM)
		   Add: bnameCEL48XSFDE(688420),             -- Finished Board Unit,CloudEngine 16800,CEL48XSFD-E,48-port 10GE interface card (FD-E, SFP+)
                   Add: bnameFM686548S8CQSI(716824),
		   Add: bnamePDC3000WA(688421),              -- 
	   "
				
        REVISION    "202103020000Z"
                DESCRIPTION "V11.18
                    Add:fnameNE40E-X2-M14-AC(688351),         --Quidway fnameNE40E-X2-M14-AC FRAME for V8R12C00
                    Add:fnameNE40E-X2-M14-DC(688352),         --Quidway fnameNE40E-X2-M14-DC FRAME for V8R12C00
                    Add:fnamePTN6900-2-M14-AC(688353),         --Quidway fnamePTN6900-2-M14-AC FRAME for V8R12C00
                    Add:fnamePTN6900-2-M14-DC(688354),         --Quidway fnamePTN6900-2-M14-DC FRAME for V8R12C00
                    Add:fnameNE40E-X2-M14-2AC(688359),     -- Quidway fnameNE40E-X2-M14-2AC FRAME for V8R21C00
                    Add:fnameNE40E-X2-M14-4AC(688360),     -- Quidway fnameNE40E-X2-M14-4AC FRAME for V8R21C00
                    Add:fnamePTN6900-2-M14-2AC(688361),     -- Quidway fnamePTN6900-2-M14-2AC FRAME for V8R21C00
                    Add:fnamePTN6900-2-M14-4AC(688362),     -- Quidway fnamePTN6900-2-M14-4AC FRAME for V8R21C00
                    Add:virent8090DEVIG2D00SPUG07(688648),    -- V8R13C00 for IG2D00SPUG07(SBOM) High Performance X8A&X16A Service Processing Unit-SPUGA,with HW Service Inspection Gateway Software
                "
        REVISION    "202102240000Z"
                DESCRIPTION "V11.17
                    Add:bnameH901MPLG(148732),                --  control board of MA5800-X17.
                    Add:bnameH901TNSC(148750),                --  4*OTN board of MA5800.
                "

		REVISION    "202102220000Z"
        DESCRIPTION "V11.16
				Add:bnameAR651K(668113),                 --AR651K Main Control Unit
				Add:bnameAR6140K-9G-2AC(668114),         --AR6140K-9G-2AC Main Control Unit
				Add:bnameAR6121K(668115),        		 --AR6121K Main Control Unit
				Add:bnameSRU-600HK(668116),        		 --SRU-600HK Main Control Unit
				Add:bnameSRU-400HK(668117),        		 --SRU-400HK Main Control Unit
				Add:bnameSRG1340-16G4XG(668119),         --SRG1340-16G4XG Main Control Unit
				Add:bnameSRG1321(668120),                --SRG1321 Main Control Unit
				Add:fnameAR651K(668010),                 --AR651K FRAME
				Add:fnameAR6140K-9G-2AC(668011),   	     --AR6140K-9G-2AC FRAME
				Add:fnameAR6121K(668012),                --AR6121K FRAME
				Add:fnameAR6280K(668013),                --AR6280K FRAME
				Add:fnameAR6300K(668014),                --AR6300K FRAME
				Add:fnameSRG1340-16G4XG(668016),         --SRG1340-16G4XG FRAME
				Add:fnameSRG1321(668017),                --SRG1321 FRAME
				modify:bnameAR6140E-9G-2AC(668110),      --AR6140E-9G-2AC Main Control Unit
				modify:bnameAR6121E(668111),             --AR6121E Main Control Unit
				modify:fnameAR6140E-9G-2AC(668007),      --AR6140E-9G-2AC FRAME
				modify:fnameAR6121E(668008),   	         --AR6121E FRAME
        "
                
        REVISION    "202102200000Z"
        DESCRIPTION "V11.15,
                Add:virent8090DEVCR5DMPUX8673(688620),    -- V8R13C00 for CR5DMPUX8673(SBOM) Main Processing Unit B11A(32G Memory)
                Add:virent8090DEVME0DMPUX8673(688621),    -- V8R13C00 for ME0DMPUX8673(SBOM) Main Processing Unit B11A(32G Memory)
                Add:virent8090DEVCR5DMPUX8672(688622),    -- V8R13C00 for CR5DMPUX8672(SBOM) Main Processing Unit B11(32G Memory)
                Add:virent8090DEVCX6DMPUX8672(688623),    -- V8R13C00 for CX6DMPUX8672(SBOM) Main Processing Unit B11(32G Memory)
                Add:virent8090DEVTNRDMPUX8672(688624),    -- V8R13C00 for TNRDMPUX8672(SBOM) Main Processing Unit B11(32G Memory)
                Add:virent8090DEVME0DMPUX8672(688625),    -- V8R13C00 for ME0DMPUX8672(SBOM) Main Processing Unit B11(32G Memory)
                Add:virent8090DEVCR5D0SRUAI70(688626),    -- V8R13C00 for CR5D0SRUAI70(SBOM) Switch and Route Processing Unit A18A(SRUA-1TA-F, 32G Memory)
                Add:virent8090DEVME0D0SRUAI70(688627),    -- V8R13C00 for ME0D0SRUAI70(SBOM) Switch and Route Processing Unit A18A(SRUA-1TA-F, 32G Memory)
                Add:virent8090DEVCR5D0SRUAI71(688628),    -- V8R13C00 for CR5D0SRUAI71(SBOM) Switch and Route Processing Unit A18(SRUA-1T-F, 32G Memory)
                Add:virent8090DEVCX6D0SRUAI71(688629),    -- V8R13C00 for CX6D0SRUAI71(SBOM) Switch and Route Processing Unit A18(SRUA-1T-F, 32G Memory)
                Add:virent8090DEVTNRD0SRUAI71(688630),    -- V8R13C00 for TNRD0SRUAI71(SBOM) Switch and Route Processing Unit A18(SRUA-1T-F, 32G Memory)
                Add:virent8090DEVME0D0SRUAI71(688631),    -- V8R13C00 for ME0D0SRUAI71(SBOM) Switch and Route Processing Unit A18(SRUA-1T-F, 32G Memory)
                Add:virent8090DEVCR5D0SRUAH70(688632),    -- V8R13C00 for CR5D0SRUAH70(SBOM) Switch and Route Processing Unit A17A(SRUA-480A-G, 32G Memory)
                Add:virent8090DEVME0D0SRUAH70(688633),    -- V8R13C00 for ME0D0SRUAH70(SBOM) Switch and Route Processing Unit A17A(SRUA-480A-G, 32G Memory)
                Add:virent8090DEVCR5D0SRUAH71(688634),    -- V8R13C00 for CR5D0SRUAH71(SBOM) Switch and Route Processing Unit A17(SRUA-480-G, 32G Memory)
                Add:virent8090DEVCX6D0SRUAH71(688635),    -- V8R13C00 for CX6D0SRUAH71(SBOM) Switch and Route Processing Unit A17(SRUA-480-G, 32G Memory)
                Add:virent8090DEVTNRD0SRUAH71(688636),    -- V8R13C00 for TNRD0SRUAH71(SBOM) Switch and Route Processing Unit A17(SRUA-480-G, 32G Memory)
                Add:virent8090DEVME0D0SRUAH71(688637),    -- V8R13C00 for ME0D0SRUAH71(SBOM) Switch and Route Processing Unit A17(SRUA-480-G, 32G Memory)
                Add:virent8090DEVCX6DMPUX8613(688638),    -- V8R13C00 for CX6DMPUX8613(SBOM) Main Processing Unit B11A(32G Memory)
                Add:virent8090DEVCX6D0SRUAI11(688639),    -- V8R13C00 for CX6D0SRUAI11(SBOM) Switch and Route Processing Unit A18(SRUA-1T-F, 32G Memory)
                Add:virent8090DEVCX6D0SRUAH11(688640),    -- V8R13C00 for CX6D0SRUAH11(SBOM) Switch and Route Processing Unit A17(SRUA-480-G, 32G Memory)
                Add:virent8090DEVCR5D0MPUB973(688641),    -- V8R13C00 for CR5D0MPUB973(SBOM) Main Processing Unit B91A(32G Memory)
                Add:virent8090DEVCR5D0SRUAE72(688642),    -- V8R13C00 for CR5D0SRUAE72(SBOM) Switch and Route Processing Unit A141A(SRUA-1TA-E, 32G Memory)
                Add:fnameNETENGINE-8000-F2A-8K36H(688643),    --Quidway fnameNETENGINE-8000-F2A-8K36H FRAME for V8R21C00
                Add:fnameNETENGINE-8000-F2A-8K36H-AC(688644), --Quidway fnameNETENGINE-8000-F2A-8K36H-AC FRAME for V8R21C00
                Add:fnameNETENGINE-8000-F2A-8K36H-DC(688645), --Quidway fnameNETENGINE-8000-F2A-8K36H-DC FRAME for V8R21C00
                Add:virent600DEVCR8P0BKP03C0(688646),    -- V8R21C00 CR8P0BKP03C0(SBOM) NetEngine 8000 F2A-8K36H Integrated Chassis Components(Port-side Intake)
                Add:virent600DEVCR8P0BKP03C1(688647),    -- V8R21C00 CR8P0BKP03C1(SBOM) NetEngine 8000 F2A-8K36H Integrated Chassis Components(Port-side Exhaust)
            "
        REVISION    "202102070000Z"
        DESCRIPTION "V11.14,
                Add:virent8090DEVCR5D00EENB74(688615),    -- V8R13C00 for CR5D00EENB74(SBOM) 8-Port 20-Port 100GBase-QSFP28 Integrated Line Processing Unit (LPUI-2TA)
                Add:virent8090DEVCR5D00EENB75(688616),    -- V8R13C00 for CR5D00EENB75(SBOM) 8-Port 20-Port 100GBase-QSFP28 Integrated Line Processing Unit L(LPUI-2T-L)
                Add:virent8090DEVCR5D00EENB7R(688617),    -- V8R13C00 for CR5D00EENB7R(SBOM) 8-Port 20-Port 100GBase-QSFP28 FlexE/MACsec Integrated Line Processing Unit CM(LPUI-2T-CM)
                Add:virent8090DEVCR5D00EENBK4(688618)    -- V8R13C00 for CR5D00EENBK4(SBOM) 8-Port 20-Port 100GBase-QSFP28 Integrated Line Processing Unit(LPUI-2T-K)
                Add:virent8090DEVIG2D00EENB05(688619),    -- V8R13C00 for IG2D00EENB05(SBOM) 20-Port 100GBase-QSFP28 Integrated Line Processing Unit (LPUI-2TA)
                Add:fnameATNDEV910C-H-AC(225622), --910C-H-AC chassis
                Add:fnameATNDEV910C-S-AC(225623), --910C-S-AC chassis
                Add:virentANGMHSTH0200(225615), -- ATN 910C-H,ANGMHSTH0200,ATN 910C-H AC Basic Configuration(Includes Fixed Enable Interface (4*10GE/GE/FE(o)+4*GE/FE(o)+4*GE/FE(e))/Dual Power/FAN/Chassis)
                Add:virentANGMHSTS0200(225616), -- ATN 910C-S,ANGMHSTS0200,ATN 910C-S AC Basic Configuration(Includes Fixed Enable Interface (5*10GE/GE/FE(o)+3*GE/FE(o)+4*GE/FE(e))/Dual Power/FAN/Chassis)
				Add:virent8090DEVME0DMSUFT076(686959),    -- V8R13C00 for ME0DMSUFT076(SBOM) Flexible Card Broadband Service Unit(BSUF-1T2,2 sub-slots)
                Add:virent8090DEVME0DMSUFT077(686960),    -- V8R13C00 for ME0DMSUFT077(SBOM) Flexible Card Broadband Service Unit(BSUF-1T2A,2 sub-slots)
                Add:virent8090DEVIG2DLPUFM305(686961),    -- V8R13C00 for IG2DLPUFM305(SBOM) Flexible Card Line Processing Unit (LPUF-483A)
                Add:virent8090DEVIG2DLPUFT005(686963),    -- V8R13C00 for IG2DLPUFT005(SBOM) Flexible Card Line Processing Unit (LPUF-1T2A)
                Add:virent8090DEVCR5D00E8NB7R(686964),    -- V8R13C00 for CR5D00E8NB7R(SBOM) 16-Port 50G/8-Port 100GBase-QSFP28 FlexE/MACsec Integrated Line Processing Unit CM(LPUI-1T2-CM)
                Add:virent8090DEVCR5D00E8NB7S(686965),    -- V8R13C00 for CR5D00E8NB7S(SBOM) 16-Port 50G/8-Port 100GBase-QSFP28 FlexE/MACsec Integrated Line Processing Unit CM(LPUI-1T2A-CM)
                Add:virent8090DEVCR2DNSPC1010(688612),    -- V8R13C00 for CR2DNSPC1010(SBOM) Network Processing Unit (NSP-C1)
                Add:virent600DEVTNRDIPU1T2C5(688613),     -- V8R13C00 for TNRDIPU1T2C5(SBOM)Integrated Network Processing Unit (IPU-1T2-BN)
                Add:virent8090DEVIG2D00SPUG06(688614),    -- V8R13C00 for IG2D00SPUG06(SBOM)High Performance X8A&X16A Enhanced Service Processing Unit-SPUGEA,with HW Service Inspection Gateway Software
                Add:virent8090DEVCR5DSRUAD270(564873),    -- V8R13C00 for CR5DSRUAD270(SBOM) Switch and Route Processing Unit A132(32G Memory)
                Add:virent8090DEVCR5DSFUIT27Q(564874),    -- V8R13C00 for CR5DSFUIT27Q(SBOM) 2Tbps Switch Fabric Unit P(SFUI-2T-P)
                Add:virent8090DEVCR5DSFUITD72(564875),    -- V8R13C00 for CR5DSFUITD72(SBOM) 2Tbps Switch Fabric Unit Q(SFUI-2T-Q)
                Add:virent8090DEVCR8D00LRXFC6(564878),    -- V8R13C00 for CR8D00LRXFC6(SBOM) 72-Port 25GE(SFP28)/10GE(SFP+)/GE(SFP) Integrated Line Processing Unit CM(LPUI-2T-CM)
                Add:virent8090DEVCR8D00LRXFC7(564879),    -- V8R13C00 for CR8D00LRXFC7(SBOM) 72-Port 25GE(SFP28)/10GE(SFP+)/GE(SFP) Integrated Line Processing Unit CM(LPUI-2TA-CM)
                Add:virent8090DEVCR8D00LRXFC8(564880),    -- V8R13C00 for CR8D00LRXFC8(SBOM) 72-Port 25GE(SFP28)/10GE(SFP+)/GE(SFP) Integrated Line Processing Unit L CM(LPUI-2T-L-CM)
                Add:virent8090DEVCR8D00LRXFC9(564881),    -- V8R13C00 for CR8D00LRXFC9(SBOM) 72-Port 25GE(SFP28)/10GE(SFP+)/GE(SFP) Integrated Line Processing Unit L(LPUI-2TA-L-CM)
                Add:virent8090DEVCR8DE8KE8NCU(564882),    -- V8R13C00 for CR8DE8KE8NCU(SBOM) 8-Port 400GBase-QSFP-DD + 8-Port 100GBase-QSFP28 Integrated Line Processing Unit CM(LPUI-4T-CM,Enable 16*100GE by default)
                Add:virent8090DEVCR8DE8KE8NCV(564883),    -- V8R13C00 for CR8DE8KE8NCV(SBOM) 8-Port 400GBase-QSFP-DD + 8-Port 100GBase-QSFP28 Integrated Line Processing Unit CM(LPUI-4TA-CM)
                Add:virent8090DEVCR8DE8KE8NCX(564884),    -- V8R13C00 for CR8DE8KE8NCX(SBOM) 8-Port 400GBase-QSFP-DD + 8-Port 100GBase-QSFP28 Integrated Line Processing Unit L CM(LPUI-4TA-L-CM)
                Add:virent8090DEVCR8DE8KE8NCW(564885),    -- V8R13C00 for CR8DE8KE8NCW(SBOM) 8-Port 400GBase-QSFP-DD + 8-Port 100GBase-QSFP28 Integrated Line Processing Unit L CM(LPUI-4T-L-CM,Enable 16*100GE by default)
            "
        REVISION    "202102050000Z"
        DESCRIPTION "V11.13,
                Add: bnameLST7MPUE0001(700544),            --S12700E main control unit E for v2r20c10
                Add: bnameLST7MPUE000K1(700545),          --S12700E main control unit E(AK) for v2r20c10
                Add: bnameLST3MPUE0001(659752),            --S9300X main control unit E for v2r20c10
           "
		
       REVISION    "202102040000Z"
       DESCRIPTION "V11.12,
                Add:bnameH901CSPD(148726),                --  8*XGS/G combo board of MA5800.
                Add:bnameORCSF1(148727),                    --  16*XGS GPON and GPON combo board of EA5800.
           "
	   
	   REVISION    "202102040000Z"
       DESCRIPTION "V11.11,
		   Add: bnameCEL48CCQHGX(688410),                -- Finished Board Unit,CloudEngine 16800,CEL48CCQHG-B,48-port 200GE interface card (HG-B, QSFP56)
                   Add: fnameCE6820H48S6CQ(688218),          -- Assembling Components,CloudEngine 6800,CE6820H-48S6CQ-F,CE6820H-48S6CQ switch(48*10G SFP+,6*100GE QSFP28,2*AC power modules,4*fan modules,port-side exhaust)				
                   Add: bnameCE6820H48S6CQ(688411),              -- Assembling Components,CloudEngine 6800,CE6820H-48S6CQ-F,CE6820H-48S6CQ switch(48*10G SFP+,6*100GE QSFP28,2*AC power modules,4*fan modules,port-side exhaust)					

	   "

	   REVISION    "202101290000Z"
       DESCRIPTION "V11.10, 
                Add:subnameS7Y08000(536806),           --8-port 25GE/10GE/GE SFP28 interface card for V2R20C00
                Add:subnamePDC260S12DL(536807),           --260W DC Power Module for V2R20C00
                Add:subnamePDC180S12CR(536808),           --180W DC Power Module for V2R20C00
                Add:subnamePDC180S12CL(536809),           --PDC180S12-CL,Power Board for V2R20C00
                Add:subnamePAC300S12CL(536810),           --300 AC Power Module for V2R20C00
                Add:subnameFAN0031AF(536812),           --Fan box(F,FAN panel side intake) for V2R20C00
                Add:subnamePAC1000S56-DB(536813),           --1000W AC&240V DC Power Module for V2R20C10
                Add:subnamePAC600S12-DB(536814),             --600W AC Power Module(Back to Front, Power panel side exhaust) for V2R20C10
                Add:subnamePAC-600WD-B(536815),               --600W AC Power Module(Back to Front,Power panel side exhaust) for V2R20C10
                Add:subnamePAC460S55-D(536816),               --PoE 460W Power Board for V2R20C10
	       "

	   REVISION    "202101280000Z"
       DESCRIPTION "V11.09, 
               Add:fname8031S5700W-H24T4XC1(537529), --S5700W-H24T4XC1 (24*10/100/1000BASE-T ports, 4*10GE SFP+ ports, 1*expansion slot, without power module) for V2R20C10
               Add:fname8031S5700W-H48T4XC1(537530), --S5700W-H48T4XC1 (48*10/100/1000BASE-T ports, 4*10GE SFP+ ports, 1*expansion slot, without power module) for V2R20C10	
               Add:bnameS5700W-H24T4XC1(537713), --S5700W-H24T4XC1 (24*10/100/1000BASE-T ports, 4*10GE SFP+ ports, 1*expansion slot, without power module) for V2R20C10
               Add:bnameS5700W-H48T4XC1(537714), --S5700W-H48T4XC1 (48*10/100/1000BASE-T ports, 4*10GE SFP+ ports, 1*expansion slot, without power module) for V2R20C10		
	       "
	   REVISION    "202101210000Z"
       DESCRIPTION "V11.08, 
       Add:fnameES1BS8706SP0(713472),
       Add:fnameES1BS8710SP0(713473)
       Add:bnameLSG7SRUEX1C0(713472),  --S8700-6 main control unit E, supporting 1*100G QSFP28, 2*40G QSFP+, 4*25G SFP28, or 8*10G SFP+ ports
       Add:bnameLSG7SRUEX1T0(713473),  --S8700-6 main control unit E, supporting 1*100G QSFP28, 2*40G QSFP+, 4*25G SFP28, or 8*10G SFP+ ports (TPM)
       Add:bnameLSG7SRUFX1C0(713474),  --S8700-10 main control unit E, supporting 1*100G QSFP28, 2*40G QSFP+, 4*25G SFP28, or 8*10G SFP+ ports
       Add:bnameLSG7SRUFX1T0(713475),  --S8700-10 main control unit E, supporting 1*100G QSFP28, 2*40G QSFP+, 4*25G SFP28, or 8*10G SFP+ ports (TPM)
       Add:bnameLSG7X48SX1E0(713476),  --48-port 100M/1G/10GBASE-X interface card (SFP+)
       Add:bnameLSG7G48SX1E0(713477),  --48-port 100/1000BASE-X interface card (SFP)
       Add:bnameLSG7X24SX1E0(713478),  --24-port 100M/1G/10GBASE-X interface card (SFP+)
       Add:bnameLSG7G24SX1E0(713479),  --24-port 100/1000BASE-X interface card (SFP)
       Add:bnameLSG7M48VX1E0(713480),  --48-port 100M/1G/2.5G/5G/10G multi-GE PoE++ interface card (RJ45, PoE++)
       Add:bnameLSG7M24VX1E0(713481),  --24-port 100M/1G/2.5G/5G/10G multi-GE PoE++ interface card (RJ45, PoE++)
       Add:bnameLSG7G48VX1E0(713482),  --48-port 10/100/1000BASE-T PoE++ interface card (RJ45, PoE++)
       Add:bnameLSG7G48TX1E0(713483),  --48-port 10/100/1000BASE-T interface card (RJ45)
       Add:bnameLSG7G24TX1E0(713484),  --24-port 10/100/1000BASE-T interface card (RJ45)
       Add:bnameLSG7X52BX1E0(713485),  --12-port 100M/1G/10GBASE-X, 16-port 100M/1GBASE-X, and 24-port 10/100/1000BASE-T interface card (SFP+, SFP, RJ45)
       Add:bnameLSG7Y24QX1E0(713486),  --24-port 1G/10G/25GBASE-X interface card (SFP28)		
	       "
		
	   REVISION    "202101200000Z"
       DESCRIPTION "V11.07,
	   Add: bnameCEMPUFHALF(688406),                 -- Finished Board Unit,CE16800,CE-MPUF-HALF,CE16800 Main Processing Unit F (half-width)
	   Add: bnameCEMPUFFULL(688407),                 -- Finished Board Unit,CE16800,CE-MPUF-FULL,CE16800 Main Processing Unit F (full-width)
	   Add: bnameCEMPUFHT(688408),                     -- Finished Board Unit,CE16800,CE-MPUF-HT,CE16800 Main Processing Unit F-HT (half-width)
          Add: bnameCEMPUFFT(688409), 	               -- Finished Board Unit,CE16800,CE-MPUF-FT,CE16800 Main Processing Unit F-FT (full-width) 		
	       "
       REVISION    "202101190000Z"
       DESCRIPTION "V11.06,
	   Add: fname8031S5735-L32ST4X-A1(537531), --S5735-L32ST4X-A1 (24*GE SFP ports, 8*10/100/1000BASE-T ports, 4*10GE SFP+ ports, AC power) for V2R20C10
	   Add: fname8031S5335-L32ST4X-A1(537532), --S5335-L32ST4X-A1 (24*GE SFP ports, 8*10/100/1000BASE-T ports, 4*10GE SFP+ ports, AC power, front access) for V2R20C10
	   Add: fname8031S5735S-L32ST4X-A1(537533), --S5735S-L32ST4X-A1 (24*GE SFP ports, 8*10/100/1000BASE-T ports, 4*10GE SFP+ ports, AC power) for V2R20C10
	   Add: fname8031S500-32ST4X(537534), --S500-32ST4X (24*GE SFP ports, 8*10/100/1000BASE-T ports, 4*10GE SFP+ ports, AC power) for V2R20C10
	   Add: fname8031S5735-L32ST4X-D1(537535), --S5735-L32ST4X-V2 (24*GE SFP ports, 8*10/100/1000BASE-T ports, 4*10GE SFP+ ports, DC power) for V2R20C10
	   Add: fname8031S5335-L32ST4X-D1(537536), --S5335-L32ST4X-V2 (24*GE SFP ports, 8*10/100/1000BASE-T ports, 4*10GE SFP+ ports, DC power, front access) for V2R20C10
	   Add: bnameS5735-L32ST4X-A1(537715), --S5735-L32ST4X-A1 (24*GE SFP ports, 8*10/100/1000BASE-T ports, 4*10GE SFP+ ports, AC power) for V2R20C10
	   Add: bnameS5335-L32ST4X-A1(537716), --S5335-L32ST4X-A1 (24*GE SFP ports, 8*10/100/1000BASE-T ports, 4*10GE SFP+ ports, AC power, front access) for V2R20C10
	   Add: bnameS5735S-L32ST4X-A1(537717), --S5735S-L32ST4X-A1 (24*GE SFP ports, 8*10/100/1000BASE-T ports, 4*10GE SFP+ ports, AC power) for V2R20C10
	   Add: bnameS500-32ST4X(537718), --S500-32ST4X (24*GE SFP ports, 8*10/100/1000BASE-T ports, 4*10GE SFP+ ports, AC power) for V2R20C10
	   Add: bnameS5735-L32ST4X-D1(537719), --S5735-L32ST4X-V2 (24*GE SFP ports, 8*10/100/1000BASE-T ports, 4*10GE SFP+ ports, DC power) for V2R20C10
	   Add: bnameS5335-L32ST4X-D1(537720), --S5335-L32ST4X-V2 (24*GE SFP ports, 8*10/100/1000BASE-T ports, 4*10GE SFP+ ports, DC power, front access) for V2R20C10
           "

        REVISION    "202101090000Z"
        DESCRIPTION "V11.05,"

	  REVISION    "202101080000Z"
	     DESCRIPTION "V11.04,
			Add: fnameFM5855E48T4S2Q(716811),
			Add: fnameFM6857E48S6CQ(716812),
			Add: fnameFM6857E48T6CQ(716813),
			Add: bnameFM5855E48T4S2Q(716821),
			Add: bnameFM6857E48S6CQ(716822),
			Add: bnameFM6857E48T6CQ(716823),
			"

           REVISION    "202101060000Z"
	   DESCRIPTION "V11.03,
					Add: bnameH903XEHD(148686),        --  8*10G EPON board of MA5800."
				
	  REVISION    "202101050000Z"
         DESCRIPTION "V11.02,           
     		        Add: bnameCE6860SAN(688402),                 -- CloudEngine 6800,CE6860-SAN switch (48*25G SFP28, 8*100G QSFP28, without fan and power modules)(CM)
			Add: bnameCE8850SAN(688403),                 -- CloudEngine 8800,CE8850-SAN switch (32*100G QSFP28, without fan and power modules)(CM)
			Add: bnameCEL48CQSAN(688404),              -- 48-port 100GE SAN interface card(SAN, QSFP28)(CM)
			Add: bnameCEL72XSSAN(688405),              -- 72-port 25GE and 6-port 100GE interface card with optical module bundle 1 (HGA-P, SFP28, QSFP28, 24*10GE+2*100GE port RTU, 3*(24*25GE capacity upgrade RTU), 72*25GBase-SR-MP) 
			Add: fnameCE6860SAN(688216),                  -- CloudEngine 6800,CE6860-SAN switch (48*25G SFP28, 8*100G QSFP28, without fan and power modules)(CM)
			Add: fnameCE8850SAN(688217),                  -- CloudEngine 8800,CE8850-SAN switch (32*100G QSFP28, without fan and power modules)(CM)
			"

				
	   REVISION    "202101040000Z"
         DESCRIPTION "V11.01,
            Add: bnameCEL48CQHGX(688401),         -- Finished Board Unit, CloudEngine 16800, CEL48CQHG-B, 48-port 100GE interface card (HG-B, QSFP28)
			"


        REVISION    "202012300000Z"
         DESCRIPTION "V11.00,
            Add: fnameAirEngine6760-51EI(692355), --WLAN R20C10 new AP ENUM_
            Add: fnameAirEngine6761-21T(692356),  --WLAN R20C10 new AP ENUM_
            Add: fnameAirEngine6761S-21T(692357), --WLAN R20C10 new AP ENUM_
            Add: fnameAirEngine5761-21(692358),   --WLAN R20C10 new AP ENUM_
            Add: fnameAirEngine6761-21E(692359),  --WLAN R20C10 new AP ENUM_
            Add: fnameAirEngine5761S-21(692360),  --WLAN R20C10 new AP ENUM_
            Add: fnameAirEngine5761-11(692361),   --WLAN R20C10 new AP ENUM_
            Add: fnameAirEngine5761S-11(692362),  --WLAN R20C10 new AP ENUM_
            Add: fnameAirEngine5761-12W(692363),  --WLAN R20C10 new AP ENUM_
            Add: fnameAirEngine5761S-12W(692364), --WLAN R20C10 new AP ENUM_
            Add: fnameAirEngine5761-11W(692365),  --WLAN R20C10 new AP ENUM_
            Add: fnameAirEngine5761S-11W(692366), --WLAN R20C10 new AP ENUM_
            Add: fnameAirEngine5761-11WD(692367), --WLAN R20C10 new AP ENUM_
            Add: bnameAirEngine6760-51EI(692355), --WLAN R20C10 new AP ENUM_
            Add: bnameAirEngine6761-21T(692356),  --WLAN R20C10 new AP ENUM_
            Add: bnameAirEngine6761S-21T(692357), --WLAN R20C10 new AP ENUM_
            Add: bnameAirEngine5761-21(692358),   --WLAN R20C10 new AP ENUM_
            Add: bnameAirEngine6761-21E(692359),  --WLAN R20C10 new AP ENUM_
            Add: bnameAirEngine5761S-21(692360),  --WLAN R20C10 new AP ENUM_
            Add: bnameAirEngine5761-11(692361),   --WLAN R20C10 new AP ENUM_
            Add: bnameAirEngine5761S-11(692362),  --WLAN R20C10 new AP ENUM_
            Add: bnameAirEngine5761-12W(692363),  --WLAN R20C10 new AP ENUM_
            Add: bnameAirEngine5761S-12W(692364), --WLAN R20C10 new AP ENUM_
            Add: bnameAirEngine5761-11W(692365),  --WLAN R20C10 new AP ENUM_
            Add: bnameAirEngine5761S-11W(692366), --WLAN R20C10 new AP ENUM_
            Add: bnameAirEngine5761-11WD(692367), --WLAN R20C10 new AP ENUM_
            "                
        REVISION    "202012290000Z"
        DESCRIPTION "V10.99,"

        REVISION    "202012280000Z"
        DESCRIPTION "V10.98,
                Add: virent8090DEVCR8DVSUIK0C2(675828)     -- V8R21C00 for CR8DVSUIK0C2(SBOM) Integrated Service Unit 400(VSUI-400A-E)
                Add: virent8090DEVCR5DVSUIK076(688604)     -- V8R21C00 for CR5DVSUIK076(SBOM) Integrated Service Unit 400(VSUI-400)
                Add: virent8090DEVCR5DVSUIK077(688605)     -- V8R21C00 for CR5DVSUIK077(SBOM) Integrated Service Unit 400(VSUI-400A)
                Add: virent8090DEVME0DVSUIK076(688606)     -- V8R21C00 for ME0DVSUIK076(SBOM) Integrated Service Unit 400(VSUI-400)
                Add: virent8090DEVME0DVSUIK077(688607)     -- V8R21C00 for ME0DVSUIK077(SBOM) Integrated Service Unit 400(VSUI-400A)
                Add: virent8090DEVCR5DVSUIK078(688608)     -- V8R21C00 for CR5DVSUIK078(SBOM) Integrated Service Unit 400(VSUI-400-E)
                Add: virent8090DEVCR5DVSUIK079(688609)     -- V8R21C00 for CR5DVSUIK079(SBOM) Integrated Service Unit 400(VSUI-400A-E)
                Add: virent8090DEVME0DVSUIK078(688610)     -- V8R21C00 for ME0DVSUIK078(SBOM) Integrated Service Unit 400(VSUI-400-E)
                Add: virent8090DEVME0DVSUIK079(688611)    -- V8R21C00 for ME0DVSUIK079(SBOM) Integrated Service Unit 400(VSUI-400A-E)
                Modify:  virent8090DEVCR8DSFUI14C0(567882) to virent8090DEVCR8DSFU14TCA(567882)
                Modify:  virent8090DEVCR8DSFUI14C2(567883) to virent8090DEVCR8DSFU14TCB(567883)
                Modify:  virent8090DEVCR8DSFUI14C1(567884) to virent8090DEVCR8DSFU14TC8(567884)
                Modify:  virent8090DEVCR8DSFUI14C3(567885) to virent8090DEVCR8DSFU14TC9(567885)
                Modify:  virent8090DEVCR8DSFUI14C3(567885) to virent8090DEVCR8DSFU14TC9(567885)
                Modify: virentANGMHSTK0100(229789),         --ATN 910C-K, DC Power, Port Capacity 16*10GE/GE/FE+8*GE/FE(o)+4*GE/FE(e)+16*E1
                Modify: virentANGMHSTK0200(229790),         --ATN 910C-K, AC Power, Port Capacity 16*10GE/GE/FE+8*GE/FE(o)+4*GE/FE(e)+16*E1
                Modify: virentANGMHSTM0100(229791),         --ATN 910C-M, DC Power, Port Capacity 16*10GE/GE/FE+8*GE/FE(o)+4*GE/FE(e)
                Modify: virentANGMHSTM0200(229792),         --ATN 910C-M, AC Power, Port Capacity 16*10GE/GE/FE+8*GE/FE(o)+4*GE/FE(e)
                Add: virentANGMHSTK0300(229793),            --ATN 910C-K, AC+DC Power, Port Capacity 16*10GE/GE/FE+8*GE/FE(o)+4*GE/FE(e)+16*E1
                Add: virentANGMHSTM0300(229794),            --ATN 910C-M, AC+DC Power, Port Capacity 16*10GE/GE/FE+8*GE/FE(o)+4*GE/FE(e)
                Add: fnameATNDEV910C-K(226116),             --ATN910-C-K chassis
                Add: fnameATNDEV910C-M(226117),             --ATN910-C-M chassis
                Add: virentANHMHSTA0330(225306),            --V800R013C00 for ANHMHSTA0330  ATN 910D-A, AC+DC Power, Port Capacity 4*100GE/50GE + 16*25GE/10GE/GE/FE + 8*10GE/GE/FE, default all the GE/FE ports is enabled
                Add: fnameATNDEV910D-A(225641),             -- ATN910D-A chassis
                Add: fnameNETENGINE-8000-F1A-8H20Q-E(688589),         --Quidway fnameNETENGINE-8000-F1A-8H20Q-E FRAME for V8R13C00
                Add: virent8090DEVCR9DLPUIT081(688594),    -- V8R13C00 for CR9DLPUIT081(SBOM)
                Add: virent8090DEVCR9D00EPYF8Q(688595),    -- V8R13C00 for CR9D00EPYF8Q(SBOM)
                Add: virent8090DEVCR9D00EKNB82(688596),    -- V8R13C00 for CR9D00EKNB82(SBOM)
                Add: virent8090DEVCR9DE8KE8N8V(688597),    -- V8R13C00 for CR9DE8KE8N8V(SBOM)
                Add: virent8090DEVCR9D00EKNB8S(688598),    -- V8R13C00 for CR9D00EKNB8S(SBOM)
                Add: virent8090DEVCR9D00EKNB8U(688599),    -- V8R13C00 for CR9D00EKNB8U(SBOM)
                Add: virent8090DEVCR9DE8KE8N8W(688600),    -- V8R13C00 for CR9DE8KE8N8W(SBOM)
                Add: virent8090DEVCR9D00EENB86(688601),    -- V8R13C00 for CR9D00EENB86(SBOM)
                Add: virent8090DEVCR9D00EKNB86(688602),    -- V8R13C00 for CR9D00EKNB86(SBOM)
                Add: virent8090DEVCR9P9KHALM8E(688603),    -- V8R13C00 for CR9P9KHALM8E(SBOM)
                "
        REVISION    "202012260000Z"
        DESCRIPTION "V10.97,
                Add: virentANPM001AICG1(225662),         --ATN 905-G System,AC,2*GE/FE Combo,2*GE/FE(o),2*GE/FE(e)
                "
        REVISION    "202012221500Z"
        DESCRIPTION "V10.96,
                Add: bnamePTN7900TPD1FGUB(229627),    --TPD1FGUB, Fine Granularity Unit Functional Board
                "

        REVISION    "202012220000Z"
		DESCRIPTION "V10.95,			
			Change the subbnameSIC-2SM-BF to bnameSIC-2SM-BF     (16748677)"

        REVISION "202012210000Z" 
        DESCRIPTION "V10.94
            Changed the name of USG6615F-AC to USG6615F
            Changed the name of USG6625F-AC to USG6625F
            Changed the name of USG6635F-AC to USG6635F
            Changed the name of USG6650F-AC to USG6655F
            Changed the name of Eudemon1000E-F15-AC to Eudemon1000E-F15
            Changed the name of Eudemon1000E-F25-AC to Eudemon1000E-F25
            Changed the name of AntiDDoS1905-AC to AntiDDoS1905
            Changed the name of IPS6580F-AC to IPS6585F
            Changed the name of IPS6612F-AC to IPS6615F
            Changed the name of Eudemon1000E-F35-AC to Eudemon1000E-F35
            Changed the name of Eudemon1000E-F50-AC to Eudemon1000E-F55
            Changed the name of IPS6620F-AC to IPS6625F
            "
				
        REVISION    "202012210000Z"
        DESCRIPTION "V10.93
                Add: fname8031S5336-S24S4X-A(537527), --S5336-S24S4X-A base (24*GE SFP ports, optional RTU upgrade to 10G, 4*10GE SFP+ ports, AC power supply, front access) for V2R20C10
                Add: fname8031S5336-S24S4X-D(537528), --S5336-S24S4X-D base (24*GE SFP ports, optional RTU upgrade to 10G, 4*10GE SFP+ ports, AC power supply, front access) for V2R20C10
                Add: bnameS5336-S24S4X-A(537711), --S5336-S24S4X-A base (24*GE SFP ports, optional RTU upgrade to 10G, 4*10GE SFP+ ports, AC power supply, front access) for V2R20C10
                Add: bnameS5336-S24S4X-D(537712), --S5336-S24S4X-D base (24*GE SFP ports, optional RTU upgrade to 10G, 4*10GE SFP+ ports, AC power supply, front access) for V2R20C10
                "
        REVISION    "202012180000Z"
        DESCRIPTION "V10.92
                Add: bnamePTN7900TPD1SCAC(229620),   --TPD1SCAC, System Control, Communication and Switch Fabric Process Unit,1*1
                Add: bnamePTN7900TPD1XCSC(229621),   --TPD1XCSC, Switch Fabric Unit,1*1
                Add: bnamePTN7900TPF1CXPC(229622),   --TPF1CXPC, System Control, Communication and Switch Fabric Process Unit,1*1
                Add: bnamePTN7900TPF1VXCSC(229623), --TPF1VXCSC, Switch Fabric Unit,1*1
                Add: bnamePTN7900TPA5FH4(229624),       --TPA5FH4,  4-port 100 Gigabit Ethernet Switching Processing Board
                Add: bnamePTN7900TPA5FV8(229625),       --TPA5FV8, 8-port 50 Gigabit Ethernet Switching Processing Board
                Add: bnamePTN7900TPA6FHD1(229626),    --TPA6FHD1, 1-port 200 Gigabit Ethernet Switching Processing Board
            "

        REVISION "202012170000Z" 
        DESCRIPTION "V10.91"	
       
        REVISION "202012160000Z" 
        DESCRIPTION "V10.90
            Add: bnameUSG6615F-AC      (16748665),--0x00ff9079
            Add: bnameUSG6625F-AC      (16748666),--0x00ff907a
            Add: bnameUSG6635F-AC      (16748667),--0x00ff907b
            Add: bnameUSG6650F-AC      (16748668),--0x00ff907c
            Add: bnameEudemon1000E-F15-AC      (16748669),--0x00ff907d
            Add: bnameEudemon1000E-F25-AC      (16748670),--0x00ff907e
            Add: bnameAntiDDoS1905-AC      (16748671),--0x00ff907f
            Add: bnameIPS6580F-AC      (16748672),--0x00ff9080
            Add: bnameIPS6612F-AC      (16748673),--0x00ff9081
            Add: bnameEudemon1000E-F35-AC      (16748674),--0x00ff9082
            Add: bnameEudemon1000E-F50-AC      (16748675),--0x00ff9083
            Add: bnameIPS6620F-AC      (16748676),--0x00ff9084
			"	

		REVISION "202012100000Z" 
        DESCRIPTION "V10.89
               Add:virentANTD00CXPA02(227998),            --ATN 980D,ANT1CXPA20,System Control,Cross-connect and Multi-protocol Process Unit with 360G
               Add:virent8090DEVCR8D00EJKBCP(676978),    -- V8R21C00 for CR8D00EJKBCP(SBOM) 36-Port 400GBase-QSFP-DD Integrated Line Processing Unit CM(LPUI-14T4-CM,Enable 36*100GE by default)
               Add:virent8090DEVCR8D0E18KBCP(676979),    -- V8R21C00 for CR8D0E18KBCP(SBOM) 18-Port 400GBase-QSFP-DD Integrated Line Processing Unit CM(LPUI-7T2-CM,Enable 18*100GE by default)
               Add:virent8090DEVCR5DNPU48071(677910),     -- V8R13C00 for CR5DNPU48071(SBOM) Network Processing Unit(NPU-480-B)
               Add:virent8090DEVCR5DNPU1TM72(677911),    -- V8R13C00 for CR5DNPU1TM72(SBOM) Network Processing Unit(NPU-1T-B)
               Add:virent8090DEVCR8D00EENBC7(688578),    -- V8R13C00 for CR8D00EENBC7(SBOM) 20-Port 100GBase-QSFP28 Integrated Line Processing Unit CM(LPUI-2T-CM)
               Add:virent8090DEVCR8D00EENBCD(688579),    -- V8R13C00 for CR8D00EENBCD(SBOM) 20-Port 100GBase-QSFP28 Integrated Line Processing Unit CM(LPUI-2TA-CM)
               Add:virent8090DEVCR8D00EENBC9(688580),    -- V8R13C00 for CR8D00EENBC9(SBOM) 20-Port 100GBase-QSFP28 Integrated Line Processing Unit L CM(LPUI-2T-L-CM)
               Add:virent8090DEVCR8D00EENBCA(688581),    -- V8R13C00 for CR8D00EENBCA(SBOM) 20-Port 100GBase-QSFP28 Integrated Line Processing Unit L CM(LPUI-2TA-L-CM)
               Add:virent8090DEVCR8D00EKNBC6(688582),    -- V8R13C00 for CR8D00EKNBC6(SBOM) 40-Port 100GBase-QSFP28 Integrated Line Processing Unit CM(LPUI-4T-CM)
               Add:virent8090DEVCR8D00EKNBC7(688583),    -- V8R13C00 for CR8D00EKNBC7(SBOM) 40-Port 100GBase-QSFP28 Integrated Line Processing Unit CM(LPUI-4TA-CM)
               Add:virent8090DEVCR8D00EKNBC8(688584),    -- V8R13C00 for CR8D00EKNBC8(SBOM) 40-Port 100GBase-QSFP28 Integrated Line Processing Unit L CM(LPUI-4T-L-CM)
               Add:virent8090DEVCR8D00EKNBC9(688585),    -- V8R13C00 for CR8D00EKNBC9(SBOM) 40-Port 100GBase-QSFP28 Integrated Line Processing Unit L CM(LPUI-4TA-L-CM)
               Add:virent8090DEVCR8DVSUIK0C1(675822),    -- V8R21C00 for CR8DVSUIK0C1(SBOM) Integrated Service Unit 400(VSUI-400-E)
	"

        REVISION "202012090000Z" 
        DESCRIPTION "V10.88
	    Add: bnameLSS7SRUHD000(663707), --S7706/S7712 main control unit HD for V2R20C10 S7700
	    Add: bnameLSS3SRUHD000(659750), --S9306/S9312 main control unit HD for V2R20C10 S9300
	    Add: bnameLSS7SRUED000(663708), --S7706/S7712 main control unit ED for V2R20C10 S7700
	"	

        REVISION "202012080000Z" 
	DESCRIPTION "V10.87
	Add: bnameLSS7G48SD1E0(663701), --48-port 100/1000BASE-X interface card (D1E, SFP) for V2R20C00 S7700
	Add: bnameLST7G48SD1E0(700538), --48-port 100/1000BASE-X interface card (D1E, SFP) for V2R20C00 S12700
	Add: bnameLSS3G48SD1E0(659746), --48-port 100/1000BASE-X interface card (D1E, SFP) for V2R20C00 S9300
	Add: bnameLSS7X48SD1E0(663702), --48-Port 10GBASE-X Interface card(D1E,SFP+) for V2R20C00 S7700
	Add: bnameLST7X48SD1E0(700539), --48-Port 10GBASE-X Interface card(D1E,SFP+) for V2R20C00 S12700
	Add: bnameLSS7X24BD1E0(663703), --24-port 10GE SFP+ interface and 24-port GE SFP interface card (D1E,SFP+) for V2R20C00 S7700
	Add: bnameLST7X24BD1E0(700540), --24-port 10GE SFP+ interface and 24-port GE SFP interface card (D1E,SFP+) for V2R20C00 S12700
	Add: bnameLSS3X24BD1E0(659747), --24-port 10GE SFP+ interface and 24-port GE SFP interface card (D1E,SFP+) for V2R20C00 S9300
	Add: bnameLSS7X16BD1E0(663704), --16-port 10GE SFP+ interface and 16-port GE SFP interface card (D1E,SFP+) for V2R20C00 S7700
	Add: bnameLST7X16BD1E0(700541), --16-port 10GE SFP+ interface and 16-port GE SFP interface card (D1E,SFP+) for V2R20C00 S12700
	Add: bnameLSS3X16BD1E0(659748), --16-port 10GE SFP+ interface and 16-port GE SFP interface card (D1E,SFP+) for V2R20C00 S9300
	Add: bnameLSS7X32SD1E0(663705), --32-Port 10GBASE-X Interface card(D1E,SFP+) for V2R20C00 S7700
	Add: bnameLST7X32SD1E0(700542), --32-Port 10GBASE-X Interface card(D1E,SFP+) for V2R20C00 S12700
	Add: bnameLSS3X32SD1E0(659749), --32-Port 10GBASE-X Interface card(D1E,SFP+) for V2R20C00 S9300
	Add: bnameLSS7X12BD1E0(663706), --12-port 10GE SFP+ interface and 12-port GE SFP interface card (D1E,SFP+) for V2R20C00 S7700
	Add: bnameLST7X12BD1E0(700543), --12-port 10GE SFP+ interface and 12-port GE SFP interface card (D1E,SFP+) for V2R20C00 S12700
	Add: fname8031S5735-L8T4X-A1(537460), --S5735-L8T4X-A1 (8*10/100/1000BASE-T ports, 4*10GE SFP+ ports, AC power) for V2R20C10
	Add: fname8031S5335-L8T4X-A1(537461), --S5335-L8T4X-A1 (8*10/100/1000BASE-T ports, 4*10GE SFP+ ports, AC power) for V2R20C10
	Add: fname8031S5735-L8T4S-A1(537462), --S5735-L8T4S-A1 (8*10/100/1000BASE-T ports, 4*GE SFP ports, AC power) for V2R20C10
	Add: fname8031S5735S-L8T4S-A1(537463), --S5735S-L8T4S-A1 (8*10/100/1000BASE-T ports, 4*GE SFP ports, AC power) for V2R20C10
	Add: fname8031S1730S-S8T4S-A1(537464), --S1730S-S8T4S-A1 (8*10/100/1000BASE-T ports, 4*GE SFP ports, AC power) for V2R20C10
	Add: fname8031S2730S-S8FT4S-A(537465), --S2730S-S8FT4S-A (4*10/100BASE-TX ports, 4*10/100/1000BASE-T ports, 4*GE SFP ports, AC power) for V2R20C10
	Add: fname8031S500-8T4S(537466), --S500-8T4S (8*10/100/1000BASE-T ports, 4*GE SFP ports, AC power) for V2R20C10
	Add: fname8031S300-8T4S(537467), --S300-8T4S (8*10/100/1000BASE-T ports, 4*GE SFP ports, AC power) for V2R20C10
	Add: fname8031S200-8T4S(537468), --S200-8T4S (8*10/100/1000BASE-T ports, 4*GE SFP ports, AC power) for V2R20C10
	Add: fname8031S5735-L8P4X-A1(537469), --S5735-L8P4X-A1 (8*10/100/1000BASE-T ports, 4*10GE SFP+ ports, PoE+, AC power) for V2R20C10
	Add: fname8031S5735-L8T4X-D1(537470), --S5735-L8T4X-D1 (8*10/100/1000BASE-T ports, 4*10GE SFP+ ports, DC power) for V2R20C10
	Add: fname8031S5335-L8P4X-A1(537471), --S5335-L8P4X-A1 (8*10/100/1000BASE-T ports, 4*10GE SFP+ ports, PoE+, AC power) for V2R20C10
	Add: fname8031S5335-L8T4X-D1(537472), --S5335-L8T4X-D1 (8*10/100/1000BASE-T ports, 4*10GE SFP+ ports, DC power) for V2R20C10
	Add: fname8031S5735-L8P4S-A1(537473), --S5735-L8P4S-A1 (8*10/100/1000BASE-T ports, 4*GE SFP ports, PoE+, AC power) for V2R20C10
	Add: fname8031S5735S-L8P4S-A1(537474), --S5735S-L8P4S-A1 (8*10/100/1000BASE-T ports, 4*GE SFP ports, PoE+, AC power) for V2R20C10
	Add: fname8031S1730S-S8P4S-A1(537475), --S1730S-S8P4S-A1 (8*10/100/1000BASE-T ports, 4*GE SFP ports, PoE+, AC power) for V2R20C10
	Add: fname8031S2730S-S8FP4S-A(537476), --S2730S-S8FP4S-A (4*10/100BASE-TX ports, 4*10/100/1000BASE-T ports, 4*GE SFP ports, PoE+, AC power) for V2R20C10
	Add: fname8031S500-8P4S(537477), --S500-8P4S (8*10/100/1000BASE-T ports, 4*GE SFP ports, PoE+, AC power) for V2R20C10
	Add: fname8031S300-8P4S(537478), --S300-8P4S (8*10/100/1000BASE-T ports, 4*GE SFP ports, PoE+, AC power) for V2R20C10
	Add: fname8031S200-8P4S(537479), --S200-8P4S (8*10/100/1000BASE-T ports, 4*GE SFP ports, PoE+, AC power) for V2R20C10
	Add: fname8031S5735-L24T4X-A1(537480), --S5735-L24T4X-A1 (24*10/100/1000BASE-T ports, 4*10GE SFP+ ports, AC power) for V2R20C10
	Add: fname8031S5335-L24T4X-A1(537481), --S5335-L24T4X-A1 (24*10/100/1000BASE-T ports, 4*10GE SFP+ ports, AC power, front access) for V2R20C10
	Add: fname8031S5735-L24T4X-D1(537482), --S5735-L24T4X-D1 (24*10/100/1000BASE-T ports, 4*10GE SFP+ ports, DC power) for V2R20C10
	Add: fname8031S5335-L24T4X-D1(537483), --S5335-L24T4X-D1 (24*10/100/1000BASE-T ports, 4*10GE SFP+ ports, DC power, front access) for V2R20C10
	Add: fname8031S5735-L24T4S-A1(537484), --S5735-L24T4S-A1 (24*10/100/1000BASE-T ports, 4*GE SFP ports, AC power) for V2R20C10
	Add: fname8031S5735S-L24T4S-A1(537485), --S5735S-L24T4S-A1 (24*10/100/1000BASE-T ports, 4*GE SFP ports, AC power) for V2R20C10
	Add: fname8031S1730S-S24T4S-A1(537486), --S1730S-S24T4S-A1 (24*10/100/1000BASE-T ports, 4*GE SFP ports, AC power) for V2R20C10
	Add: fname8031S2730S-S24FT4S-A(537487), --S2730S-S24FT4S-A (12*10/100BASE-TX ports, 12*10/100/1000BASE-T ports, 4*GE SFP ports, AC power) for V2R20C10
	Add: fname8031S5735S-L24T4X-A1(537488), --S5735S-L24T4X-A1 (24*10/100/1000BASE-T ports, 4*XGE SFP+ ports, AC power) for V2R20C10
	Add: fname8031S1730S-S24T4X-A1(537489), --S1730S-S24T4X-A1 (24*10/100/1000BASE-T ports, 4*XGE SFP+ ports, AC power) for V2R20C10
	Add: fname8031S500-24T4S(537490), --S500-24T4S (24*10/100/1000BASE-T ports, 4*GE SFP ports, AC power) for V2R20C10
	Add: fname8031S300-24T4S(537491), --S300-24T4S (24*10/100/1000BASE-T ports, 4*GE SFP ports, AC power) for V2R20C10
	Add: fname8031S200-24T4S(537492), --S200-24T4S (24*10/100/1000BASE-T ports, 4*GE SFP ports, AC power) for V2R20C10
	Add: fname8031S2730S-S16FT4S-A(537493), --S2730S-S16FT4S-A (8*10/100BASE-TX ports, 8*10/100/1000BASE-T ports, 4*GE SFP ports, AC power) for V2R20C10
	Add: fname8031S500-16T4S(537494), --S500-16T4S (16*10/100/1000BASE-T ports, 4*GE SFP ports, AC power) for V2R20C10
	Add: fname8031S300-16T4S(537495), --S300-16T4S (16*10/100/1000BASE-T ports, 4*GE SFP ports, AC power) for V2R20C10
	Add: fname8031S5735-L24P4X-A1(537496), --S5735-L24P4X-A1 (24*10/100/1000BASE-T ports, 4*10GE SFP+ ports, PoE+, AC power) for V2R20C10
	Add: fname8031S5335-L24P4X-A1(537497), --S5335-L24P4X-A1 (24*10/100/1000BASE-T ports, 4*10GE SFP+ ports, PoE+, AC power) for V2R20C10
	Add: fname8031S5735-L24P4S-A1(537498), --S5735-L24P4S-A1 (24*10/100/1000BASE-T ports, 4*GE SFP ports, PoE+, AC power) for V2R20C10
	Add: fname8031S5735S-L24P4S-A1(537499), --S5735S-L24P4S-A1 (24*10/100/1000BASE-T ports, 4*GE SFP ports, PoE+, AC power) for V2R20C10
	Add: fname8031S1730S-S24P4S-A1(537500), --S1730S-S24P4S-A1 (24*10/100/1000BASE-T ports, 4*GE SFP ports, PoE+, AC power) for V2R20C10
	Add: fname8031S2730S-S24FP4S-A(537501), --S2730S-S24FP4S-A (12*10/100BASE-TX ports, 12*10/100/1000BASE-T ports, 4*GE SFP ports, PoE+, AC power) for V2R20C10
	Add: fname8031S500-24P4S(537502), --S500-24P4S (24*10/100/1000BASE-T ports, 4*GE SFP ports, PoE+, AC power) for V2R20C10
	Add: fname8031S300-24P4S(537503), --S300-24P4S (24*10/100/1000BASE-T ports, 4*GE SFP ports, PoE+, AC power) for V2R20C10
	Add: fname8031S200-24P4S(537504), --S200-24P4S (24*10/100/1000BASE-T ports, 4*GE SFP ports, PoE+, AC power) for V2R20C10
	Add: fname8031S5735S-L24P4X-A1(537505), --S5735S-L24P4X-A1 (24*10/100/1000BASE-T ports, 4*10GE SFP+ ports, PoE+, AC power) for V2R20C10
	Add: fname8031S2730S-S16FP4S-A(537506), --S2730S-S16FP4S-A1 (8*10/100BASE-TX ports, 8*10/100/1000BASE-T ports,, 4*GE SFP ports, PoE+, AC power) for V2R20C10
	Add: fname8031S500-16P4S(537507), --S500-16P4S (16*10/100/1000BASE-T ports, 4*GE SFP ports, PoE+, AC power) for V2R20C10
	Add: fname8031S300-16P4S(537508), --S500-16P4S (16*10/100/1000BASE-T ports, 4*GE SFP ports, PoE+, AC power) for V2R20C10
	Add: fname8031S5735-L48T4X-A1(537509), --S5735-L48T4X-A1 (48*10/100/1000BASE-T ports, 4*10GE SFP+ ports, AC power) for V2R20C10
	Add: fname8031S5335-L48T4X-A1(537510), --S5335-L48T4X-A1 (48*10/100/1000BASE-T ports, 4*10GE SFP+ ports, AC power) for V2R20C10
	Add: fname8031S5735-L48T4S-A1(537511), --S5735-L48T4S-A1 (48*10/100/1000BASE-T ports, 4*GE SFP ports, AC power) for V2R20C10
	Add: fname8031S5735S-L48T4S-A1(537512), --S5735S-L48T4S-A1 (48*10/100/1000BASE-T ports, 4*GE SFP ports, AC power) for V2R20C10
	Add: fname8031S1730S-S48T4S-A1(537513), --S1730S-S48T4S-A1 (48*10/100/1000BASE-T ports, 4*GE SFP ports, AC power) for V2R20C10
	Add: fname8031S2730S-S48FT4S-A(537514), --S2730S-S48FT4S-A (24*10/100BASE-TX ports, 24*10/100/1000BASE-T ports, 4*GE SFP ports, AC power) for V2R20C10
	Add: fname8031S5735S-L48T4X-A1(537515), --S5735S-L48T4X-A1 (48*10/100/1000BASE-T ports, 4*10GE SFP+ ports, AC power) for V2R20C10
	Add: fname8031S1730S-S48T4X-A1(537516), --S1730S-S48T4X-A1 (48*10/100/1000BASE-T ports, 4*10GE SFP+ ports, AC power) for V2R20C10
	Add: fname8031S500-48T4S(537517), --S500-48T4S (48*10/100/1000BASE-T ports, 4*GE SFP ports, AC power) for V2R20C10
	Add: fname8031S300-48T4S(537518), --S300-48T4S (48*10/100/1000BASE-T ports, 4*GE SFP ports, AC power) for V2R20C10
	Add: fname8031S200-48T4S(537519), --S200-48T4S (48*10/100/1000BASE-T ports, 4*GE SFP ports, AC power) for V2R20C10
	Add: fname8031S5735-L48P4X-A1(537520), --S5735-L48P4X-A1 (48*10/100/1000BASE-T ports, 4*10GE SFP+ ports, PoE+, AC power) for V2R20C10
	Add: fname8031S5335-L48P4X-A1(537521), --S5335-L48P4X-A1 (48*10/100/1000BASE-T ports, 4*10GE SFP+ ports, PoE+, AC power) for V2R20C10
	Add: fname8031S5735-L48P4S-A1(537522), --S5735-L48P4S-A1 (48*10/100/1000BASE-T ports, 4*GE SFP ports, PoE+, AC power) for V2R20C10
	Add: fname8031S5735S-L48P4S-A1(537523), --S5735S-L48P4S-A1 (48*10/100/1000BASE-T ports, 4*GE SFP ports, PoE+, AC power) for V2R20C10
	Add: fname8031S5735S-L48P4X-A1(537524), --S5735S-L48P4X-A1 (48*10/100/1000BASE-T ports, 4*10GE SFP+ ports, PoE+, AC power) for V2R20C10
	Add: fname8031S1730S-S48P4S-A1(537525), --S1730S-S48P4S-A1 (48*10/100/1000BASE-T ports, 4*GE SFP ports, PoE+, AC power) for V2R20C10
	Add: fname8031S2730S-S48FP4S-A(537526), --S2730S-S48FP4S-A (24*10/100BASE-TX ports, 24*10/100/1000BASE-T ports, 4*GE SFP ports, PoE+, AC power) for V2R20C10
	Add: bnameS5735-L8T4X-A1(537644), --S5735-L8T4X-A1 (8*10/100/1000BASE-T ports, 4*10GE SFP+ ports, AC power) for V2R20C10
	Add: bnameS5335-L8T4X-A1(537645), --S5335-L8T4X-A1 (8*10/100/1000BASE-T ports, 4*10GE SFP+ ports, AC power) for V2R20C10
	Add: bnameS5735-L8T4S-A1(537646), --S5735-L8T4S-A1 (8*10/100/1000BASE-T ports, 4*GE SFP ports, AC power) for V2R20C10
	Add: bnameS5735S-L8T4S-A1(537647), --S5735S-L8T4S-A1 (8*10/100/1000BASE-T ports, 4*GE SFP ports, AC power) for V2R20C10
	Add: bnameS1730S-S8T4S-A1(537648), --S1730S-S8T4S-A1 (8*10/100/1000BASE-T ports, 4*GE SFP ports, AC power) for V2R20C10
	Add: bnameS2730S-S8FT4S-A(537649), --S2730S-S8FT4S-A (4*10/100BASE-TX ports, 4*10/100/1000BASE-T ports, 4*GE SFP ports, AC power) for V2R20C10
	Add: bnameS500-8T4S(537650), --S500-8T4S (8*10/100/1000BASE-T ports, 4*GE SFP ports, AC power) for V2R20C10
	Add: bnameS300-8T4S(537651), --S300-8T4S (8*10/100/1000BASE-T ports, 4*GE SFP ports, AC power) for V2R20C10
	Add: bnameS200-8T4S(537652), --S200-8T4S (8*10/100/1000BASE-T ports, 4*GE SFP ports, AC power) for V2R20C10
	Add: bnameS5735-L8P4X-A1(537653), --S5735-L8P4X-A1 (8*10/100/1000BASE-T ports, 4*10GE SFP+ ports, PoE+, AC power) for V2R20C10
	Add: bnameS5735-L8T4X-D1(537654), --S5735-L8T4X-D1 (8*10/100/1000BASE-T ports, 4*10GE SFP+ ports, DC power) for V2R20C10
	Add: bnameS5335-L8P4X-A1(537655), --S5335-L8P4X-A1 (8*10/100/1000BASE-T ports, 4*10GE SFP+ ports, PoE+, AC power) for V2R20C10
	Add: bnameS5335-L8T4X-D1(537656), --S5335-L8T4X-D1 (8*10/100/1000BASE-T ports, 4*10GE SFP+ ports, DC power) for V2R20C10
	Add: bnameS5735-L8P4S-A1(537657), --S5735-L8P4S-A1 (8*10/100/1000BASE-T ports, 4*GE SFP ports, PoE+, AC power) for V2R20C10
	Add: bnameS5735S-L8P4S-A1(537658), --S5735S-L8P4S-A1 (8*10/100/1000BASE-T ports, 4*GE SFP ports, PoE+, AC power) for V2R20C10
	Add: bnameS1730S-S8P4S-A1(537659), --S1730S-S8P4S-A1 (8*10/100/1000BASE-T ports, 4*GE SFP ports, PoE+, AC power) for V2R20C10
	Add: bnameS2730S-S8FP4S-A(537660), --S2730S-S8FP4S-A (4*10/100BASE-TX ports, 4*10/100/1000BASE-T ports, 4*GE SFP ports, PoE+, AC power) for V2R20C10
	Add: bnameS500-8P4S(537661), --S500-8P4S (8*10/100/1000BASE-T ports, 4*GE SFP ports, PoE+, AC power) for V2R20C10
	Add: bnameS300-8P4S(537662), --S300-8P4S (8*10/100/1000BASE-T ports, 4*GE SFP ports, PoE+, AC power) for V2R20C10
	Add: bnameS200-8P4S(537663), --S200-8P4S (8*10/100/1000BASE-T ports, 4*GE SFP ports, PoE+, AC power) for V2R20C10
	Add: bnameS5735-L24T4X-A1(537664), --S5735-L24T4X-A1 (24*10/100/1000BASE-T ports, 4*10GE SFP+ ports, AC power) for V2R20C10
	Add: bnameS5335-L24T4X-A1(537665), --S5335-L24T4X-A1 (24*10/100/1000BASE-T ports, 4*10GE SFP+ ports, AC power, front access) for V2R20C10
	Add: bnameS5735-L24T4X-D1(537666), --S5735-L24T4X-D1 (24*10/100/1000BASE-T ports, 4*10GE SFP+ ports, DC power) for V2R20C10
	Add: bnameS5335-L24T4X-D1(537667), --S5335-L24T4X-D1 (24*10/100/1000BASE-T ports, 4*10GE SFP+ ports, DC power, front access) for V2R20C10
	Add: bnameS5735-L24T4S-A1(537668), --S5735-L24T4S-A1 (24*10/100/1000BASE-T ports, 4*GE SFP ports, AC power) for V2R20C10
	Add: bnameS5735S-L24T4S-A1(537669), --S5735S-L24T4S-A1 (24*10/100/1000BASE-T ports, 4*GE SFP ports, AC power) for V2R20C10
	Add: bnameS1730S-S24T4S-A1(537670), --S1730S-S24T4S-A1 (24*10/100/1000BASE-T ports, 4*GE SFP ports, AC power) for V2R20C10
	Add: bnameS2730S-S24FT4S-A(537671), --S2730S-S24FT4S-A (12*10/100BASE-TX ports, 12*10/100/1000BASE-T ports, 4*GE SFP ports, AC power) for V2R20C10
	Add: bnameS5735S-L24T4X-A1(537672), --S5735S-L24T4X-A1 (24*10/100/1000BASE-T ports, 4*XGE SFP+ ports, AC power) for V2R20C10
	Add: bnameS1730S-S24T4X-A1(537673), --S1730S-S24T4X-A1 (24*10/100/1000BASE-T ports, 4*XGE SFP+ ports, AC power) for V2R20C10
	Add: bnameS500-24T4S(537674), --S500-24T4S (24*10/100/1000BASE-T ports, 4*GE SFP ports, AC power) for V2R20C10
	Add: bnameS300-24T4S(537675), --S300-24T4S (24*10/100/1000BASE-T ports, 4*GE SFP ports, AC power) for V2R20C10
	Add: bnameS200-24T4S(537676), --S200-24T4S (24*10/100/1000BASE-T ports, 4*GE SFP ports, AC power) for V2R20C10
	Add: bnameS2730S-S16FT4S-A(537677), --S2730S-S16FT4S-A (8*10/100BASE-TX ports, 8*10/100/1000BASE-T ports, 4*GE SFP ports, AC power) for V2R20C10
	Add: bnameS500-16T4S(537678), --S500-16T4S (16*10/100/1000BASE-T ports, 4*GE SFP ports, AC power) for V2R20C10
	Add: bnameS300-16T4S(537679), --S300-16T4S (16*10/100/1000BASE-T ports, 4*GE SFP ports, AC power) for V2R20C10
	Add: bnameS5735-L24P4X-A1(537680), --S5735-L24P4X-A1 (24*10/100/1000BASE-T ports, 4*10GE SFP+ ports, PoE+, AC power) for V2R20C10
	Add: bnameS5335-L24P4X-A1(537681), --S5335-L24P4X-A1 (24*10/100/1000BASE-T ports, 4*10GE SFP+ ports, PoE+, AC power) for V2R20C10
	Add: bnameS5735-L24P4S-A1(537682), --S5735-L24P4S-A1 (24*10/100/1000BASE-T ports, 4*GE SFP ports, PoE+, AC power) for V2R20C10
	Add: bnameS5735S-L24P4S-A1(537683), --S5735S-L24P4S-A1 (24*10/100/1000BASE-T ports, 4*GE SFP ports, PoE+, AC power) for V2R20C10
	Add: bnameS1730S-S24P4S-A1(537684), --S1730S-S24P4S-A1 (24*10/100/1000BASE-T ports, 4*GE SFP ports, PoE+, AC power) for V2R20C10
	Add: bnameS2730S-S24FP4S-A(537685), --S2730S-S24FP4S-A (12*10/100BASE-TX ports, 12*10/100/1000BASE-T ports, 4*GE SFP ports, PoE+, AC power) for V2R20C10
	Add: bnameS500-24P4S(537686), --S500-24P4S (24*10/100/1000BASE-T ports, 4*GE SFP ports, PoE+, AC power) for V2R20C10
	Add: bnameS300-24P4S(537687), --S300-24P4S (24*10/100/1000BASE-T ports, 4*GE SFP ports, PoE+, AC power) for V2R20C10
	Add: bnameS200-24P4S(537688), --S200-24P4S (24*10/100/1000BASE-T ports, 4*GE SFP ports, PoE+, AC power) for V2R20C10
	Add: bnameS5735S-L24P4X-A1(537689), --S5735S-L24P4X-A1 (24*10/100/1000BASE-T ports, 4*10GE SFP+ ports, PoE+, AC power) for V2R20C10
	Add: bnameS2730S-S16FP4S-A(537690), --S2730S-S16FP4S-A1 (8*10/100BASE-TX ports, 8*10/100/1000BASE-T ports,, 4*GE SFP ports, PoE+, AC power) for V2R20C10
	Add: bnameS500-16P4S(537691), --S500-16P4S (16*10/100/1000BASE-T ports, 4*GE SFP ports, PoE+, AC power) for V2R20C10
	Add: bnameS300-16P4S(537692), --S500-16P4S (16*10/100/1000BASE-T ports, 4*GE SFP ports, PoE+, AC power) for V2R20C10
	Add: bnameS5735-L48T4X-A1(537693), --S5735-L48T4X-A1 (48*10/100/1000BASE-T ports, 4*10GE SFP+ ports, AC power) for V2R20C10
	Add: bnameS5335-L48T4X-A1(537694), --S5335-L48T4X-A1 (48*10/100/1000BASE-T ports, 4*10GE SFP+ ports, AC power) for V2R20C10
	Add: bnameS5735-L48T4S-A1(537695), --S5735-L48T4S-A1 (48*10/100/1000BASE-T ports, 4*GE SFP ports, AC power) for V2R20C10
	Add: bnameS5735S-L48T4S-A1(537696), --S5735S-L48T4S-A1 (48*10/100/1000BASE-T ports, 4*GE SFP ports, AC power) for V2R20C10
	Add: bnameS1730S-S48T4S-A1(537697), --S1730S-S48T4S-A1 (48*10/100/1000BASE-T ports, 4*GE SFP ports, AC power) for V2R20C10
	Add: bnameS2730S-S48FT4S-A(537698), --S2730S-S48FT4S-A (24*10/100BASE-TX ports, 24*10/100/1000BASE-T ports, 4*GE SFP ports, AC power) for V2R20C10
	Add: bnameS5735S-L48T4X-A1(537699), --S5735S-L48T4X-A1 (48*10/100/1000BASE-T ports, 4*10GE SFP+ ports, AC power) for V2R20C10
	Add: bnameS1730S-S48T4X-A1(537700), --S1730S-S48T4X-A1 (48*10/100/1000BASE-T ports, 4*10GE SFP+ ports, AC power) for V2R20C10
	Add: bnameS500-48T4S(537701), --S500-48T4S (48*10/100/1000BASE-T ports, 4*GE SFP ports, AC power) for V2R20C10
	Add: bnameS300-48T4S(537702), --S300-48T4S (48*10/100/1000BASE-T ports, 4*GE SFP ports, AC power) for V2R20C10
	Add: bnameS200-48T4S(537703), --S200-48T4S (48*10/100/1000BASE-T ports, 4*GE SFP ports, AC power) for V2R20C10
	Add: bnameS5735-L48P4X-A1(537704), --S5735-L48P4X-A1 (48*10/100/1000BASE-T ports, 4*10GE SFP+ ports, PoE+, AC power) for V2R20C10
	Add: bnameS5335-L48P4X-A1(537705), --S5335-L48P4X-A1 (48*10/100/1000BASE-T ports, 4*10GE SFP+ ports, PoE+, AC power) for V2R20C10
	Add: bnameS5735-L48P4S-A1(537706), --S5735-L48P4S-A1 (48*10/100/1000BASE-T ports, 4*GE SFP ports, PoE+, AC power) for V2R20C10
	Add: bnameS5735S-L48P4S-A1(537707), --S5735S-L48P4S-A1 (48*10/100/1000BASE-T ports, 4*GE SFP ports, PoE+, AC power) for V2R20C10
	Add: bnameS5735S-L48P4X-A1(537708), --S5735S-L48P4X-A1 (48*10/100/1000BASE-T ports, 4*10GE SFP+ ports, PoE+, AC power) for V2R20C10
	Add: bnameS1730S-S48P4S-A1(537709), --S1730S-S48P4S-A1 (48*10/100/1000BASE-T ports, 4*GE SFP ports, PoE+, AC power) for V2R20C10
	Add: bnameS2730S-S48FP4S-A(537710), --S2730S-S48FP4S-A (24*10/100BASE-TX ports, 24*10/100/1000BASE-T ports, 4*GE SFP ports, PoE+, AC power) for V2R20C10
	"					
		 REVISION    "202012030000Z"
         DESCRIPTION "V10.86
            Add: subbnameH902CKUF(148520),      --  CLock subboard of MA5800.
            Add: bnameH906CGUF(156011),         --  16*XG/G GPON combo board of MA5800.
            Add: fnameEA5801EGP16(148519),      --  Backplane of the EA5801E-GP16."
				
         REVISION    "202012030000Z"
         DESCRIPTION "V10.85 
            add: fnameCE6865E48S8CQ(688215),          -- CloudEngine 6800,CE6865E-48S8CQ,CE6865E-48S8CQ switch
            add: bnameCE6865E48S8CQ(688400),          -- CloudEngine 6800,CE6865E-48S8CQ,CE6865E-48S8CQ switch
            add: subbnameCED8DQ(688144),              -- Manufactured Board,CloudEngine 9800,CE98-D8DQ,CE98:8 Port 400GE QSFPDD Interface Card"
			
         REVISION    "202012020000Z"
         DESCRIPTION "V10.84 
            add: bname8090DEVBOARDSLOT(561997),       -- BOARDSLOT
            add: bname8090DEVCFCARDSLOT(561999),      -- CFCARDSLOT
            add: virent8090DEVCR8D0CGN1HC1(676990)    -- V8R21C00 for CR8D0CGN1HC1(SBOM) CGN Versatile Service Flexible Card (VSUP-100)
            add: bname8090DEVPMUSLOT(561887),        -- PMUSLOT
            add: bname8090DEVFANSLOT(561888),        -- FANSLOT
            add: bname8090DEVPOWERSLOT(561889),      -- POWERSLOT"

         REVISION    "202011240000Z"
         DESCRIPTION "V10.83 
            add: bname8090DEVVSU(561998),             --CGN Versatile Service Flexible Card (VSUP-100)"
           
         REVISION    "202011180000Z"
         DESCRIPTION "V10.82 
            add FutureMatrix device"
			
          REVISION    "202011170000Z"
         DESCRIPTION "V10.81 
            add: virent8090DEVCR5D0MPUB873(688566),    -- V8R13C00 for CR5D0MPUB873(SBOM) Main Processing Unit B81A
            add: virent8090DEVCR5D0MPUB874(688567),    -- V8R13C00 for CR5D0MPUB874(SBOM) Main Processing Unit B81
            add: virent8090DEVCX6D0MPUB872(688568),    -- V8R13C00 for CX6D0MPUB872(SBOM) Main Processing Unit B81
            add: virent8090DEVCX6D0MPUB811(688569),    -- V8R13C00 for CX6D0MPUB811(SBOM) Main Processing Unit B81A
            add: virent8090DEVTNRD0MPUB872(688570),    -- V8R13C00 for TNRD0MPUB872(SBOM) Main Processing Unit B81
            add: virent8090DEVCR9D00EENB85(688571),    -- V8R12C11 for CR9D00EENB85(SBOM) 20-Port 100GE/50GE-QSFP28 Integrated Line Process Unit CM(LPUI-2T-CM)
            add: virent8090DEVCR9D00EKNB85(688572),    -- V8R12C11 for CR9D00EKNB85(SBOM) 20-Port 100GE/50GE-QSFP28 Integrated Line Process Unit L(LPUI-2T-L)
            add: virent8090DEVCR9P9KHALM8D(688573),    -- V8R12C11 for CR9P9KHALM8D(SBOM) 20-Port 100GE/50GE-QSFP28 Integrated Line Process Unit (LPUI-2TA)"
          REVISION    "202011160000Z"
         DESCRIPTION "V10.80 
            add:bnameMPUA-U-X4X8-T        (16748655),--0x00ff906f
            add:bnameMPUA-E-X4X8-T        (16748656),--0x00ff9070
            add:bnameMPUB-IPS-X4X8        (16748657),--0x00ff9071
            add:bnameMPUB-USG-X4X8        (16748658),--0x00ff9072
            add:bnameMPUB-E9KE-X4X8       (16748659),--0x00ff9073
            add:bnameMPUB-ADS-X4X8        (16748660),--0x00ff9074
            add:bnameMPUB-A-X4X8-T        (16748661),--0x00ff9075
            add:bnameMPUB-U-X4X8-T        (16748662),--0x00ff9076
            add:bnameMPUB-E-X4X8-T        (16748663),--0x00ff9077
            add:bnameSPUA-E9KE-03         (16748664),--0x00ff9078
            delete:fnameUSG6615F-TPM-AC        (16715959),      --00FF10B7
            delete:fnameUSG6625F-TPM-AC        (16715960),      --00FF10B8
            delete:fnameUSG6635F-TPM-AC        (16715961),      --00FF10B9
            delete:fnameUSG6650F-TPM-AC        (16715962),      --00FF10BA
            delete:fnameEudemon1000E-F15-TPM-AC	(16715971),    --00FF10C
            delete:fnameEudemon1000E-F25-TPM-AC	(16715972),    --00FF10C
            delete:fnameAntiDDoS1905-TPM-AC	(16715973),    --00FF10C
            delete:fnameEudemon1000E-F35-TPM-AC	(16715974),    --00FF10C
            delete:fnameEudemon1000E-F50-TPM-AC	(16715975)    --00FF10C         "

          REVISION    "202011110000Z"
         DESCRIPTION "V10.79 
           Add:virentANTD00CXPA00(227797),         --ATN 980D,ANT1CXPA00,System Control,Cross-connect and Multi-protocol Process Unit with 800G
           Add:virentANTD00CXPA03(227897),         --ATN 980D,ANT1CXPA00,System Control,Cross-connect and Multi-protocol Process Unit with 360G
           Add:virentANTD00CXPA01(227997),         --ATN 980D,ANT1CXPA00,System Control,Cross-connect and Multi-protocol Process Unit with 320G
           Add:fnameATNDEV980D(229798),            --ATN980D chassis
           Add:fnameATNDEV980D-DC(229799),         --ATN980D-DC chassis
           Add:fnameATNDEV980D-AC(229800),         --ATN980D-AC chassis
         "
          REVISION    "202011100000Z"
         DESCRIPTION "V10.78 
           Add:virentANND00CXPB00(225304),         -- V800R013C00 for ANND00CXPB00  ATN 980C,ANN2CXPB0,System Control,Cross-connect and Multi-protocol Process Unit with 800G
           Add:virentANND00CXPB03(225305),         -- V800R013C00 for ANND00CXPB03  ATN 980C,ANN2CXPB3,System Control,Cross-connect and Multi-protocol Process Unit with 360G
           Add:virent600DEVCR8DIPU1T2CB(800007),    --V8R13C00 NetEngine-8000-M8 CR8DIPU1T2CB(SBOM), M8
           Add:virent600DEVCR8DIPU1T2CC(800008),    --V8R13C00 NetEngine-8000-M8 CR8DIPU1T2CC(SBOM), M8
           Add:virent600DEVCR8DIPU240C3(800011),    --V8R13C00 NetEngine-8000-M8 CR8DIPU240C3(SBOM), M8
           Add:virent600DEVCR8DIPU240C4(800012),    --V8R13C00 NetEngine-8000-M8 CR8DIPU240C4(SBOM), M8
           Add:virent600DEVTNRDIPU1T2C2(800013),    --V8R13C00 PTN6900-2-M8C TNRDIPU1T2C2(SBOM), M8
           Add:virent600DEVTNRDIPU480C2(800014),    --V8R13C00 PTN6900-2-M8C TNRDIPU480C2(SBOM), M8
           Add:virent600DEVCR8D0IPU2TC3(800015),    --V8R13C00 NetEngine-8000-M14 CR8D0IPU2TC3(SBOM), M14
           Add:virent600DEVCR8D0IPU2TC4(800016),    --V8R13C00 NetEngine-8000-M14 CR8D0IPU2TC4(SBOM), M14
           Add:virent600DEVCR8DIPU1T2C7(800017),    --V8R13C00 NetEngine-8000-M14 CR8DIPU1T2C7(SBOM), M14
           Add:virent600DEVCR8DIPU1T2C8(800018),    --V8R13C00 NetEngine-8000-M14 CR8DIPU1T2C8(SBOM), M14
           Add:virent600DEVCR8DIPU1T2C9(800019),    --V8R13C00 NetEngine-8000-M14 CR8DIPU1T2C9(SBOM), M14
           Add:virent600DEVCR8DIPU1T2CA(800020),    --V8R13C00 NetEngine-8000-M14 CR8DIPU1T2CA(SBOM), M14
           Add:virent600DEVTNRD0IPU2TC2(800021),    --V8R13C00 PTN6900-M14 TNRD0IPU2TC2(SBOM), M14
           Add:virent600DEVTNRDIPU1T2C4(800022),    --V8R13C00 PTN6900-M14 TNRDIPU1T2C4(SBOM), M14
           Add:virent600DEVCR5DIPU1T2CA(800023),    --V8R13C00 NE40E-X2-M14 CR5DIPU1T2CA(SBOM), M14
           Add:virent600DEVCR5D0IPU2TC3(800024),    --V8R13C00 NE40E-X2-M14 CR5D0IPU2TC3(SBOM), M14
           Add:virent600DEVCR5DIPU1T2C1(800025),    --V8R13C00 NE40E-X2-M14 CR5DIPU1T2C1(SBOM), M14
           Add:virent8090DEVCR8D00LRXFC3(688553),    -- V8R13C00 for CR8D00LRXFC3(SBOM) 72-Port 10GE-SFP+ Integrated Line Processing Unit(LPUI-1TA-E-CM)
           Add:virent8090DEVCR8D00EENBC8(688554),    -- V8R13C00 for CR8D00EENBC8(SBOM) 20-Port 100GBase-QSFP28 Integrated Line Processing Unit CM(LPUI-2TA-CM)
           Add:virent8090DEVCR8D00LRXFC4(688555),    -- V8R13C00 for CR8D00LRXFC4(SBOM) 72-Port 10GE-SFP+ Integrated Line Processing Unit(LPUI-1TA-CM)
           Add:virent8090DEVCR8D0MPUA3C4(688556),    -- V8R13C00 for CR8D0MPUA3C4(SBOM) NetEngine 8000E Main Processing Unit A3A(MPUA3A)
           Add:virent8090DEVCR8D0MPUA5C5(688557),    -- V8R13C00 for CR8D0MPUA5C5(SBOM) NetEngine 8000S Main Processing Unit A5A(MPUA5A)
           Add:fnameNETENGINE-8000E-X4-DC(688558),   --Quidway fnameNETENGINE-8000E-X4-DC for V8R13C00
           Add:fnameNETENGINE-8000E-X4-HVDC(688559), --Quidway fnameNETENGINE-8000E-X4-HVDC for V8R13C00
           Add:fnameNETENGINE-8000E-X8-DC(688560),   --Quidway fnameNETENGINE-8000E-X8-DC for V8R13C00
           Add:fnameNETENGINE-8000E-X8-HVDC(688561), --Quidway fnameNETENGINE-8000E-X8-HVDC for V8R13C00
           Add:fnameNETENGINE-8000S-X4-DC(688562),   --Quidway fnameNETENGINE-8000S-X4-DC for V8R13C00
           Add:fnameNETENGINE-8000S-X4-HVDC(688563), --Quidway fnameNETENGINE-8000S-X4-HVDC for V8R13C00
           Add:fnameNETENGINE-8100-X8-DC(688564),   --Quidway fnameNETENGINE-8100-X8-DC for V8R13C00
           Add:fnameNETENGINE-8100-X8-HVDC(688565), --Quidway fnameNETENGINE-8100-X8-HVDC for V8R13C00
         "
          REVISION    "202011090000Z"
         DESCRIPTION "V10.77 "

		REVISION    "202010260000Z"
        DESCRIPTION "V10.76,  
                Add: bnameH903CSHF(148699),        --  16*XGS GPON and GPON combo board of MA5800.
				Add: bnameH906CGHF(156010),        -- 16*XG/G GPON combo board of MA5800.
				Add: bnameH906CIUA(148723),        -- GPIO board of MA5800.
				Add: bnameH903GPHF(148698),        --  16*GPON board of MA5800
        "
         REVISION    "202010210000Z"
         DESCRIPTION "V10.75
			  Add:bnameCEL18CQFD(688399),                  -- Finished Board,CloudEngine 12800,CE-L18CQ-FD,18-Port-100GE Interface Card(FD, QSFP28)
        "
		
		 REVISION    "202010150000Z"
         DESCRIPTION "V10.74
			  Add: bnameAR8140-12G10XG(668104),          --AR8140-12G10XG Main Control Unit
	          Add:bnameAR8140-T-12G10XG(668105),         --AR8140-T-12G10XG Main Control Unit
	          Add:bnameAR502H(668106),        		     --AR502H Main Control Unit
	          Add:bnameAR502H-CN(668107),        		 --AR502H-CN Main Control Unit
	          Add:bnameAR502H-5G(668108),        		 --AR502H-5G Main Control Unit
	          Add:bnameAR651W-8P(668109),                --AR651W-8P Main Control Unit
	          Add:bnameAR6140H-9G-2AC(668110),           --AR6140H-9G-2AC Main Control Unit
	          Add:bnameAR6121H(668111),                  --AR6121H Main Control Unit
	          Add:bnameSRU10-FusionCube(668112),         --SRU10-FusionCube Main Control Unit
	          Add:fnameAR8140-12G10XG(668001),           --AR8140-12G10XG FRAME
	          Add:fnameAR8140-T-12G10XG(668002),         --AR8140-T-12G10XG FRAME
	          Add:fnameAR502H(668003),     	             --AR502H FRAME
	          Add:fnameAR502H-CN(668004),                --AR502H-CN FRAME
	          Add:fnameAR502H-5G(668005),                --AR502H-5G FRAME
	          Add:fnameAR651W-8P(668006),   	         --AR651W-8P FRAME
	          Add:fnameAR6140H-9G-2AC(668007),           --AR6140H-9G-2AC FRAME
	          Add:fnameAR6121H(668008),   	             --AR6121H FRAME
	          Add:fnameSRU10-FusionCube(668009),         --SRU10-FusionCube FRAME.
        "
       
         REVISION    "202010140000Z"
         DESCRIPTION "V10.73 "

         REVISION    "202009300000Z"
         DESCRIPTION "V10.72
              Add: bnameTM62HPXCL(148721),         -- control board of OSN1600IIM.
              Add: bnameTM62HPCS8(148722),         -- 8 port dual-channel service board of OSN1600IIM.
        "

         REVISION    "202009280000Z"
         DESCRIPTION "V10.71 "

         REVISION    "202009270000Z"
         DESCRIPTION "V10.70
              Add: virent8090DEVCR5D0MPUB972(688520),    -- V8R12C11 for CR5D0MPUB972(SBOM) Main Processing Unit B91(32G Memory)
              Add: virent8090DEVCR5DSFUIT27P(688521),    -- V8R12C11 for CR5DSFUIT27P(SBOM) 2Tbps Switch Fabric Unit I(SFUI-2T-I)
              Add: virent8090DEVCR5DSRUA9171(688522),    -- V8R12C11 for CR5DSRUA9171(SBOM) Switch and Route Processing Unit A131(16G Memory)
              Add: virent8090DEVCR5DSFUITD71(688523),    -- V8R12C11 for CR5DSFUITD71(SBOM) 2Tbps Switch Fabric Unit J(SFUI-2T-J)
              Add: virent8090DEVCX6D0MPUB972(688524),    -- V8R12C11 for CX6D0MPUB972(SBOM) Main Processing Unit B91(32G Memory)
              Add: virent8090DEVCX6DSFUIT27P(688525),    -- V8R12C11 for CX6DSFUIT27P(SBOM) 2Tbps Switch Fabric Unit I(SFUI-2T-I)
              Add: virent8090DEVCX6DSRUA9171(688526),    -- V8R12C11 for CX6DSRUA9171(SBOM) Switch and Route Processing Unit A131(16G Memory)
              Add: virent8090DEVCX6DSFUITD71(688527),    -- V8R12C11 for CX6DSFUITD71(SBOM) 2Tbps Switch Fabric Unit J(SFUI-2T-J)
              Add: virent8090DEVTNRD0MPUB972(688528),    -- V8R12C11 for TNRD0MPUB972(SBOM) Main Processing Unit B91(32G Memory)
              Add: virent8090DEVTNRDSFUIT27P(688529),    -- V8R12C11 for TNRDSFUIT27P(SBOM) 2Tbps Switch Fabric Unit I(SFUI-2T-I)
              Add: virent8090DEVTNRDSRUA9171(688530),    -- V8R12C11 for TNRDSRUA9171(SBOM) Switch and Route Processing Unit A131(16G Memory)
              Add: virent8090DEVTNRDSFUITD71(688531),    -- V8R12C11 for TNRDSFUITD71(SBOM) 2Tbps Switch Fabric Unit J(SFUI-2T-J)
              Add: virent8090DEVME0DJYSUK071(688424),    -- V8R12C11 for CR8DSFUI4TC4(SBOM) NetEngine 8000 X4 4Tbps Switch Fabric Unit(SFUI-4T-C)
              Add: virent8090DEVME0DJYSUK071(688425),    -- V8R12C11 for CR8DSFUI4TC5(SBOM) NetEngine 8000 X4 4Tbps Switch Fabric Unit(SFUIA-4T-C)
              Add: virent8090DEVME0DJYSUK071(688426),    -- V8R12C11 for CR8DSFUI4TC6(SBOM) NetEngine 8000 X8 4Tbps Switch Fabric Unit(SFUI-4T-D)
              Add: virent8090DEVME0DJYSUK071(688427),    -- V8R12C11 for CR8DSFUI4TC7(SBOM) NetEngine 8000 X8 4Tbps Switch Fabric Unit(SFUIA-4T-D)
              Add: virent8090DEVCR8D00LRXFCS(688372),    -- V8R12C11 for CR8D00LRXFCS(SBOM) 72-Port 25GE(SFP28)/10GE(SFP+)/GE(SFP) Integrated Line Processing Unit L(LPUIA-2T-L)
              Add: virent8090DEVCR8D00EENBC6(688428)     -- V8R12C11 for CR8D00EENBC6(SBOM) 20-Port 100GBase-QSFP28 Integrated Line Processing Unit CM(LPUI-2TA-CM)
        "
         REVISION    "202009220000Z"
         DESCRIPTION "V10.69
			  Add: subbnameH901OTD1(148519),         -- OTDR subboard of MA5800 H901OTEF.
			 "
         REVISION    "202009170000Z"
         DESCRIPTION "V10.68
		      Add: virent8090DEVCR9D0MPUR280(688408),    -- V8R12C11 for CR9D0MPUR280(SBOM) NE9000-8 Main Processing Unit R2(MPUR2)
			  Add: virent8090DEVCR9D0MPUR281(688409),    -- V8R12C11 for CR9D0MPUR281(SBOM) NE9000-8 Main Processing Unit R2A(MPUR2A)
			  Add: virent8090DEVCR9D0SFUTG80(688410),    -- V8R12C11 for CR9D0SFUTG80(SBOM) NE9000-20 Switch Fabric Unit G for Single Chassis(SFU4T-G)
			  Add: virent8090DEVCR9D0SFUTH80(688420),    -- V8R12C11 for CR9D0SFUTH80(SBOM) NE9000-8 Switch Fabric Unit H for Single Chassis(SFU4T-H)
			  Add: virent8090DEVCR9D0SFUTH81(688421),    -- V8R12C11 for CR9D0SFUTH81(SBOM) NE9000-8 Switch Fabric Unit HA for Single Chassis(SFU4T-HA)
			 "
		 REVISION "202009150000Z" 
         DESCRIPTION "V10.67
              Add:  fnameAirEngine9700-M1(692346), --WLAN R19C00 new AC ENUM_
              Add:  bnameAirEngine9700-M1(692346), --WLAN R19C00 new AC ENUM_
        "
         REVISION "202009100000Z" 
         DESCRIPTION "V10.66
            Add:subbnameCARDNetEngine8000M1C(333125),    --NetEngine8000 M1C virtual card,16*10GE(o), 8*GE /GE/FE(o),4*GE/FE(e)
			Add:bnameAR651W-8P(668104),               --AR651W-8P Main Control Unit
            Add:bnameAR6140H-9G-2AC(668105),          --AR6140H-9G-2AC Main Control Unit
            Add:bnameAR6121H(668106),                 --AR6121H Main Control Unit
        	Add:bnameSRU10-FusionCube(668107),        --SRU10-FusionCube Main Control Unit
			Add:fnameAR651W-8P(668001),   	          --AR651W-8P FRAME
			Add:fnameAR6140H-9G-2AC(668002),          --AR6140H-9G-2AC FRAME
			Add:fnameAR6121H(668003),   	          --AR6121H FRAME
        "
        REVISION "202009040000Z" 
         DESCRIPTION "V10.65
            Add:virent600DEVCR8DIPU480CT(800006),   --V8R12C11 NetEngine-8000-M8 CR8DIPU480CT(SBOM), M8
            Add:virentANHMHSTA0120(225302),         -- V800R012C11 for ANHMHSTA0120  ATN 910D-A, DC Power, Port Capacity 4*100GE/50GE + 16*25GE/10GE/GE/FE + 8*10GE/GE/FE, default all the GE/FE ports is enabled
            Add:virentANHMHSTA0220(225303),         -- V800R012C11 for ANHMHSTA0220  ATN 910D-A, AC Power, Port Capacity 4*100GE/50GE + 16*25GE/10GE/GE/FE + 8*10GE/GE/FE, default all the GE/FE ports is enabled
        "
        REVISION "202009030000Z" 
         DESCRIPTION "V10.64
            delete bnameOSU4811(148726),                 --  DQ ODN OAI board of MA5800.
        "
        REVISION "202009020000Z" 
         DESCRIPTION "V10.63
            Add:bnameTPTD01CXPA01(229616),           -- OptiX PTN 980B,TPT1CXPA01,System Control,Cross-connect and Multi-protocol Process Unit
            Add:bnameTPTD01CXPA02(229617),           -- OptiX PTN 980B,TPT1CXPA02,System Control,Cross-connect and Multi-protocol Process Unit
            Add:bnameTPUD01CXPA01(229618),           -- OptiX PTN 990B,TPU1CXPA01,System Control,Cross-connect and Multi-protocol Process Unit
            Add:bnameTPUD01CXPA02(229619),           -- OptiX PTN 990B,TPU1CXPA02,System Control,Cross-connect and Multi-protocol Process Unit
            Add:fnamePTN980B(226369),                -- PTN980B chassis
            Add:fnamePTN990B(226370),                -- PTN990B chassis
            Add:virent8090DEVCR8D00LRXFCW(688430),   -- V8R12C11 CR8D00LRXFCW 72-Port 10GE-SFP+ Integrated Line Processing Unit(LPUI-1TA-CM)
            Add:virent8090DEVCR8D0MPUA1C2(688431),   -- V8R12C11 CR8D0MPUA1C2 NetEngine 8000 Main Processing Unit A2(MPUA2)
            Add:virent8090DEVCR8D0MPUA1C3(688432),   -- V8R12C11 CR8D0MPUA1C3 NetEngine 8000 Main Processing Unit A2A(MPUA2A)
            Add:virentCR8PM1CBASC6(688350),        --NetEngine 8000 M1C, 2*DC Power, Port Capacity 16*10GE+8*GE(o)+4*GE(e), Default 2*10GE+8*GE
            Add:virentCR8PM1CBASC7(688351),        --NetEngine 8000 M1C, 2*AC Power, Port Capacity 16*10GE+8*GE(o)+4*GE(e), Default 2*10GE+8*GE
            Add:virentCR8PM1CBASA6(688352),        --NetEngine 8000 M1C(A), 2*DC Power, Port Capacity 16*10GE+8*GE(o)+4*GE(e), Default 2*10GE+8*GE
            Add:virentCR8PM1CBASA7(688353),        --NetEngine 8000 M1C(A), 2*AC Power, Port Capacity 16*10GE+8*GE(o)+4*GE(e), Default 2*10GE+8*GE
            Add:fnameNETENGINE-8000-M1C-AC(226115),        --Quidway fnameNETENGINE-8000-M1C-AC FRAME for V8R13C00
            Add:fnameNETENGINE-8000-M1C-DC(226114),        --Quidway fnameNETENGINE-8000-M1C-DC FRAME for V8R13C00
            Add:subbname8090DEVGPLI72YSE6(225934),        --72-Port 10GE-SFP+ Integrated Line Processing Unit
        "

         REVISION "202009010000Z" 
         DESCRIPTION "V10.61
           add:bnameE8KE-X8-SRUE-480       (16748651)
           add:bnameE8KE-X16-SFUG-480       (16748652)
           add:bnameE8KE-X8-SFUF-480       (16748653)
           add:bnameSPUA-USG-03       (16748654)
        "
         REVISION "202008290000Z" 
         DESCRIPTION "V10.61
           fnameEudemon1000E-F15-AC	(16715963)
           fnameEudemon1000E-F25-AC	(16715964)
           fnameAntiDDoS1905-AC	(16715965)
           fnameIPS6580F-AC	(16715966)
           fnameIPS6612F-AC	(16715967)
           fnameEudemon1000E-F35-AC	(16715968)
           fnameEudemon1000E-F50-AC	(16715969)
           fnameIPS6620F-AC	(16715970)
           fnameEudemon1000E-F15-TPM-AC	(16715971)
           fnameEudemon1000E-F25-TPM-AC	(16715972)
           fnameAntiDDoS1905-TPM-AC	(16715973)
           fnameEudemon1000E-F35-TPM-AC	(16715974)
           fnameEudemon1000E-F50-TPM-AC	(16715975)
        "

        REVISION "202008280000Z" 
        DESCRIPTION "V10.60
           Add: fnameLE1BS9312XS00(659481),              --S9300XS-12 assembly chassis for V2R20C00
           Add: fname8031S5720-52X-LI-48S-AC1(537452), --S5720-52X-LI-48S-AC1 (46*GE SFP ports, 2 of which are 10/100/1000BASE-T + SFP combo ports, 4*10GE SFP+ ports, AC power supply) for V2R20C00
           Add: fname8031S5720-52X-LI-48S-DC1(537453), --S5720-52X-LI-48S-DC1 (46*GE SFP ports, 2 of which are 10/100/1000BASE-T + SFP combo ports, 4*10GE SFP+ ports, DC power supply) for V2R20C00
           Add: fname8031S5720-52X-LI-24S-AC1(537454), --S5720-52X-LI-24S-AC1 (24*FE SFP ports,22*GE SFP ports, 2 of which are 10/100/1000BASE-T + SFP combo ports, 4*10GE SFP+ ports, AC power supply) for V2R20C00
           Add: fname8031S5720S-52X-LI-24S-AC1(537455), --S5720S-52X-LI-24S-AC1 (24*FE SFP ports,22*GE SFP ports, 2 of which are 10/100/1000BASE-T + SFP combo ports, 4*10GE SFP+ ports, AC power supply) for V2R20C00
           Add: fname8031S5320-52X-LI-48S-AC1(537456), --S5320-52X-LI-48S-AC1 (46*GE SFP ports, 2 of which are 10/100/1000BASE-T + SFP combo ports, 4*10GE SFP+ ports, AC power supply) for V2R20C00
           Add: fname8031S5320-52X-LI-48S-DC1(537457), --S5320-52X-LI-48S-DC1 (46*GE SFP ports, 2 of which are 10/100/1000BASE-T + SFP combo ports, 4*10GE SFP+ ports, DC power supply) for V2R20C00
           Add: fname8031S5320-52X-LI-24S-AC1(537458), --S5320-52X-LI-24S-AC1 (24*FE SFP ports,22*GE SFP ports, 2 of which are 10/100/1000BASE-T + SFP combo ports, 4*10GE SFP+ ports, AC power supply) for V2R20C00
           Add: bnameS5720-52X-LI-48S-AC1(537636), --S5720-52X-LI-48S-AC1 (46*GE SFP ports, 2 of which are 10/100/1000BASE-T + SFP combo ports, 4*10GE SFP+ ports, AC power supply) for V2R20C00
           Add: bnameS5720-52X-LI-48S-DC1(537637), --S5720-52X-LI-48S-DC1 (46*GE SFP ports, 2 of which are 10/100/1000BASE-T + SFP combo ports, 4*10GE SFP+ ports, DC power supply) for V2R20C00
           Add: bnameS5720-52X-LI-24S-AC1(537638), --S5720-52X-LI-24S-AC1 (24*FE SFP ports,22*GE SFP ports, 2 of which are 10/100/1000BASE-T + SFP combo ports, 4*10GE SFP+ ports, AC power supply) for V2R20C00
           Add: bnameS5720S-52X-LI-24S-AC1(537639), --S5720S-52X-LI-24S-AC1 (24*FE SFP ports,22*GE SFP ports, 2 of which are 10/100/1000BASE-T + SFP combo ports, 4*10GE SFP+ ports, AC power supply) for V2R20C00
           Add: bnameS5320-52X-LI-48S-AC1(537640), --S5320-52X-LI-48S-AC1 (46*GE SFP ports, 2 of which are 10/100/1000BASE-T + SFP combo ports, 4*10GE SFP+ ports, AC power supply) for V2R20C00
           Add: bnameS5320-52X-LI-48S-DC1(537641), --S5320-52X-LI-48S-DC1 (46*GE SFP ports, 2 of which are 10/100/1000BASE-T + SFP combo ports, 4*10GE SFP+ ports, DC power supply) for V2R20C00
           Add: bnameS5320-52X-LI-24S-AC1(537642), --S5320-52X-LI-24S-AC1 (24*FE SFP ports,22*GE SFP ports, 2 of which are 10/100/1000BASE-T + SFP combo ports, 4*10GE SFP+ ports, AC power supply) for V2R20C00
           Add: bnameLST7MPUA1000(700535), --S12700,Main Processing Unit A(Optional clock) for V2R20C00
           Add: bnameLST3MPUA1000(659739), --S9300XS,Main Processing Unit A(Optional clock) for V2R20C00
           Add: bnameLSS7SRUH1000(663698), --S7706/S7712,Main Control Unit H for V2R20C00
           Add: bnameLSS3SRUH1000(659740), --S9306/S9312,Main Control Unit H for V2R20C00
           Add: bnameLSS7SRUE1000(663699), --S7706/S7712,Main Control Unit E for V2R20C00
        "
        REVISION "202008250000Z" 
        DESCRIPTION "V10.59
           Add: subbnameH901CKUF(148518),             --  CLock subboard of MA5800.
           Add: bnameV921MPCCE(148729),               --  control board of EA5801E-GP16.
           Add: bnameV921GPHFE(148730),               --  16*GPON board of EA5801E-GP16.
           Add: bnameV923NXHCE(148731),               --  4*10GE/GE board of EA5801E-GP16.
           Add: bnameH901CASZT(148690),               --  AI compute board of MA5800.
           Add: bnameH901GPEF(148691),                --  16*GPON board of MA5800.
           Add: bnameH905CIUA(148692),                --  GPIO board of MA5800.
           Add: bnameH901GPEFE(148693),               --  16*GPON board of EA5800.
           Add: bnameH903CSHDE(148694),               --  8*XGS combo PON of EA5800.
           Add: bnameH903CGHF(148697),                --  16*XG/G combo board of MA5800.
           Add: bnameH901OTEF(148725),                --  DN_ODN board of MA5800.
           Add: bnameOSU4811(148726),                 --  DQ ODN OAI board of MA5800.
        "
        REVISION "202008250000Z" 
        DESCRIPTION "V10.58
           Add: fnameCE5855E48T4S2Q(688212),         -- CloudEngine 5800,CE5855E-48T4S2Q,CE5855E-48T4S2Q switch
           Add: fnameCE6857E48S6CQ(688213),          -- CloudEngine 6800,CE6857E-48S6CQ,CE6857E-48S6CQ switch 
           Add: fnameCE6857E48T6CQ(688214),          -- CloudEngine 6800,CE6857E-48T6CQ,CE6857E-48T6CQ switch 
           Add: bnameCESFU08FGK(688395),             -- Finished Board Unit,CE16800,CE-SFU08F-GK,CE16808 Switch Fabric Unit F-GK
           Add: bnameCE5855E48T4S2Q(688396),         -- CloudEngine 5800,CE5855E-48T4S2Q,CE5855E-48T4S2Q switch 
           Add: bnameCE6857E48S6CQ(688397),          -- CloudEngine 6800,CE6857E-48S6CQ,CE6857E-48S6CQ switch
           Add: bnameCE6857E48T6CQ(688398),          -- CloudEngine 6800,CE6857E-48T6CQ,CE6857E-48T6CQ switch 
        "
		
		REVISION "202008240000Z" 
        DESCRIPTION "V10.57
           Add: virentANND00CXPA01(225301),         -- V800R012C10 for ANND00CXPA01  ATN 980C,ANN1CXPA10,System Control,Cross-connect and Multi-protocol Process Unit with 320G
        "
		REVISION "202008210000Z" 
		DESCRIPTION "V10.56
			Add: bnameLSS3G48TA1S0(659734), --48-port 10/100/1000BASE-T PoE interface card (EA1, RJ45) for V2R20C00 S9300
			Add: bnameLSS3G48TA1E0(659735), --48-port 10/100/1000BASE-T PoE interface card (EC1, RJ45) for V2R20C00 S9300
			Add: bnameLSS3G48VA1S0(659736), --48-port 10/100/1000BASE-T PoE interface card (EA1, RJ45, PoE++) for V2R20C00 S9300
			Add: bnameLSS3G48SA1S0(659737), --48-Port 100/1000BASE-X Interface Card(EA1,SFP) for V2R20C00 S9300
			Add: bnameLSS3G48SA1E0(659738), --48-Port 100/1000BASE-X Interface Card(EC1,SFP) for V2R20C00 S9300
			Add: bnameLSS3X48SA100(659742), --48-Port 10GBASE-X Interface Card(EC,SFP+) for V2R20C00	
			Add: bnameLSS7G48TA1S0(663693), --48-port 10/100/1000BASE-T PoE interface card (EA1, RJ45) for V2R20C00 S7700
			Add: bnameLSS7G48TA1E0(663694), --48-port 10/100/1000BASE-T PoE interface card (EC1, RJ45) for V2R20C00 S7700
			Add: bnameLSS7G48VA1S0(663695), --48-port 10/100/1000BASE-T PoE interface card (EA1, RJ45, PoE++) for V2R20C00 S7700
			Add: bnameLSS7G48SA1S0(663696), --48-Port 100/1000BASE-X Interface Card(EA1,SFP) for V2R20C00 S7700
			Add: bnameLSS7G48SA1E0(663697), --48-Port 100/1000BASE-X Interface Card(EC1,SFP) for V2R20C00 S7700
			Add: bnameLST7G48TA1S0(700531), --48-port 10/100/1000BASE-T PoE interface card (EA1, RJ45) for V2R20C00 S12700
			Add: bnameLST7G48TA1E0(700532), --48-port 10/100/1000BASE-T PoE interface card (EC1, RJ45) for V2R20C00 S12700
			Add: bnameLST7G48SA1S0(700533), --48-Port 100/1000BASE-X Interface Card(EA1,SFP) for V2R20C00 S12700
			Add: bnameLST7G48SA1E0(700534), --48-Port 100/1000BASE-X Interface Card(EC1,SFP) for V2R20C00 S12700	
			Add: fname8031S5736-S24UM4XC(537429), --S5736-S24UM4XC Base(24*100M/1G Ethernet ports,Optional RTU upgrade to 2.5/5/10G, 4*10GE SFP+ ports, 1*expansion slot, PoE++, without power module) for V2R20C00
			Add: fname8031S5336-S24UM4XC(537430), --S5336-S24UM4XC Base(24*100M/1G Ethernet ports,Optional RTU upgrade to 2.5/5/10G, 4*10GE SFP+ ports, 1*expansion slot, PoE++, without power module) for V2R20C00
			Add: fname8031S5736-S24T4XC(537431), --S5736-S24T4XC (24*10/100/1000BASE-T ports, 4*10GE SFP+ ports, 1*expansion slot, without power module) for V2R20C00
			Add: fname8031S5336-S24T4XC(537432), --S5336-S24T4XC (24*10/100/1000BASE-T ports, 4*10GE SFP+ ports, 1*expansion slot, without power module) for V2R20C00
			Add: fname8031S5735S-H24T4XC-A(537433), --S5735S-H24T4XC bundle(24*10/100/1000BASE-T ports, 4*10GE SFP+ ports, 1*expansion slot, one AC power module) for V2R20C00
			Add: fname8031S5736-S48T4XC(537434), --S5736-S48T4XC (48*10/100/1000BASE-T ports, 4*10GE SFP+ ports, 1*expansion slot, without power module) for V2R20C00
			Add: fname8031S5336-S48T4XC(537435), --S5336-S48T4XC (48*10/100/1000BASE-T ports, 4*10GE SFP+ ports, 1*expansion slot, without power module) for V2R20C00
			Add: fnameS5735S-H48T4XC-A(537436), --S5735S-H48T4XC bundle(48*10/100/1000BASE-T ports, 4*10GE SFP+ ports, 1*expansion slot, one AC power module) for V2R20C00
			Add: fname8031S5736-S24U4XC(537437), --S5736-S24U4XC (24*10/100/1000BASE-T ports, 4*10GE SFP+ ports, 1*expansion slot, PoE++, without power module) for V2R20C00
			Add: fname8031S5336-S24U4XC(537438), --S5336-S24U4XC (24*10/100/1000BASE-T ports, 4*10GE SFP+ ports, 1*expansion slot, PoE++, without power module) for V2R20C00
			Add: fname8031S5735S-H24U4XC-A(537439), --S5735S-H24U4XC bundle(24*10/100/1000BASE-T ports, 4*10GE SFP+ ports, 1*expansion slot, PoE++, one AC power module) for V2R20C00
			Add: fname8031S5736-S48U4XC(537440), --S5736-S48U4XC (48*10/100/1000BASE-T ports, 4*10GE SFP+ ports, 1*expansion slot, PoE++, without power module) for V2R20C00
			Add: fname8031S5336-S48U4XC(537441), --S5336-S48U4XC (48*10/100/1000BASE-T ports, 4*10GE SFP+ ports, 1*expansion slot, PoE++, without power module) for V2R20C00
			Add: fname8031S5735S-H48U4XC-A(537442), --S5735S-H48U4XC bundle(48*10/100/1000BASE-T ports, 4*10GE SFP+ ports, 1*expansion slot, PoE++, one AC power module) for V2R20C00
			Add: fname8031S5736-S24S4XC(537443), --S5736-S24S4XC (24*GE SFP ports, 4*10GE SFP+ ports, 1*expansion slot, without power module) for V2R20C00
			Add: fname8031S5336-S24S4XC(537444), --S5336-S24S4XC (24*GE SFP ports, 4*10GE SFP+ ports, 1*expansion slot, without power module) for V2R20C00
			Add: fname8031S5735S-H24S4XC-A(537445), --S5735S-H24S4XC bundle(24*GE SFP ports, 4*10GE SFP+ ports, 1*expansion slot, one AC power module) for V2R20C00
			Add: fname8031S5736-S48S4XC(537446), --S5736-S48S4XC (48*GE SFP ports, 4*10GE SFP+ ports, 1*expansion slot, without power module) for V2R20C00
			Add: fname8031S5336-S48S4XC(537447), --S5336-S48S4XC (48*GE SFP ports, 4*10GE SFP+ ports, 1*expansion slot, without power module) for V2R20C00
			Add: fname8031S5336-S48S4X-A(537448), --S5336-S48S4X-A Base(48*GE SFP ports,Optional RTU upgrade to 10G, 4*10GE SFP+ ports, AC power, front access) for V2R20C00
			Add: fname8031S5336-S48S4X-D(537449), --S5336-S48S4X-D Base(48*GE SFP ports,Optional RTU upgrade to 10G, 4*10GE SFP+ ports, DC power, front access) for V2R20C00
			Add: fname8031S6720S-S52X-A(537450), --S6720S-S52X-A(52*10GE SFP+ ports, AC power, front access) for V2R20C00
			Add: fname8031S6720S-S24S28X-A(537451), --S6720S-S24S28X-A(24*GE SFP ports,28*10GE SFP+ ports, AC power, front access) for V2R20C00			
			Add: bnameS5736-S24UM4XC(537613), --S5736-S24UM4XC Base(24*100M/1G Ethernet ports,Optional RTU upgrade to 2.5/5/10G, 4*10GE SFP+ ports, 1*expansion slot, PoE++, without power module) for V2R20C00
			Add: bnameS5336-S24UM4XC(537614), --S5336-S24UM4XC Base(24*100M/1G Ethernet ports,Optional RTU upgrade to 2.5/5/10G, 4*10GE SFP+ ports, 1*expansion slot, PoE++, without power module) for V2R20C00
			Add: bnameS5736-S24T4XC(537615), --S5736-S24T4XC (24*10/100/1000BASE-T ports, 4*10GE SFP+ ports, 1*expansion slot, without power module) for V2R20C00
			Add: bnameS5336-S24T4XC(537616), --S5336-S24T4XC (24*10/100/1000BASE-T ports, 4*10GE SFP+ ports, 1*expansion slot, without power module) for V2R20C00
			Add: bnameS5735S-H24T4XC-A(537617), --S5735S-H24T4XC bundle(24*10/100/1000BASE-T ports, 4*10GE SFP+ ports, 1*expansion slot, one AC power module) for V2R20C00
			Add: bnameS5736-S48T4XC(537618), --S5736-S48T4XC (48*10/100/1000BASE-T ports, 4*10GE SFP+ ports, 1*expansion slot, without power module) for V2R20C00
			Add: bnameS5336-S48T4XC(537619), --S5336-S48T4XC (48*10/100/1000BASE-T ports, 4*10GE SFP+ ports, 1*expansion slot, without power module) for V2R20C00
			Add: bnameS5735S-H48T4XC-A(537620), --S5735S-H48T4XC bundle(48*10/100/1000BASE-T ports, 4*10GE SFP+ ports, 1*expansion slot, one AC power module) for V2R20C00
			Add: bnameS5736-S24U4XC(537621), --S5736-S24U4XC (24*10/100/1000BASE-T ports, 4*10GE SFP+ ports, 1*expansion slot, PoE++, without power module) for V2R20C00
			Add: bnameS5336-S24U4XC(537622), --S5336-S24U4XC (24*10/100/1000BASE-T ports, 4*10GE SFP+ ports, 1*expansion slot, PoE++, without power module) for V2R20C00
			Add: bnameS5735S-H24U4XC-A(537623), --S5735S-H24U4XC bundle(24*10/100/1000BASE-T ports, 4*10GE SFP+ ports, 1*expansion slot, PoE++, one AC power module) for V2R20C00
			Add: bnameS5736-S48U4XC(537624), --S5736-S48U4XC (48*10/100/1000BASE-T ports, 4*10GE SFP+ ports, 1*expansion slot, PoE++, without power module) for V2R20C00
			Add: bnameS5336-S48U4XC(537625), --S5336-S48U4XC (48*10/100/1000BASE-T ports, 4*10GE SFP+ ports, 1*expansion slot, PoE++, without power module) for V2R20C00
			Add: bnameS5735S-H48U4XC-A(537626), --S5735S-H48U4XC bundle(48*10/100/1000BASE-T ports, 4*10GE SFP+ ports, 1*expansion slot, PoE++, one AC power module) for V2R20C00
			Add: bnameS5736-S24S4XC(537627), --S5736-S24S4XC (24*GE SFP ports, 4*10GE SFP+ ports, 1*expansion slot, without power module) for V2R20C00
			Add: bnameS5336-S24S4XC(537628), --S5336-S24S4XC (24*GE SFP ports, 4*10GE SFP+ ports, 1*expansion slot, without power module) for V2R20C00
			Add: bnameS5735S-H24S4XC-A(537629), --S5735S-H24S4XC bundle(24*GE SFP ports, 4*10GE SFP+ ports, 1*expansion slot, one AC power module) for V2R20C00
			Add: bnameS5736-S48S4XC(537630), --S5736-S48S4XC (48*GE SFP ports, 4*10GE SFP+ ports, 1*expansion slot, without power module) for V2R20C00
			Add: bnameS5336-S48S4XC(537631), --S5336-S48S4XC (48*GE SFP ports, 4*10GE SFP+ ports, 1*expansion slot, without power module) for V2R20C00
			Add: bnameS5336-S48S4X-A(537632), --S5336-S48S4X-A Base(48*GE SFP ports,Optional RTU upgrade to 10G, 4*10GE SFP+ ports, AC power, front access) for V2R20C00
			Add: bnameS5336-S48S4X-D(537633), --S5336-S48S4X-D Base(48*GE SFP ports,Optional RTU upgrade to 10G, 4*10GE SFP+ ports, DC power, front access) for V2R20C00
			Add: bnameS6720S-S52X-A(537634), --S6720S-S52X-A(52*10GE SFP+ ports, AC power, front access) for V2R20C00
			Add: bnameS6720S-S24S28X-A(537635), --S6720S-S24S28X-A(24*GE SFP ports,28*10GE SFP+ ports, AC power, front access) for V2R20C00
		" 	
		
				
		REVISION    "202008120000Z"
		DESCRIPTION "V10.55,
			Add: bnameH903MPLB(148687),         --  control board of MA5800-X17.
			Add: bnameH903MPLBE(148720),        --  control board of EA5800-X17.
			Add: bnameH903PILA(148696),         --  Power board of MA5800.
			modify: bnameH905CGHD(148695),      --  8*XG/G combo board of MA5800.
		"
				
        REVISION    "202008100000Z"
		DESCRIPTION "V10.54,
			Add:fnameUSG6615F-AC        (16715955) 
			Add:fnameUSG6625F-AC        (16715956) 
			Add:fnameUSG6635F-AC        (16715957) 
			Add:fnameUSG6650F-AC        (16715958)
			Add:fnameUSG6615F-TPM-AC        (16715959)
			Add:fnameUSG6625F-TPM-AC        (16715960)
			Add:fnameUSG6635F-TPM-AC        (16715961)
			Add:fnameUSG6650F-TPM-AC        (16715962)
			
			Add:subbnameSIC-2SM-BF      (16728140)
		"
        REVISION    "202008070000Z"	
        DESCRIPTION "V10.53,"
				
        REVISION    "202008050000Z"
        DESCRIPTION "V10.52,
            Add:  virent8090DEVCR5D000CMU63(675999),    -- V8R12C10 for CR5D000CMU63(SBOM) Centralized Monitoring Module 2.0
            Add:  virent8090DEVCR5D0MPUQ2D1(567016),   -- v8r12c10 NE5000E-20 Main Processing Unit Q2(MPUQ2)
            Add:  virent8090DEVCR5D0MPUQ2D0(567015),   -- v8r12c10 NE5000E-20 Main Processing Unit Q2(MPUQ2)
            Add:  virent8090DEVCR9D0MPUQ280(561800),   -- v8r12c10 NE9000-20 Main Processing Unit Q2(MPUQ2)
            Add:  virent8090DEVCR5DVSUIK074(676969),    -- V8R12C11 for CR5DVSUIK074(SBOM) Integrated Service Unit 400(VSUI-400-S)
            Add:  virent8090DEVCR5DVSUIK075(676970),    -- V8R12C11 for CR5DVSUIK075(SBOM) Integrated Service Unit 400(VSUI-400A-S)
            Add:  virent8090DEVCR5DJYSUK073(676971),    -- V8R12C11 for CR5DJYSUK073(SBOM) Public Security Service Unit(PSSU-S)
            Add:  virent8090DEVME0DVSUIK074(676972),    -- V8R12C11 for ME0DVSUIK074(SBOM) Integrated Service Unit 400(VSUI-400-S)
            Add:  virent8090DEVME0DVSUIK075(676973),    -- V8R12C11 for ME0DVSUIK075(SBOM) Integrated Service Unit 400(VSUI-400A-S)
            Add:  virent8090DEVME0DJYSUK071(676974),    -- V8R12C11 for ME0DJYSUK071(SBOM) Public Security Service Unit(PSSU-S)
            Add:  virent8090DEVME0DJYSUK071(676975),    -- V8R13C00 for CR9DLPUIT080(SBOM) 60-Port 10GBase LAN/WAN-SFP+ MACSec Integrated Line Process Unit (LPUI-1TA)
        "
        REVISION    "202007240000Z"
        DESCRIPTION "V10.51,
                 Add: bnameH905CGHD(148663),         --  8*XG/G combo board of MA5800.
        "

        REVISION    "202007240000Z"
        DESCRIPTION "V10.50,
            Add:  fnameNETENGINE-8000-M14-2AC(688343),
            Add:  fnameNETENGINE-8000-M14-4AC(688344),
        "

         REVISION    "202007210000Z"	
        DESCRIPTION "V10.49,"
        
        REVISION    "202007200000Z"
        DESCRIPTION "V10.48,
            Add: bnameBT82TODU(696839),              --T8010V800R020C10:The input and output of 1PPS+TOD signals can be supported by all the eight ports. 
                                                    The input and output of E1 signals can be supported only by the first four ports.
        "
        REVISION    "202007130000Z"	
        DESCRIPTION "V10.47,
            Add: subbnameHI1620CPU(16728139)
        "
        
        REVISION    "202007110000Z"
        DESCRIPTION "V10.46"

        REVISION    "202007100000Z"
        DESCRIPTION "V10.45
                Add: virentANGMHSTK0100(229789),         --ATN 910C-K, DC Power, Port Capacity 16*10GE/GE/FE+8*GE/FE(o)+4*GE/FE(e)+16*E1, Default 2*10GE+8*GE/FE 
                Add: virentANGMHSTK0200(229790),         --ATN 910C-K, AC Power, Port Capacity 16*10GE/GE/FE+8*GE/FE(o)+4*GE/FE(e)+16*E1, Default 2*10GE+8*GE/FE      
                Add: virentANGMHSTM0100(229791),         --ATN 910C-M, DC Power, Port Capacity 16*10GE/GE/FE+8*GE/FE(o)+4*GE/FE(e), Default 2*10GE+8*GE/FE            
                Add: virentANGMHSTM0200(229792),         --ATN 910C-M, AC Power, Port Capacity 16*10GE/GE/FE+8*GE/FE(o)+4*GE/FE(e), Default 2*10GE+8*GE/FE            
                Add: fnameATNDEV910C-KDC(226110),        --ATN910-C-K DC chassis
                Add: fnameATNDEV910C-KAC(226111),        --ATN910-C-K AC chassis
                Add: fnameATNDEV910C-MDC(226112),        --ATN910-C-M DC chassis
                Add: fnameATNDEV910C-MAC(226113),        --ATN910-C-M AC chassis
                Add: virent8090DEVCR8D00EENBC5(688419),   -- 20-Port 100GBase-QSFP28 Integrated Line Processing Unit E CM(LPUI-2TA-E-CM)
                Add: virent8090DEVCR8D00EENBC2(688416),   -- 20-Port 100GBase-QSFP28 Integrated Line Processing Unit CM(LPUI-2TA-CM)
                Add: virent8090DEVCR8D00EENBC4(688418),   -- 20-Port 100GBase-QSFP28 Integrated Line Processing Unit L CM(LPUI-2TA-L-CM)
                Add: virent8090DEVCR8D00EENBC1(688415),   -- 20-Port 100GBase-QSFP28 20-Port 100GBase-QSFP28 Integrated Line Processing Unit CM(LPUI-2T-CM)
                Add: virent8090DEVCR8D00EENBC3(688423),   -- 20-Port 100GBase-QSFP28 Integrated Line Processing Unit L CM(LPUI-2T-L-CM)
                Add: virent8090DEVCR8D00LRXFCU(688412),   -- 72-Port 25GE(SFP28)/10GE(SFP+)/GE(SFP) Integrated Line Processing Unit CM(LPUI-2TA-CM)
                Add: virent8090DEVCR8D00LRXFCT(688411),   -- 72-Port 25GE(SFP28)/10GE(SFP+)/GE(SFP) Integrated Line Processing Unit CM(LPUI-2T-CM)
                Add: virent8090DEVCR8D00LRXFC1(688414),   -- 72-Port 10GE(SFP+)/GE(SFP) Integrated Line Processing Unit(LPUIA-2T)
                Add: virent8090DEVCR8D00LRXFCV(688413),   -- 72-Port 25GE(SFP28)/10GE(SFP+)/GE(SFP) Integrated Line Processing Unit L(LPUI-2T-L-CM)
                modify:fname8090SIG9800-X8A(562200),        --Quidway SIG9800-X8A FRAME,
                modify:fname8090SIG9800-X8A-DC(562201),        --Quidway SIG9800-X8A-DC FRAME,
                modify:fname8090SIG9800-X8A-HVDC(562202),        --Quidway SIG9800-X8A-HVDC FRAME,
                modify:fname8090SIG9800-X16A(562203),        --Quidway SIG9800-X16A FRAME,
                modify:fname8090SIG9800-X16A-DC(562204),        --Quidway SIG9800-X16A-DC FRAME,
                modify:fname8090SIG9800-X16A-HVDC(562205),        --Quidway SIG9800-X16A-HVDC FRAME,
                Add: subbname8090DEVVIRTUALPIC(225907),         --FLEXE_VIRTUAL
            "

        REVISION    "202007040000Z"
            DESCRIPTION "V10.44,
                Add:fnameMA5801GP16(148517),       --  Backplane of the MA5801-GP16.
                Add:fnameMA5801SGP16(148518),      --  Backplane of the MA5801S-GP16.
                Add:bnameV921MPCC(148714),         --  control board of MA5801-GP16.
                Add:bnameV931MPBB(148715),         --  control board of MA5801S-GP16.
                Add:bnameV921GPHF(148716),         --  16*GPON board of MA5801-GP16.
                Add:bnameV923NXHC(148717),         --  4*10GE/GE board of MA5801-GP16.
                Add:bnameV931GPHF(148718),         --  16*GPON board of MA5801S-GP16.
                Add:bnameV932NXHC(148719),         --  4*10GE/GE board of MA5801S-GP16.
            "

		REVISION    "202006300000Z"
        DESCRIPTION "V10.43
            Add:fnamePTN916-F-AC(226366),                           -- PTN916-F-AC chassis
            Add:fnamePTN916-F-DC(226367),                           -- PTN916-F-DC chassis
           "

        REVISION    "202006290000Z"
        DESCRIPTION "V10.42
                Add: bnamePTN7900TPE2CXP(229605),  --TPE2CXP, System Control, Communication and Switch Fabric Process Unit,1*1
                Add: bnamePTN7900TPE2XCS(229606),  --TPE2XCS, Switch Fabric Unit,1*1
                Add: bnamePTN7900TPE2VXCS(229607), --TPE2VXCS, Switch Fabric Unit,1*1
                Add: bnamePTN7900TPF2CXP(229608),  --TPF2CXP, System Control, Communication and Switch Fabric Process Unit,1*1
                Add: bnamePTN7900TPF2XCS(229609),  --TPF2XCS, Switch Fabric Unit,1*1
                Add: bnamePTN7900TPF2VXCS(229610), --TPF2VXCS, Switch Fabric Unit,1*1
                Add: bnamePTN7900TPD2XCS(229611),  --TPD2XCS, Switch Fabric Unit,1*1
                Add: bnamePTN7900TPA6FH2(229612),  --TPA6FH2, 2-port 100 Gigabit Ethernet Switching Processing Board
                Add: bnamePTN7900TPA6FV4(229613),  --TPA6FV4, 4-port 50 Gigabit Ethernet Switching Processing Board
                Add: bnamePTN7900TPA6EX16S(229614), --TPA6EX16S, 16-port 10 Gigabit Ethernet Switching Processing Board
                Add: bnamePTN7900TPA6EY8(229615),  --TPA6EY8, 8-port 25 Gigabit Ethernet Switching Processing Board
            "

        REVISION    "202006280000Z"
        DESCRIPTION "V10.41
                Add: bnameCEMPUDFT(688393),                   -- Finished Board Unit,CE16800,CE-MPUD-FT,CE16800 Main Processing Unit D (full-width)-TPM
				Add: bnameCEMPUDHT(688394),                   -- Finished Board Unit,CE16800,CE-MPUD-HT,CE16800 Main Processing Unit D (half-width)-TPM
                Add: portnameDCDE01QSFPDD(688146),            -- The port with 400G QSFP type
                Add: portnameDCDE01QSFP56(688147),            -- The port with 200G QSFP type
                Add: portnameDCDE01SFP56(688148),             -- The port with 50G SFP type
           "
		   
		REVISION    "202006240000Z"
        DESCRIPTION "V10.40
                Add: bnameLSS7C06HX6EK0(663690),     --6-port 100GE QSFP28 interface card (AK,QSFP28) for V2R20C00
                Add: bnameLSS7G48VX5EK0(663692),     --48-port 10/100/1000BASE-T PoE interface card (AK, RJ45, PoE++) for V2R20C00
           "

        REVISION    "202006220000Z"
        DESCRIPTION "V10.39
                delete: fname8090NE40E-X16B(562069),       --Quidway NE40E-X16B FRAME
                delete: virent8090DEVCR5D00LMXF62(567011),    -- V8R11C10 for CR5D00LMXF62(SBOM) 48-Port 10GBase LAN/WAN-SFP+ Integrated Line Process Unit(LPUI-1T)
                delete: virent8090DEVCR5D00E8NB62(567012),    -- V8R11C10 for CR5D00E8NB62(SBOM) 8-Port 100GBase QSFP28 Integrated Line Process Unit(LPUI-1T)
                delete: virent8090DEVCR5D0MPUB680(562085), --Main Processing Unit B6
                delete: virent8090DEVCR5DSFUIT16E(562066),   -- 1Tbps Switch Fabric Unit B(SFUI-1T-E),CR57SUF1TE
                delete: virent8090DEVCR5DE2NLEX80(562067),   -- 2-Port 100GBase-CFP2 + 20-Port 10GBase-SFP+ Integrated Line Process Unit (LPUI-400), CR57LPUI400	        
           "

        REVISION    "202006190000Z"
        DESCRIPTION "V10.38
                Add: bname8031S6730-H28Y4C-K(537610),                                          --S6730-H28Y4C-K (24*GE SFP ports, 4*25GE SFP28 ports, 4*40GE QSFP+ ports, without power module) for V2R20C00	        
                Add: bname8031S5732-H24UM2C-K(537611),                                       --S5732-H24UM2C-K 2.5G Bundle(24*100M/1G/2.5G Ethernet ports, Optional RTU upgrade to 5/10G, 4*25GE SFP28 + 2*40GE or 2*100GE QSFP28 ports, 1*expansion slot, PoE++, 1*1000W AC power) for V2R20C00	  
                Add: bname8031S5732-H48UM2C-K(537612),                                       --S5732-H48UM2C-K 2.5G Bundle(48*100M/1G/2.5G Ethernet ports, Optional RTU upgrade to 5/10G, 4*25GE SFP28 + 2*40GE or 2*100GE QSFP28 ports, 1*expansion slot, PoE++, 1*1000W AC power) for V2R20C00	         
                fname8031S6730-H28Y4C-K(537426),                                          --S6730-H28Y4C-K (24*GE SFP ports, 4*25GE SFP28 ports, 4*40GE QSFP+ ports, without power module) for V2R20C00	        
                fname8031S5732-H24UM2C-K(537427),                                       --S5732-H24UM2C-K 2.5G Bundle(24*100M/1G/2.5G Ethernet ports, Optional RTU upgrade to 5/10G, 4*25GE SFP28 + 2*40GE or 2*100GE QSFP28 ports, 1*expansion slot, PoE++, 1*1000W AC power) for V2R20C00	  
                fname8031S5732-H48UM2C-K(537428),                                       --S5732-H48UM2C-K 2.5G Bundle(48*100M/1G/2.5G Ethernet ports, Optional RTU upgrade to 5/10G, 4*25GE SFP28 + 2*40GE or 2*100GE QSFP28 ports, 1*expansion slot, PoE++, 1*1000W AC power) for V2R20C00
           "

        REVISION    "202006180000Z"
        DESCRIPTION "V10.37"

        REVISION    "202006150000Z"
        DESCRIPTION "V10.36
               Add:virent8090DEVCR5DLPUFM07C(564946),    -- CR5DLPUFM07C Flexible Card Line Processing Unit(LPUF-480)
               Add:virent8090DEVCX6DISUFM11C(564947),    -- CX6DISUFM11C Flexible Card Line Processing Unit(ISUF-480)
               Add:virent8090DEVME0DMSUFM073(564948),    -- ME0DMSUFM073 Flexible Card Multi Service Unit(MSUF-480,2 sub-slots)
               Add:virent8090DEVME0DBSUFM074(564949),    -- ME0DBSUFM074 Flexible Card Broadband Service Unit(BSUF-480,2 sub-slots)
               Add:virent8090DEVCR5D0EEXFF70(564950),    -- CR5D0EEXFF70 20-Port 10Gase LAN/WAN-SFP+ FlexE Integrated Line Processing Unit CM(LPUI-242-CM)
               Add:virent8090DEVCR5D0E2NBF70(564951),    -- CR5D0E2NBF70 2-Port 100GBase-QSFP28 FlexE Integrated Line Processing Unit CM(LPUI-242-CM)
               Add:virent8090DEVCR5D0EEXFF71(564952),    -- CR5D0EEXFF71 20-Port 10Gase LAN/WAN-SFP+ FlexE Integrated Line Processing Unit(LPUI-242A)
               Add:virent8090DEVCR5D0E2NBF71(564953),    -- CR5D0E2NBF71 2-Port 100GBase-QSFP28 FlexE Integrated Line Processing Unit(LPUI-242A)
               Add:virent8090DEVCX6D0EEXFF11(564954),    -- CX6D0EEXFF11 20-Port 10Gase LAN/WAN-SFP+ FlexE Integrated Line Processing Unit(ISUI-242A)
               Add:virent8090DEVCX6D0E2NBF12(564955),    -- CX6D0E2NBF12 2-Port 100GBase-QSFP28 FlexE Integrated Line Processing Unit(ISUI-242A)
            "
        REVISION    "202006110000Z"
        DESCRIPTION "V10.35
               Add:virent8090DEVME0D0E4NBB71(564942),    -- ME0D0E4NBB71 4-Port 100GBase-QSFP28 Broadband Service Unit Integrated (BSUI-402A)
               Add:virent8090DEVME0D0EKXFB70(564943),    -- ME0D0EKXFB70 40-Port 10GBase LAN/WAN-SFP+ Broadband Service Unit Integrated (BSUI-402)
               Add:virent8090DEVME0D0EKXFB71(564944),    -- ME0D0EKXFB71 40-Port 10GBase LAN/WAN-SFP+ Broadband Service Unit Integrated (BSUI-402A)
               Add:virent8090DEVME0DE2NEEX70(564945),    -- ME0DE2NEEX70 2-Port 100GBase-QSFP28 + 20-Port 10GBase LAN/WAN-SFP+ Broadband Service Unit Integrated (BSUI-402A)
               Add:virent8090DEVCX6DNKFEDY70(564935),    -- CX6DNKFEDY70 40-Port 10GBase LAN/WAN-SFP+ MACsec Integrated Integrated Service Unit(ISUI-402)
               Add:virent8090DEVCX6D0EKGFA71(564919),    -- CX6D0EKGFA71 40-Port 100/1000Base-X-SFP MACsec Integrated Integrated Service Unit(ISUI-52)
               Add:virent8090DEVME0DE4VE2N70(564938),    -- ME0DE4VE2N70 4-Port 50G/2-Port 100GBase-QSFP28 Broadband Service Unit Integrated (BSUI-242)
               Add:virent8090DEVME0DE4VE2N71(564940),    -- ME0DE4VE2N71 4-Port 50G/2-Port 100GBase-QSFP28 Broadband Service Unit Integrated(BSUI-242A)
               Add:virent8090DEVME0D0EFXFB70(564939),    -- ME0D0EFXFB70 24-Port 10GBase LAN/WAN-SFP+ Broadband Service Unit Integrated (BSUI-242)
               Add:virent8090DEVME0D0EFXFB71(564941),    -- ME0D0EFXFB71 24-Port 10GBase LAN/WAN-SFP+ Broadband Service Unit Integrated (BSUI-242A)
               Add:virent8090DEVME0D0EKGFB70(564936),    -- ME0D0EKGFB70 40-Port 100/1000Base-X-SFP Broadband Service Unit Integrated (BSUI-52)
               Add:virent8090DEVME0D0EKGFB71(564937),    -- ME0D0EKGFB71 40-Port 100/1000Base-X-SFP Broadband Service Unit Integrated (BSUI-52A)
               Add:virent8090DEVCX6D0E2NBA72(564931),    -- CX6D0E2NBA72 4-Port 50G/2-Port 100GBase-QSFP28 FlexE/MACsec Integrated Integrated Service Unit(ISUI-242-G)
               Add:virent8090DEVCX6D0EEXFA70(564927),    -- CX6D0EEXFA70 20-Port 10GBase LAN/WAN-SFP+ Integrated Integrated Service Unit (ISUI-242)
               Add:virent8090DEVCR5D00E4NC7P(564917),    -- CR5D00E4NC7P 4-Port 100G ETH/DWDM-CFP2 Integrated Line Processing Unit CM(LPUI-480-CM)
               Add:virent8090DEVCR5D00D8NC70(564916),    -- CR5D00D8NC70 8-Port 100G ETH/DWDM-CFP2 Integrated Line Processing Unit(LPUI-1T)
            "
        REVISION    "202005290000Z"
        DESCRIPTION "V10.34
               Add: virent8090DEVCR9D00EKNB8T(567887),    -- V800R012C10 for CR9D00EKNB8T(SBOM) 40-Port 100GE/50GE-QSFP28 Integrated Line Process Unit CM(LPUI-4T-CM)
               Add: virent8090DEVCR9D00EKNB8R(567888),    -- V800R012C10 for CR9D00EKNB8R(SBOM) 40-Port 100GE/50GE-QSFP28 Integrated Line Process Unit L(LPUI-4T-L)
               Add: virent8090DEVCR9D00EKNB81(567889),    -- V800R012C10 for CR9D00EKNB81(SBOM) 40-Port 100GE/50GE-QSFP28 Integrated Line Process Unit(LPUI-4TA)
               Add: virent8090DEVCR9DE8KE8N8U(567894),    -- V800R012C10 for CR9DE8KE8N8U(SBOM) 8-Port 400GE-QSFP-DD + 8-Port 100GE-QSFP28 Integrated Line Process Unit CM(LPUI-4T-CM)
               Add: virent8090DEVCR9DE8KE8N8T(567891),    -- V800R012C10 for CR9DE8KE8N8T(SBOM) 8-Port 400GE-QSFP-DD + 8-Port 100GE-QSFP28 Integrated Line Process Unit(LPUI-4TA)
               Add: virent8090DEVCR9D00EKNB8Q(567892),    -- V800R012C10 for CR9D00EKNB8Q(SBOM) 40-Port 100GE/50GE-QSFP28 Integrated Line Process Unit CM(LPUI-4T-CM)
               Add: virent8090DEVCR9DE8KE8N8S(567893),    -- V800R012C10 for CR9DE8KE8N8S(SBOM) 8-Port 400GE-QSFP-DD + 8-Port 100GE-QSFP28 Integrated Line Process Unit CM(LPUI-4T-CM)
               Add: fnameNETENGINE-8000-X16(688393),           --Quidway fnameNETENGINE-8000-X16 FRAME for V8R13C00
               Add: fnameNETENGINE-8000-X16-DC(688394),        --Quidway fnameNETENGINE-8000-X16-DC FRAME for V8R13C00
               Add: fnameNETENGINE-8000-X16-HVDC(688395),      --Quidway fnameNETENGINE-8000-X16-HVDC FRAME for V8R13C00
               Add: virentCR8DCXP160C2(226106),             -- V800R012C10 for CR8DCXP160C2(SBOM) NetEngine 8000 M6,System Control,Cross-connect and Multi-protocol Process Unit (CXP-160-A)
               Add: virentCR8DCXP160C3(226107),             -- V800R012C10 for CR8DCXP160C3(SBOM) NetEngine 8000 M6,System Control,Cross-connect and Multi-protocol Process Unit (CXPA-160-A)
               Add: virent600DEVCR8DIPU480C3(688513),    --V8R12C10 NetEngine-8000-M14 CR8DIPU480C3(SBOM), M14
               Add: virent600DEVCR8DIPU480C4(688514),    --V8R12C10 NetEngine-8000-M14 CR8DIPU480C4(SBOM), M14
            "
        REVISION    "202005210000Z"
        DESCRIPTION "V10.33
                Add: bname8031S6730-H28Y4C(537585),                                      --S6730-H28Y4C (28*25GE SFP28 ports, 4*100GE QSFP28 ports, without power module) for V2R20C00
                Add: bname8031S6330-H28Y4C(537586),                                      --S6330-H28Y4C (28*25GE SFP28 ports, 4*100GE QSFP28 ports, without power module) for V2R20C00
                Add: bname8031S6730-H24X4Y4C(537587),                                  --S6730-H24X4Y4C (24*10GE SFP+ ports, 4*25GE SFP28 ports, 4*100GE QSFP28 ports, without power module) for V2R20C00
                Add: bname8031S6330-H24X4Y4C(537588),                                  --S6330-H24X4Y4C (24*10GE SFP+ ports, 4*25GE SFP28 ports, 4*100GE QSFP28 ports, without power module) for V2R20C00
                Add: bname8031S6730S-H24X4Y4C-A(537589),                                  --S6730S-H24X4Y4C-A bundle (24*10GE SFP+ ports, 4*25GE SFP28 ports, 4*100GE QSFP28 ports, 1*300W AC power module) for V2R20C00
                Add: bname8031S6730S-S24X4Y4Q-A(537590),                                  --S6730S-S24X4Y4Q-A bundle (24*10GE SFP+ ports, 4*25GE SFP28 ports, 4*40GE QSFP+ ports, 1*300W AC power module) for V2R20C00
                Add: bname8031S5732-H24S4Y4Q(537591),                                        --S5732-H24S4Y4Q (24*GE SFP ports, 4*25GE SFP28 ports, 4*40GE QSFP+ ports, without power module) for V2R20C00
                Add: bname8031S5332-H24S4Y4Q(537592),                                        --S5232-H24S4Y4Q (24*GE SFP ports, 4*25GE SFP28 ports, 4*40GE QSFP+ ports, without power module) for V2R20C00
                Add: bname8031S5735-L24T4X-D(537593),                                          --S5735-L24T4X-D (24*10/100/1000BASE-T ports, 4*10GE SFP+ ports, DC power) for V2R20C00
                Add: bname8031S5335-L24T4X-D(537594),                                          --S5335-L24T4X-D (24*10/100/1000BASE-T ports, 4*10GE SFP+ ports, DC power, front access) for V2R20C00
                Add: bname8031S5735-L12T4S-D(537595),                                          --S5735-L12T4S-D (12*10/100/1000BASE-T ports, 4*GE SFP ports, DC power) for V2R20C00
                Add: bname8031S5335-L12T4S-D(537596),                                          --S5335-L12T4S-D (12*10/100/1000BASE-T ports, 4*GE SFP ports, DC power) for V2R20C00
                Add: bname8031S5735-L32ST4X-D(537597),                                        --S5735-L32ST4X-D (24*GE SFP ports, 8*10/100/1000BASE-T ports, 4*10GE SFP+ ports, DC power) for V2R20C00
                Add: bname8031S5335-L32ST4X-D(537598),                                        --S5335-L32ST4X-D (24*GE SFP ports, 8*10/100/1000BASE-T ports, 4*10GE SFP+ ports, DC power, front access) for V2R20C00
                fname8031S6730-H28Y4C(537401),                                            --S6730-H28Y4C (28*25GE SFP28 ports, 4*100GE QSFP28 ports, without power module) for V2R20C00
                fname8031S6330-H28Y4C(537402),                                            --S6330-H28Y4C (28*25GE SFP28 ports, 4*100GE QSFP28 ports, without power module) for V2R20C00
                fname8031S6730-H24X4Y4C(537403),                                        --S6730-H24X4Y4C (24*10GE SFP+ ports, 4*25GE SFP28 ports, 4*100GE QSFP28 ports, without power module) for V2R20C00
                fname8031S6330-H24X4Y4C(537404),                                        --S6330-H24X4Y4C (24*10GE SFP+ ports, 4*25GE SFP28 ports, 4*100GE QSFP28 ports, without power module) for V2R20C00
                fname8031S6730S-H24X4Y4C-A(537405),                                  --S6730S-H24X4Y4C-A bundle (24*10GE SFP+ ports, 4*25GE SFP28 ports, 4*100GE QSFP28 ports, 1*300W AC power module) for V2R20C00
                fname8031S6730S-S24X4Y4Q-A(537406),                                 --S6730S-S24X4Y4Q-A bundle (24*10GE SFP+ ports, 4*25GE SFP28 ports, 4*40GE QSFP+ ports, 1*300W AC power module) for V2R20C00
                fname8031S5732-H24S4Y4Q(537407),                                        --S5732-H24S4Y4Q (24*GE SFP ports, 4*25GE SFP28 ports, 4*40GE QSFP+ ports, without power module) for V2R20C00
                fname8031S5332-H24S4Y4Q(537408),                                        --S5232-H24S4Y4Q (24*GE SFP ports, 4*25GE SFP28 ports, 4*40GE QSFP+ ports, without power module) for V2R20C00
                fname8031S5735-L24T4X-D(537409),                                          --S5735-L24T4X-D (24*10/100/1000BASE-T ports, 4*10GE SFP+ ports, DC power) for V2R20C00
                fname8031S5335-L24T4X-D(537410),                                          --S5335-L24T4X-D (24*10/100/1000BASE-T ports, 4*10GE SFP+ ports, DC power, front access) for V2R20C00
                fname8031S5735-L12T4S-D(537411),                                          --S5735-L12T4S-D (12*10/100/1000BASE-T ports, 4*GE SFP ports, DC power) for V2R20C00
                fname8031S5335-L12T4S-D(537412),                                          --S5335-L12T4S-D (12*10/100/1000BASE-T ports, 4*GE SFP ports, DC power) for V2R20C00
                fname8031S5735-L32ST4X-D(537413),                                        --S5735-L32ST4X-D (24*GE SFP ports, 8*10/100/1000BASE-T ports, 4*10GE SFP+ ports, DC power) for V2R20C00
                fname8031S5335-L32ST4X-D(537414),                                        --S5335-L32ST4X-D (24*GE SFP ports, 8*10/100/1000BASE-T ports, 4*10GE SFP+ ports, DC power, front access) for V2R20C00
        "

        REVISION    "202005200000Z"
        DESCRIPTION "V10.32
            Add:  virent8090DEVCR8DSFUI14C0(567882),    -- V8R13C00 for CR8DSFUI14C0(SBOM) NetEngine 8000 X4 14.4Tbps Switch Fabric Unit(SFUI-14.4T-A)
            Add:  virent8090DEVCR8DSFUI14C2(567883),    -- V8R13C00 for CR8DSFUI14C2(SBOM) NetEngine 8000 X4 14.4Tbps Switch Fabric Unit(SFUIA-14.4T-A)
            Add:  virent8090DEVCR8DSFUI14C1(567884),    -- V8R13C00 for CR8DSFUI14C1(SBOM) NetEngine 8000 X8 14.4Tbps Switch Fabric Unit(SFUI-14.4T-B)
            Add:  virent8090DEVCR8DSFUI14C3(567885),    -- V8R13C00 for CR8DSFUI14C3(SBOM) NetEngine 8000 X8 14.4Tbps Switch Fabric Unit(SFUIA-14.4T-B)
        "
        REVISION    "202005190000Z"
        DESCRIPTION "V10.31
            Add:  fnameATNDEV-950C(226100),           -- ATN-950C chassis
            Add:  fnameATNDEV-950C-AC(226101),        -- ATN-950C-AC chassis
            Add:  fnameATNDEV-950C-DC(226102),        -- ATN-950C-DC chassis
            Add:  virentANSD00CXPB00(226103),         -- V800R012C10 for ANSD00CXPB00 ATN-950C,ANS1CXPA00,System Control, Cross-connect and Multi-protocol Process Unit with 160G
            Add:  virentANSD01CXPA00(226104),         -- V800R012C10 for ANSD01CXPA00 ATN-950C,ANS2CXPA00,System Control, Cross-connect and Multi-protocol Process Unit with 400G
            Add:  virentANSD01CXPB00(226105),         -- V800R012C10 for ANSD01CXPB00 ATN-950C,ANS2CXPB00,System Control, Cross-connect and Multi-protocol Process Unit with 800G
            Add:  subbname8090DEVIG2DE4NE8V01(225891),       --8-Port 50G/4-Port 100GBase-QSFP28 Flexible Card (P1T)
            Add:  subbname8090DEVIG2D00E1KB01(225892),       --1-Port 400GBase-QSFP-DD Flexible Card(P1T)
            Add:  subbname8090DEVIG2D0LFXFM01(225893),       --24-Port 10GBase LAN/WAN-SFP+ MACsec Flexible Card(P483)
            Add:  subbname8090DEVIG2D0EFGFM01(225894),       --24-port 100/1000Base-X-SFP MACsec Flexible Card (P53)
            Add:  subbname8090DEVCX6D00E1KB10(225895),        --1-Port 400GBase-QSFP-DD Flexible Card(S1T)
            Add:  virent8090DEVCR5DEDVE8N71(567876),    -- V8R12C10 for CR5DEDVE8N71(SBOM) 16-Port 50G/8-Port 100GBase-QSFP28 FlexE/MACsec Integrated Line Processing Unit L(LPUI-1T2-L)
            Add:  virent8090DEVCR9D00EENB84(567877),    -- V8R12C10 for CR9D00EENB84(SBOM) 20-Port 100GE-QSFP28 FlexE/MACSec Integrated Line Process Unit L(LPUI-2T-L)
            Add:  virent8090DEVCR5D0MPUBA70(567878),    -- V8R12C10 for CR5D0MPUBA70(SBOM) Main Processing Unit B10(32G Memory)
            Add:  virent8090DEVCR5D0MPUBA71(567879),    -- V8R12C10 for CR5D0MPUBA71(SBOM) Main Processing Unit B10A(32G Memory)
            Add:  virent8090DEVCR5D0SRUAB72(567880),    -- V8R12C10 for CR5D0SRUAB72(SBOM) Switch and Route Processing Unit A17
            Add:  virent8090DEVCR5D0SRUAB74(567881),    -- V8R12C10 for CR5D0SRUAB74(SBOM) Switch and Route Processing Unit A17A
        "
        REVISION    "202005160000Z"
        DESCRIPTION "V10.30
            Add:  virent8090DEVCR9D0MPUR180-VMPU(570077),   -- v8r12c10 VMPU In NE9000-8 Main Processing Unit R1(MPUR1)
            Add:  virent8090DEVCR9D0MPUQ180-VMPU(570078),   -- v8r12c10 VMPU In NE9000-20 Main Processing Unit Q1(MPUQ1)
        "

        REVISION    "202005150000Z"
        DESCRIPTION "V10.29"
			
        REVISION    "202005140000Z"
        DESCRIPTION "V10.28,
            fnameCE885132CQ8DQK(688209),         -- CloudEngine 8800,CE8851-32CQ8DQ-K,CE8851-32CQ8DQ-K switch
			fnameCE686648S8CQK(688210),          -- CloudEngine 6800,CE6866-48S8CQ-K,CE6866-48S8CQ-K switch
			fnameDX110(688211),                  -- DX110
			bnameCE885132CQ8DQK(688390),         -- CloudEngine 8800,CE8851-32CQ8DQ-K,CE8851-32CQ8DQ-K switch
			bnameCE686648S8CQK(688391),          -- CloudEngine 6800,CE6866-48S8CQ-K,CE6866-48S8CQ-K switch
			bnameDX110(688392),                  -- DX110
            "
			
        REVISION    "202005130000Z"
        DESCRIPTION "V10.27,
             Modify: subbname8090PM(688390),            --PM  Module
        "

        REVISION    "202005080000Z"
        DESCRIPTION "V10.26,
            Add:  virent600DEVCR8DIPU1T2C5(688503),    --V8R12C10 NetEngine-8000-M14 CR8DIPU1T2C5(SBOM), M14
            Add:  virent600DEVCR8DIPU1T2C6(688504),    --V8R12C10 NetEngine-8000-M14 CR8DIPU1T2C6(SBOM), M14
            Add:  virent600DEVCR8DE8KE8NCP(688505),    --V8R12C10 CR8DE8KE8NCP 8-Port 400GBase-QSFP-DD + 8-Port 100GBase-QSFP28 Integrated Line Processing Unit CM(LPUI-4T-CM,Enable 8*100GE by default)
            Add:  virent600DEVCR8DE8KE8NCQ(688506),    --V8R12C10 CR8DE8KE8NCQ 8-Port 400GBase-QSFP-DD + 8-Port 100GBase-QSFP28 Integrated Line Processing Unit L(LPUI-4T-L-CM,Enable 8*100GE by default)
            Add:  virent600DEVCR8DE8KE8NCR(688507),    --V8R12C10 CR8DE8KE8NCR 8-Port 400GBase-QSFP-DD + 8-Port 100GBase-QSFP28 Integrated Line Processing Unit CM(LPUI-4TA-CM,Enable 8*100GE by default)
            Add:  virent600DEVCR8DE8KE8NCS(688508),    --V8R12C10 CR8DE8KE8NCS 8-Port 400GBase-QSFP-DD + 8-Port 100GBase-QSFP28 Integrated Line Processing Unit L(LPUI-4TA-L-CM,Enable 8*100GE by default)
            Add:  virent600DEVCR8D00EKNBC1(688509),    --V8R12C10 CR8D00EKNBC1 40-Port 100GBase-QSFP28 Integrated Line Processing Unit CM(LPUI-4T-CM)
            Add:  virent600DEVCR8D00EKNBC5(688510),    --V8R12C10 CR8D00EKNBC5 40-Port 100GBase-QSFP28 Integrated Line Processing Unit CM(LPUI-4TA-CM)
            Add:  virent600DEVCR8D00EKNBC2(688511),    --V8R12C10 CR8D00EKNBC2 40-Port 100GBase-QSFP28 Integrated Line Processing Unit L CM(LPUI-4T-L-CM)
            Add:  virent600DEVCR8D00EKNBC3(688512),    --V8R12C10 NCR8D00EKNBC3 40-Port 100GBase-QSFP28 Integrated Line Processing Unit L CM(LPUI-4TA-L-CM)
            " 				

        REVISION    "202005060000Z"
        DESCRIPTION "V10.25"

        REVISION    "202004290000Z"
        DESCRIPTION "V10.24, 
            Add:fname8031S5735S-S24T4X-A(537415), 
            Add:fname8031S5735S-S48T4X-A(537416), 
            Add:fname8031S5735S-S24P4X-A(537417), 
            Add:fname8031S5735S-S48P4X-A(537418), 
            Add:fname8031S5735S-L48T4S-MA(537419), 
            Add:fname8031S1730S-S24T4S-MA(537420), 
            Add:fname8031S1730S-S24P4S-MA(537421), 
            Add: bname8031S5735S-S24T4X-A(537599), 
            Add: bname8031S5735S-S48T4X-A(537600), 
            Add: bname8031S5735S-S24P4X-A(537601), 
            Add: bname8031S5735S-S48P4X-A(537602), 
            Add: bname8031S5735S-L48T4S-MA(537603), 
            Add: bname8031S1730S-S24T4S-MA(537604), 
            Add: bname8031S1730S-S24P4S-MA(537605), "

        REVISION    "202004200000Z"
        DESCRIPTION "V10.22,
            Modify: virent8090DEVCR5DLPUFF571(676967),    -- V800R012C10 for CR5DLPUFF571(SBOM) Flexible Card Line Processing Unit E(LPUF-245A-E)
            Modify: virent8090DEVCR5DLPUFM571(676968),    -- V800R012C10 for CR5DLPUFM571(SBOM) Flexible Card Line Processing Unit E(LPUF-485A-E)
            Add:bnameTPND02CXPA02(229604),               --OptiX PTN 980,TPN2CXPA1,System Control,Cross-connect and Multi-protocol Process Unit
            " 

        REVISION    "202004180000Z"
        DESCRIPTION "V10.21,
            Add:fnameCE688148T6CQ(688202),               -- CloudEngine 6800,CE6881-48T6CQ,CE6881-48T6CQ switch
            Add:fnameCE886832CQ8DQP(688203),             -- CloudEngine 8800,CE8868-32CQ8DQ-P,CE8868-32CQ8DQ-P Switch
            Add:fnameCE885132CQ8DQP(688204),             -- CloudEngine 8800,CE8851-32CQ8DQ-P,CE8851-32CQ8DQ-P Switch
            Add:fnameCE686848S8CQP(688205),              -- CloudEngine 6800,CE6868-48S8CQ-P,CE6868-48S8CQ-P switch 
            Add:fnameCE686648S8CQP(688206),              -- CloudEngine 6800,CE6866-48S8CQ-P,CE6866-48S8CQ-P switch 
            Add:fnameCE688148T6CQK(688207),              -- CloudEngine 6800,CE6881-48T6CQ-K,CE6881-48T6CQ-K switch 
			Add:fnameCE588148T6CQ(688208),               -- CloudEngine 5800,CE5881-48T6CQ,CE5881-48T6CQ switch
			Add:bnameCE688148T6CQ(688372),               -- CloudEngine 6800,CE6881-48T6CQ,CE6881-48T6CQ switch 
            Add:bnameCE886832CQ8DQP(688373),             -- CloudEngine 8800,CE8868-32CQ8DQ-P,CE8868-32CQ8DQ-P Switch
            Add:bnameCE885132CQ8DQP(688374),             -- CloudEngine 8800,CE8851-32CQ8DQ-P,CE8851-32CQ8DQ-P Switch
            Add:bnameCE686848S8CQP(688375),              -- CloudEngine 6800,CE6868-48S8CQ-P,CE6868-48S8CQ-P switch 
            Add:bnameCE686648S8CQP(688376),              -- CloudEngine 6800,CE6866-48S8CQ-P,CE6866-48S8CQ-P switch 
            Add:bnameCESFU16JP(688377),                  -- Finished Board Unit,CE16800,CE-SFU16J-P,CE16816 Switch Fabric Unit J-P
            Add:bnameCESFU08JP(688378),                  -- Finished Board Unit,CE16800,CE-SFU08J-P,CE16808 Switch Fabric Unit J-P
            Add:bnameCESFU08HP(688379),                  -- Finished Board Unit,CE16800,CE-SFU08H-P,CE16808 Switch Fabric Unit H-P
            Add:bnameCESFU04JP(688380),                  -- Finished Board Unit,CE16800,CE-SFU04J-P,CE16804 Switch Fabric Unit J-P
            Add:bnameCESFU04HP(688381),                  -- Finished Board Unit,CE16800,CE-SFU04H-P,CE16804 Switch Fabric Unit H-P
            Add:bnameCEMPUE(688382),                     -- Finished Board Unit,CE16800,CE-MPUE,CE16800 Main Processing Unit E
            Add:bnameCEMPUD(688383),                     -- Finished Board Unit,CE16800,CE-MPUD,CE16800 Main Processing Unit D
            Add:bnameCEL48XSHGAP(688384),                -- Finished Board Unit, CloudEngine 16800, CEL48XSHGA-P, 48-port 25GE and 2-port 100GE interface card with ENP (EGA, QSFP28)
            Add:bnameCEL48CQHGP(688385),                 -- Finished Board Unit,CloudEngine 16800,CEL48CQHG-P,48-port 100GE interface card (HG-P, QSFP28)
            Add:bnameCEL36DQHGP(688386),                 -- Finished Board Unit,CloudEngine 16800,CEL36DQHG-P,36-port 400GE interface card (HG-P,QSFP-DD)
            Add:bnameCE688148T6CQK(688387),              -- CloudEngine 6800,CE6881-48T6CQ-F,CE6881-48T6CQ-F switch
			Add:bnameCEL72XSHGAP(688388),                -- Finished Board Unit, CloudEngine 16800, CEL72XSHGA-P, 72-port 25GE and 6-port 100GE interface card with ENP 
			Add:bnameCE588148T6CQ(688389),               -- CloudEngine 5800,CE5881-48T6CQ,CE5881-48T6CQ switch
            "
		
		REVISION    "202004130000Z"
        DESCRIPTION "V10.20,
            Add:virent8090DEVCR5DSFUIM17E(567870),         -- V8R12C10 for CR5DSFUIM17E(SBOM) 480Gbps Switch Fabric Unit E(SFUI-480A-E)
            Add:virent8090DEVCR5DSFUIM07E(567871),         -- V8R12C10 for CR5DSFUIM07E(SBOM) 480bps Switch Fabric Unit E(SFUI-480-E)
            Add:virent8090DEVCR5DSFUIM17F(567872),         -- V8R12C10 for CR5DSFUIM17F(SBOM) 480Gbps Switch Fabric Unit F(SFUI-480-F)
            Add:virent8090DEVCR5D0SRUAB71(567873),         -- V8R12C10 for CR5D0SRUAB71(SBOM) Switch and Route Processing Unit A11
            Add:virent8090DEVCR5DSFUIM07F(567874),         -- V8R12C10 for CR5DSFUIM07F(SBOM) 480Gbps Switch Fabric Unit F(SFUI-480A-F)
            Add:virent8090DEVCR5D0SRUAB70(567875),         -- V8R12C10 for CR5D0SRUAB70(SBOM) Switch and Route Processing Unit A11A
            Add:virent600DEVCR8DIPU240C1(800004),          --V8R12C00 NetEngine-8000-M8 CR8DIPU240C1(SBOM), M8
            Add:virent600DEVCR8DIPU240C2(800005),          --V8R12C00 NetEngine-8000-M8 CR8DIPU240C2(SBOM), M8
            Add:virent8090DEVCR5D0SRUAC76(567860),         --V800R012C00 for CR5D0SRUAC76(SBOM) Switch and Route Processing Unit A162
            Add:virent8090DEVCR9P9KHALM8B(567836),         --V800R012C00 for CR9P9KHALM8B(SBOM) 20-Port 100GE-QSFP28 Integrated Line Process Unit(LPUI-2TA)
            Add:fname8090NE40E-X4A(562111),                --Quidway NE40E-X4A FRAME,
            Add:bnameTPQD02CXPA00(229565),                 --OptiX PTN 990E,TPQ2CXPA0,System Control,Cross-connect and Multi-protocol Process Unit
            Add:subbname8090DEVCR5D00C2CF71(225875),       --2-Port Channelized STM-1c POS-SFP + 24-Port Channelized E1 Flexible Card(P53)
            Add:subbname8090DEVCR5D00E8GF72(225876),       --8-Port 100/1000Base-X-SFP + 8-Port STM-4c POS-SFP Flexible Card(P53)
            Add:subbname8090DEVCR5D00E8GF73(225877),       --8-Port 100/1000Base-X-SFP + 8-Port STM-1c POS-SFP Flexible Card(P53)
            Add:subbname8090DEVCR5D00E8GF73-(225878),      --8-Port 100/1000Base-X-SFP + 8-Port OC-3c/STM-1c POS-SFP Flexible Card(P53)
            Add:subbname8090DEVCR5D00E8GF72-(225879),      --8-Port 100/1000Base-X-SFP + 8-Port OC-12c/STM-4c POS-SFP Flexible Card(P53)
            Add:subbname8090DEVCR5D00C2CF71-(225880),      --2-Port Channelized STM-1c POS-SFP + 24-Port Channelized E1 Flexible Card(P53)
            Add:fnamePTN980(226364),                               -- PTN980 chassis
            Add:fnamePTN970C(226363),                            -- PTN970C chassis
            Add:fnamePTN916-F(226362),                           -- PTN916-F chassis
            Add:bnameTPND01CXPA00(229599),               --OptiX PTN 980,TPN1CXPA0,System Control,Cross-connect and Multi-protocol Process Unit
            Add:bnameTPND01CXPB00(229601),               --OptiX PTN 980,TPN1CXPB0,System Control,Cross-connect and Multi-protocol Process Unit
            Add:bnameTPND01CXPC00(229603),               --OptiX PTN 980,TPN1CXPC0,System Control,Cross-connect and Multi-protocol Process Unit
            Add:virentTPRD01CXPA02(229597),                 -- OptiX PTN 970C,TPR1CXPA1,System Control,Cross-connect and Multi-protocol Process Unit
            Add:virentTPQD01CXPA00(229590),                 -- OptiX PTN 990E,TPQ1CXPA0,System Control,Cross-connect and Multi-protocol Process Unit
            Add:virentTPQD01CXPA02(229591),                 -- OptiX PTN 990E,TPQ1CXPA1,System Control,Cross-connect and Multi-protocol Process Unit
            Add:virentTPSM0HOSTB01(229592),                -- PTN 916-F - 2 channels AC entries,with 6*10GE(o),14*GE/FE(o),4*GE/FE(e),16*E1
            Add:virentTPSM0HOSTA02(229593),                -- PTN 916-F - 2 channels DC entries,with 6*10GE(o),14*GE/FE(o),4*GE/FE(e),16*E1
            Add:virentTPSM0HOSTB02(229594),                -- PTN 916-F - 2 channels AC entries,with 6*10GE(o),14*GE/FE(o),4*GE/FE(e),16*E1
            Add:virentTPSM0HOSTA03(229595),                -- PTN 916-F - 2 channels DC entries,with 6*10GE(o),14*GE/FE(o),4*GE/FE(e),16*E1
            Add:virentTPSM0HOSTB03(229596),                -- PTN 916-F - 2 channels AC entries,with 6*10GE(o),14*GE/FE(o),4*GE/FE(e),16*E1
            " 

        REVISION    "202004090000Z"
        DESCRIPTION "V10.19,
            Add: bnameH832CCMB(156101),         --Master board of MA5818 device
            " 
        
         REVISION    "202004080000Z"
        DESCRIPTION "V10.18
             Add: fnameNETENGINE-8000-M1D-DC(226359),   -- Quidway fnameNETENGINE-8000-M1D-AC FRAME for V8R12C10
             Add: virentANKD01CXPA00(225345),                     --ATN 950C,ANK3CXPA0,System Control,Cross-connect and Multi-protocol Process Unit with 480G
             Add: virentANPM001AICG0(225661),                     -- ATN 905-G,ANP2CXPD,ATN 905-G System,AC,2*GE/FE Combo,2*GE/FE(o),2*GE/FE(e)
             Add: fnameATNDEV905-G-AC(225660),                --ATN905-G-AC chassis
          "
    

        REVISION    "202004030000Z"
        DESCRIPTION "V10.17"

        REVISION    "202004020000Z"
         DESCRIPTION "V10.16,
            Add: virent8090DEVCR5DSFUIT252(561840),    -- V8R12C10 for CR5DSFUIT252(SBOM) NE5000E CCC-A 1.6T Cluster Central Switch Fabric Unit G-C(SFUI-1T6-G)
            Add: virent8090DEVCR5DSFUIT253(561841),    -- V8R12C10 for CR5DSFUIT253(SBOM) NE5000E CCC-A 1.6T Cluster Central Switch Fabric Unit G-C(SFUI-1T6-G)
            Add: virent8090DEVCR5DSFUIT2DH(561842),    -- V8R12C10 for CR5DSFUIT2DH(SBOM) NE5000E CCC-A 1.6T Cluster Central Switch Fabric Unit H-C(SFUI-1T6-H)
            Add: virent8090DEVCR5DSFUIT2DJ(561844),    -- V8R12C10 for CR5DSFUIT2DJ(SBOM) NE5000E CCC-A 1.6T Cluster Central Switch Fabric Unit H-C(SFUI-1T6-H)
            Add: virent8090DEVCR5DSFUIT2D0(561843),    -- V8R12C10 for CR5DSFUIT2D0(SBOM) NE5000E CCC-A 1.6T Cluster Central Switch Fabric Unit D-C(SFUI-1T6-D)
            Add: virent8090DEVCR5DSFUIT2D1(561845),    -- V8R12C10 for CR5DSFUIT2D1(SBOM) NE5000E CCC-A 1.6T Cluster Central Switch Fabric Unit D-C(SFUI-1T6-D)
            "
				
        REVISION    "202003250000Z"
        DESCRIPTION "V10.15"

        REVISION    "202003250000Z"
         DESCRIPTION "V10.14,
            Add: virentCR8PM1DBASC1(226361),  -- NetEngine 8000 M1D,CR8PM1DBASC1,NetEngine 8000 M1D Basic Configuration, DC Power (Port Capacity 4*100GE/50GE+16*25GE/10GE/GE/FE+8*10GE/GE/FE,exclude auxiliary materials)
            "
        
        REVISION    "202003170000Z"
            DESCRIPTION "V10.13"

        REVISION    "202003170000Z"
            DESCRIPTION "V10.12,
                Add:virent8090DEVCR5DSFUIT076(567850),    --V800R012C00 for CR5DSFUIT076(SBOM) 1Tbps Switch Fabric Unit G(SFUI-1T-G)
                Add:virent8090DEVCR5DSFUIT077(567851),    --V800R012C00 for CR5DSFUIT077(SBOM) 1Tbps Switch Fabric Unit G(SFUI-1TA-G)
                Add:virent8090DEVCR5DSFUIT078(567852),    --V800R012C00 for CR5DSFUIT078(SBOM) 1Tbps Switch Fabric Unit H(SFUI-1T-H)
                Add:virent8090DEVCR5DSFUIT079(567853),    --V800R012C00 for CR5DSFUIT079(SBOM) 1Tbps Switch Fabric Unit H(SFUI-1TA-H)
                Add:virent8090DEVCX6DSFUIT072(567854),    --V800R012C00 for CX6DSFUIT072(SBOM) 1Tbps Switch Fabric Unit G(SFUI-1T-G)
                Add:virent8090DEVCX6DSFUIT073(567855),    --V800R012C00 for CX6DSFUIT073(SBOM) 1Tbps Switch Fabric Unit H(SFUI-1T-H)
                Add:virent8090DEVTNRDSFUIT072(567856),    --V800R012C00 for TNRDSFUIT072(SBOM) 1Tbps Switch Fabric Unit G(SFUI-1T-G)
                Add:virent8090DEVTNRDSFUIT073(567857),    --V800R012C00 for TNRDSFUIT073(SBOM) 1Tbps Switch Fabric Unit H(SFUI-1T-H)
                Add:virent8090DEVCX6DSFUIT27J(567858),    --V800R012C00 for CX6DSFUIT27J(SBOM) Switch Fabric Unit G(SFUI-1T-G)
                Add:virent8090DEVCX6DSFUIT21H(567859),    --V800R012C00 for CX6DSFUIT21H(SBOM) Switch Fabric Unit H(SFUI-1T-H)
                Add:virent8090DEVCR5D0SRUADK1(567837),    -- V8R12C10 for CR5D0SRUADK1(SBOM) Switch and Route Processing Unit A13-K(32G Memory)
                Add:virent8090DEVCR5DSFUIT2KN(567838),    -- V8R12C10 for CR5DSFUIT2KN(SBOM) 2Tbps Switch Fabric Unit H(SFUI-2T-HK)
                Add:virent8090DEVCR5DLPUFF3K1(567839),    -- V8R12C10 for CR5DLPUFF3K1(SBOM) Flexible Card Line Processing Unit CM(LPUF-243-K)
                Add:virent8090DEVCR5DLPUF53K0(567840),    -- V8R12C10 for CR5DLPUF53K0(SBOM) Flexible Card Line Processing Unit(LPUF-53-K)
                Add:virent8090DEVCR5D00EENBK3(567841),    -- V8R12C10 for CR5D00EENBK3(SBOM) 20-Port 100GBase-QSFP28 Integrated Line Processing Unit (LPUI-2T-K)
                Add:virent8090DEVCR5DVSUFK0K2(567842),    -- V8R12C10 for CR5DVSUFK0K2(SBOM) Integrated Service Unit 400A(VSUI-400-K)
                Modify:virent600DEVCR8D00EKNBCS(688368) to virent600DEVCR8D00EKNBC0(688375),    --V8R12C00 40-Port 100GBase-QSFP28 Integrated Line Processing Unit(LPUIA-4T)
                Modify:virent600DEVCR8D00LRXFCS(688372) to virent600DEVCR8D00LRXFC0(688376),    --V8R12C00 72-Port 25G(SFP28)/10GE(SFP+)/GE(SFP) Integrated Line Processing Unit(LPUIA-2T)
                Add:fname8090NE40E-X8AK(562107),            --Quidway NE40E-X8AK FRAME,
                Add:fname8090NE40E-X8AK-DC(562108),         --Quidway NE40E-X8AK-DC FRAME,
                Add:fname8090NE40E-X8AK-HVDC(562109),       --Quidway NE40E-X8AK-HVDC FRAME,
                Modify:fname8090NE5000EX-A(561173) to fname8090NE5000EX16A(561173),        --Quidway NE5000E-X16A FRAME,
                Add:fname8090NE5000EX16B(561816),        --Quidway NE5000E-X16B FRAME,
            "

         REVISION    "202003130000Z"
          DESCRIPTION "V10.11,"   

        REVISION    "202003090000Z"
            DESCRIPTION "V10.10,
                Add:fnameMA5801FL16(148515),       --  Backplane of the MA5801-FL16.
                Add:fnameMA5801SFL16(148516),      --  Backplane of the MA5801S-FL16.
                Add:bnameH921MPCB(148701),         --  control board of MA5801-FL16.
                Add:bnameV931MPBA(148702),         --  control board of MA5801S-FL16.
                Add:bnameV921NXHC(148703),         --  4*10GE board of MA5801-FL16.
                Add:bnameV921FLHF(148704),         --  16*flex-PON board of MA5801-FL16.
                Add:bnameV921CIUA(148705),         --  GPIO board of MA5801-FL16.
                Add:bnamePAC300S12(148706),        --  AC Power board of MA5801-FL16.
                Add:bnamePDC300S12(148707),        --  DC Power board of MA5801-FL16.
                Add:bnameV931FLHF(148708),         --  16*flex-PON board of MA5801-FL16.
                Add:bnameV931NXHC(148709),         --  4*10GE board of MA5801S-FL16.
                Add:bnameV931CIUA(148710),         --  GPIO board of MA5801S-FL16.
                Add:bnameH931PICA(148711),         --  DC Power board of MA5801S-FL16.
                Add:bnameH931PICB(148712),         --  AC Power board of MA5801S-FL16.
            "

		REVISION    "202003060000Z"
		DESCRIPTION "V10.09,
			Add:portnameLE0225FP(659470)
                                                         Add:fname8031S5732-H48UM2CC(537396),            
                                                         Add:fname8031S5732-H24UM2CC(537397),                 
                                                         Add: fname8031S5332-H24UM2CC(537398),                 
                                                         Add: fname8031S5732-H48XUM2CC(537399),                 
                                                         Add:fname8031S5735-S24T4X-I(537400),       
                                                         Add: bname8031S5732-H48UM2CC(537580),                      
                                                        Add: bname8031S5732-H24UM2CC(537581),                 
                                                        Add: bname8031S5332-H24UM2CC(537582),                        
                                                        Add: bname8031S5732-H48XUM2CC(537583),                          
                                                       Add: bname8031S5735-S24T4X-I(537584),                           		"
		REVISION    "202003060000Z"
		DESCRIPTION "V10.08,
			Add:fnameIPS12004-AC        (16715951) 
			Add:fnameIPS12004-DC        (16715952) 
			Add:fnameIPS12008-AC        (16715953) 
			Add:fnameIPS12008-DC        (16715954)

			Add:bnameIPS-LPUA-48XS         (16748644)
			Add:bnameI-LPUA-4CQ-24XS        (16748645)
			Add:bnameI-LPUA-2CQ-24XS        (16748646)
			Add:bnameMPUA-IPS-X4X8       (16748647)
			Add:bnameSFUA-IPS12008        (16748648)
			Add:bnameSPUA-IPS-01        (16748649)
			Add:bnameSPUA-IPS-02        (16748650)

			Add: subbnameSPCA-IPS-01(16728137)
			Add: subbnameSPCA-IPS-02(16728138)
		"

        REVISION    "202003050000Z"
            DESCRIPTION "V10.07,
                Add:fnameCE686348S6CQK(688199),          -- CloudEngine 6800,CE6863-48S6CQ-KB,CE6863-48S6CQ-KB switch
                Add:fnameCE688148S6CQK(688200),              -- CloudEngine 6800,CE6881-48S6CQ-KB,CE6881-48S6CQ-KB switch
				Add:fnameCE6881E48S6CQ(688201),              -- CloudEngine 6800,CE6881E-48S6CQ-B,CE6881E-48S6CQ-B switch
                Add:bnameCE686348S6CQK(688354),              -- CloudEngine 6800,CE6863-48S6CQ-KF,CE6863-48S6CQ-KF switch 
				Add:bnameCE688148S6CQK(688355),              -- CloudEngine 6800,CE6881-48S6CQ-KF,CE6881-48S6CQ-KF switch 
				Add:bnameCE6881E48S6CQ(688356),              -- CloudEngine 6800,CE6881E-48S6CQ-B,CE6881E-48S6CQ-B switch 
				Add:bnameCEMPUDHK(688357),                   -- Finished Board Unit,CE16800,CE-MPUD-HK,CE16800 Main Processing Unit D-HK (half-width)
				Add:bnameCEMPUDFK(688358),                   -- Finished Board Unit,CE16800,CE-MPUD-FK,CE16800 Main Processing Unit D-FK (full-width)
				Add:bnameCEL36CQFDGK(688359),                -- Finished Board Unit,CloudEngine 16800,CEL36CQFD-GK,36-port 100GE interface card (FD-GK, QSFP28)
				Add:bnameCEL18CQFDGK(688360),                -- Finished Board Unit,CloudEngine 16800,CEL18CQFD-GK,18-port 100GE interface card (FD-GK, QSFP28)
				Add:bnameCEL36LQFDGK(688361),                -- Finished Board Unit,CloudEngine 16800,CEL36LQFD-GK,36-port 40GE interface card (FD-GK, QSFP+)
				Add:bnameCEL24LQFDGK(688362),                -- Finished Board Unit,CloudEngine 16800,CEL24LQFD-GK,24-port 40GE interface card (FD-GK, QSFP+)
				Add:bnameCEL48XSFDGK(688363),                -- Finished Board Unit,CloudEngine 16800,CEL48XSFD-GK,48-port 10GE interface card (FD-GK, SFP+)
				Add:bnameCESFU04GGK(688364),                 -- Finished Board Unit,CE16800,CE-SFU04G-GK,CE16804 Switch Fabric Unit GK
				Add:bnameCESFU08GGK(688365),                 -- Finished Board Unit,CE16800,CE-SFU08G-GK,CE16808 Switch Fabric Unit GK
				Add:bnameCESFU16GGK(688366),                 -- Finished Board Unit,CE16800,CE-SFU16G-GK,CE16816 Switch Fabric Unit GK
				Add:bnameCEL48XSFD1G(688367),                -- Finished Board Unit,CloudEngine 16800,CEL48XSFD1-G,48-port 10GE interface card (FD1-G, SFP+)
				Add:bnameCEL24LQFD1G(688368),                -- Finished Board Unit,CloudEngine 16800,CEL24LQFD1-G,24-port 40GE interface card (FD1-G, QSFP+)
				Add:bnameCEL36LQFD1G(688369),                -- Finished Board Unit,CloudEngine 16800,CEL36LQFD1-G,36-port 40GE interface card (FD1-G, QSFP+)
				Add:bnameCESFU04F1G(688370),                 -- Finished Board Unit,CE16800,CE-SFU04F1-G,CE16804 Switch Fabric Unit F1
				Add:bnameCESFU08F1G(688371),                 -- Finished Board Unit,CE16800,CE-SFU08F1-G,CE16808 Switch Fabric Unit F1
            " 
            
        REVISION    "202003020000Z"
            DESCRIPTION "V10.06,"   

        REVISION    "202002270000Z"
            DESCRIPTION "V10.05,"   

        REVISION    "202002250000Z"
            DESCRIPTION "V10.04,"   


        REVISION    "202002210000Z"
		DESCRIPTION "V10.03,
		Add:fnameIPS6555E-DC        (16715927) 
		Add:fnameUSG6575E-B-AC        (16715928) 
		Add:fnameUSG6605E-B-AC        (16715929) 
		Add:fnameUSG6502E-C        (16715930) 
		Add:fnameUSG6503E-C        (16715931) 
		Add:fnameUSG6302E-C        (16715932) 
		Add:fnameUSG6303E-C        (16715933) 
		Add:fnameUSG6306E-AC        (16715934) 
		Add:fnameUSG6316E-AC        (16715935) 
		Add:fnameUSG6326E-AC        (16715936) 
		Add:fnameUSG6501E-C        (16715937) 
		Add:fnameUSG6301E-C        (16715938) 
		Add:fnameUSG6510E-DK-AC        (16715939) 
		Add:fnameUSG6520E-K-AC        (16715940) 
		Add:fnameUSG6560E-K-AC        (16715941) 
		Add:fnameUSG6590E-K-AC        (16715942) 
		Add:fnameUSG6620E-K-AC        (16715943) 
		Add:fnameUSG6640E-K-AC        (16715944) 
		Add:fnameIPS6520E-K-AC        (16715945) 
		Add:fnameIPS6610E-K-AC        (16715946) 
		Add:fnameIPS6610ED-K-AC        (16715947) 
		Add:fnameIPS6515E-B-AC        (16715948) 
		Add:fnameIPS6525E-AC        (16715949) 
		Add:fnameIPS6535E-AC        (16715950)
		
		Add:bnameMPUA-ADS-X4X8         (16748642)
		Add:bnameE9KE-LPUA-12CQ        (16748643)
			  "
        REVISION    "202002180000Z"
            DESCRIPTION "V10.02,"   

        REVISION    "202002130000Z"
            DESCRIPTION "V10.01," 
    
        REVISION    "202002110000Z"
            DESCRIPTION "V10.00,
                Add:bnameH901MPLF(148700),         --  control board of MA5800-X17.
                Add:apply for 148701 to 148999 as board type reserve value for MA5800
                add:apply for 148541 to 148560 as frame type reserve value for MA5800
                add:apply for 148526 to 148555 as subboard type reserve value for MA5800
            "
        
		 REVISION    "202002060936Z"
         DESCRIPTION "V9.99,
		      Add: virent8090DEVCR9D0MPUR181(688406),    -- V8R12C00 for CR9D0MPUR181(SBOM) NE9000-8 Main Processing Unit R1(MPUR1A)
			  Add: virent8090DEVCR9D0SFUT48G(688407),    -- V8R12C00 for CR9D0SFUT48G(SBOM) NE9000-8 Switch Fabric Unit E for Single Chassis(SFU4T-EA)
			 "
		 
         REVISION    "202001210000Z"
         DESCRIPTION "V9.98,"

         REVISION    "202001160000Z"
         DESCRIPTION "V9.97,
              Add: fnameNETENGINE-8000-M14K(688400),       -- NETENGINE-8000-M14K (fnameNETENGINE-8000-M14K)
              Add: fnameNETENGINE-8000-M14K-DC(688401),    -- NETENGINE-8000-M14K-DC (fnameNETENGINE-8000-M14K-DC)
              Add: fnameNETENGINE-8000-M14K-AC(688402),    -- NETENGINE-8000-M14K-AC (fnameNETENGINE-8000-M14K-AC)
              Add: fnameNETENGINE-8000-M8K(688403),        -- NETENGINE-8000-M8K (fnameNETENGINE-8000-M8K)
              Add: fnameNETENGINE-8000-M8K-DC(688404),     -- NETENGINE-8000-M8K-DC (fnameNETENGINE-8000-M8K-DC)
              Add: fnameNETENGINE-8000-M8K-AC(688405),     -- NETENGINE-8000-M8K-AC (fnameNETENGINE-8000-M8K-AC)
              Add: virentDEVCR8DIPU1T2K0(688500),          -- V8R12C10 for DEVCR8DIPU1T2K0(SBOM) Integrated Network Processing Unit ((IPU-1T2-K))
              Add: virentDEVCR8DIPU1T2K1(688501) ,         -- V8R12C10 for DEVCR8DIPU1T2K1(SBOM) Integrated Network Processing Unit (IPU-1T2-K1)
              Add: virentDEVCR8DIPU480K0(688502),          -- V8R12C10 for DEVCR8DIPU480K0(SBOM) Integrated Network Processing Unit (IPU-480-K)
              Add: virentCR8DCXP160K0(226353),             -- V800R012C10 for CR8DCXP160K0(SBOM) NetEngine 8000 M6K,CR81CXP160C,System Control,Cross-connect and Multi-protocol Process Unit (CXP-160-K)
              Add: virentCR8DCXP160K1(226354),             -- V800R012C10 for CR8DCXP160K1(SBOM) NetEngine 8000 M6K,CR81CXP160D,System Control,Cross-connect and Multi-protocol Process Unit (CXP-160-K1)
              Add: fnameNETENGINE-8000-M6K(226355),        -- Quidway fnameNETENGINE-8000-M6K FRAME for V8R12C10
              Add: fnameNETENGINE-8000-M6K-AC(226356),     -- Quidway fnameNETENGINE-8000-M6K-AC FRAME for V8R12C10
              Add: fnameNETENGINE-8000-M6K-DC(226357),     -- Quidway fnameNETENGINE-8000-M6K-DC FRAME for V8R12C10
             "
         REVISION    "202001140000Z"
         DESCRIPTION "V9.96,"

         REVISION    "202001130000Z"
         DESCRIPTION "V9.95,"

         REVISION    "202001070000Z"
         DESCRIPTION "V9.94,"

         REVISION    "202001030000Z"
         DESCRIPTION "V9.93,
               Add: subnameEN31PERE(536805),                   --Manufactured Board,PAC460S55,EN31PERET,poe 460w power board
            "


         REVISION    "202001020000Z"
         DESCRIPTION "V9.92,
               Modify: virent8090DEVCR5DVSUIK071(676951),    -- V8R12C00 for CR5DVSUIK071(SBOM) Integrated Versatile Service Unit 400(VSUI-400-E)
               Modify: virent8090DEVCR5DVSUIK073(676952),    -- V8R12C00 for CR5DVSUIK073(SBOM) Integrated Versatile Service Unit 400(VSUI-400A-E)
               Modify: virent8090DEVME0DVSUIK071(676953),    -- V8R12C00 for ME0DVSUIK071(SBOM) Integrated Versatile Service Unit(VSUI-400-E)
               Modify: virent8090DEVME0DVSUIK073(676954),    -- V8R12C00 for ME0DVSUIK073(SBOM) Integrated Versatile Service Unit(VSUI-400A-E)
               Modify: virent8090DEVCR5DVSUIK070(676955),    -- V8R12C00 for CR5DVSUIK070(SBOM) Integrated Service Unit 400(VSUI-400)
               Modify: virent8090DEVCR5DVSUIK072(676956),    -- V8R12C00 for CR5DVSUIK072(SBOM) Integrated Service Unit 400A(VSUI-400A)
               Modify: virent8090DEVCR5DJYSUK072(676957),    -- V8R12C00 for CR5DJYSUK072(SBOM) Public Security Service Unit(PSSU-A)
               Modify: virent8090DEVME0DVSUIK070(676958),    -- V8R12C00 for ME0DVSUIK070(SBOM) Integrated Service Unit 400(VSUI-400)
               Modify: virent8090DEVME0DVSUIK072(676959),    -- V8R12C00 for ME0DVSUIK072(SBOM) Integrated Versatile Service Unit(VSUI-400A)
               Modify: virent8090DEVME0DJYSUK070(676960),    -- V8R12C00 for ME0DJYSUK070(SBOM) Public Security Service Unit(PSSU-A)
            "
            REVISION    "201912230000Z"
            DESCRIPTION "V9.91,
                 Modify: virent8090DEVCR5D00E4KB60(561784),    -- V8R11C10 for CR5D00E4KB60(SBOM) 4-Port 400GBase QSFP-DD Integrated Line Process Unit(NE5000E LPUI-1T6)
            "
            REVISION    "201912230000Z"
            DESCRIPTION "V9.90,
                 Add: virent8090DEVCR5D00E4KB60(561784),    
            "

            REVISION    "201912230000Z"
            DESCRIPTION "V9.89,
                Add:bnameH901MPSB(148684),         --  control board of MA5800-X2.
            "
            
            REVISION    "201912210000Z"
            DESCRIPTION "V9.88,
                Add:virentCR8DCXP160C0(225350),             -- V800R012C00 for CR8DCXP160C0(SBOM) NetEngine 8000 M6,CR81CXP160AS,System Control,Cross-connect and Multi-protocol Process Unit (CXP-160)
                Add:virentCR8DCXP160C1(225351),             -- V800R012C00 for CR8DCXP160C1(SBOM) NetEngine 8000 M6,CR81CXP160A,System Control,Cross-connect and Multi-protocol Process Unit (CXPA-160)
                Add:fnameNETENGINE-8000-M6(225352),         -- Quidway fnameNETENGINE-8000-M6 FRAME for V8R12C00
                Add:fnameNETENGINE-8000-M6-AC(225353),      -- Quidway fnameNETENGINE-8000-M6-AC FRAME for V8R12C00
                Add:fnameNETENGINE-8000-M6-DC(225354),      -- Quidway fnameNETENGINE-8000-M6-DC FRAME for V8R12C00
                Add:fnameATNDEV950D-AC(225619),             -- ATN950D-AC chassis
                Add:fnameATNDEV950D-DC(225620),             -- ATN950D-DC chassis
		"
            
            REVISION    "201912170000Z"
            DESCRIPTION "V9.87, " 
				
			REVISION    "201912130000Z"
            DESCRIPTION "V9.86,  
                Add:virent8090DEVCX6DISUFM310(676964),    -- V800R012C10 for CX6DISUFM310(SBOM) Flexible Card Line Processing Unit A(ISUF-483A)
                Add:virent8090DEVCX6DISUFF310(676965),    -- V800R012C10 for CX6DISUFF310(SBOM) Flexible Card Line Processing Unit A(ISUF-243A)
                Add:virent8090DEVCX6DISUF5310(676966),    -- V800R012C10 for CX6DISUF5310(SBOM) Flexible Card Line Processing Unit A(ISUF-53A)
                Add:virent8090DEVCR5DLPUFF570(676967),    -- V800R012C10 for CR5DLPUFF570(SBOM) Flexible Card Line Processing Unit E(LPUF-245A-E)
                Add:virent8090DEVCR5DLPUFM570(676968),    -- V800R012C10 for CR5DLPUFM570(SBOM) Flexible Card Line Processing Unit E(LPUF-485A-E)
			" 
            
            REVISION    "201912120000Z"
            DESCRIPTION "V9.85,  "   
          
            REVISION    "201912100000Z"
            DESCRIPTION "V9.84,  "    
            
			REVISION    "201912070000Z"
            DESCRIPTION "V9.83,
                Add:virent8090DEVCR5DLPUFM371(676961),    -- V800R012C10 for CR5DLPUFM371(SBOM) Flexible Card Line Processing Unit A(LPUF-483A)
                Add:virent8090DEVCR5DLPUFF371(676962),    -- V800R012C10 for CR5DLPUFF371(SBOM) Flexible Card Line Processing Unit A(LPUF-243A)
                Add:virent8090DEVCR5DLPUF5371(676963),    -- V800R012C10 for CR5DLPUF5371(SBOM) Flexible Card Line Processing Unit(LPUF-53)
                Add:virent8090DEVCR5D0SRUAE71(567821),    --V800R012C00 for CR5D0SRUAE71(SBOM) Switch and Route Processing Unit A14A(32G Memory)
                Add:virent8090DEVME0D0SRUAD71(567823),    --V800R012C00 for ME0D0SRUAD71(SBOM) Switch and Route Processing Unit A15(32G Memory)
                Add:virent8090DEVCR5DSFUIT27M(567828),    --V800R012C00 for CR5DSFUIT27M(SBOM) 2Tbps Switch Fabric Unit H(SFUI-2T-H)
                Add:virent8090DEVCR5DSFUIT27N(567829),    --V800R012C00 for CR5DSFUIT27N(SBOM) 2Tbps Switch Fabric Unit H(SFUI-2TA-H)
                Add:virent8090DEVCR5DSFUIT27K(567830),    --V800R012C00 for CR5DSFUIT27K(SBOM) 2Tbps Switch Fabric Unit G(SFUI-2T-G)
                Add:virent8090DEVCR5DSFUIT27L(567831),    --V800R012C00 for CR5DSFUIT27L(SBOM) 2Tbps Switch Fabric Unit G(SFUI-2TA-G)
                Add:virent8090DEVCX6DSFUIT27F(567832),    --V800R012C00 for CX6DSFUIT27F(SBOM) 2Tbps Switch Fabric Unit G(SFUI-2T-G)
                Add:virent8090DEVCX6DSFUIU07G(567833),    --V800R012C00 for CX6DSFUIU07G(SBOM) 2Tbps Switch Fabric Unit H(SFUI-2T-H)
                Add:virent8090DEVTNRDSFUIT27G(567834),    --V800R012C00 for TNRDSFUIT27G(SBOM) 2Tbps Switch Fabric Unit G(SFUI-2T-G)
                Add:virent8090DEVTNRDSFUIU07H(567835),    --V800R012C00 for TNRDSFUIU07H(SBOM) 2Tbps Switch Fabric Unit H(SFUI-2T-H)
                Add:virent8090DEVME0DSFUIT07E(567824),    --V800R012C00 for ME0DSFUIT07E(SBOM) 1Tbps Switch Fabric Unit E(SFUI-1T-E)
                Add:virent8090DEVME0DSFUIT17E(567825),    --V800R012C00 for ME0DSFUIT17E(SBOM) 1Tbps Switch Fabric Unit E(SFUI-1TA-E)
                Add:virent8090DEVME0DSFUIT07F(567826),    --V800R012C00 for ME0DSFUIT07F(SBOM) 1Tbps Switch Fabric Unit F(SFUI-1T-F)
                Add:virent8090DEVME0DSFUIT17F(567827)     --V800R012C00 for ME0DSFUIT17F(SBOM) 1Tbps Switch Fabric Unit F(SFUI-1TA-F)

            "
            REVISION    "201911300000Z"
            DESCRIPTION "V9.82,
		 Add: bnameHH903XSHDE(148685)        --  8*10G GPON board of MA5800.	    
                 Add: bnameH902NCEB(148688),         --  2x100G BOARD_GIC of MA5800.
                 Add: bnameH903FLHF(148689),         --  16*flex-PON board of MA5800.
            "                
            REVISION    "201911290000Z"
            DESCRIPTION "V9.81,
               Add: fnameBT82BP2HT8010(696833),         --T8010V800R019C20 Master board of MA5616 device
               Add: bnameBT82CPOHT8010(696835),         --T8010V800R019C20 main control board of T8010 bits, with one slot.
               Add: bnameBT82CPRHT8010(696836),         --T8010V800R019C20 main control board of T8010 bits, with two slots.
               Add: bnameBT82HDOU(696837),              --T8010V800R019C20 32 ports business board of T8010 bits.
               Add: bnameDPE1LAXF(696838),              --T8010V800R019C20 10 GE ports board of T8010 bits.
            "
            REVISION    "201911220000Z"
            DESCRIPTION "V9.80,
               Add: fnameNETENGINE-8000-X4-HVDC(688355),         --Quidway fnameNETENGINE-8000-X4-HVDC FRAME for V8R12C00
               Add: fnameNETENGINE-8000-X4-DC(688356),         --Quidway fnameNETENGINE-8000-X4-DC FRAME for V8R12C00
               Add: fnameNETENGINE-8000-X8-HVDC(688357),         --Quidway fnameNETENGINE-8000-X8-HVDC FRAME for V8R12C00
               Add: fnameNETENGINE-8000-X8-DC(688358),         --Quidway fnameNETENGINE-8000-X8-DC FRAME for V8R12C00
               Add: virent600DEVCR8D0MPUA1C0(688359),    --V8R12C00 NetEngine 8000 Main Processing Unit A1(MPUA1)
               Add: virent600DEVCR8D0MPUA1C1(688373),    --V8R12C00 NetEngine 8000 Main Processing Unit A1A(MPUA1A)
               Add: virent600DEVCR8DSFUI4TC1(688361),    --V8R12C00 NetEngine 8000 X8 4Tbps Switch Fabric Unit(SFUI-4T-B)
               Add: virent600DEVCR8DSFUI4TC3(688362),    --V8R12C00 NetEngine 8000 X8 4Tbps Switch Fabric Unit(SFUIA-4T-B)
               Add: virent600DEVCR8DSFUI4TC0(688363),    --V8R12C00 NetEngine 8000 X4 4Tbps Switch Fabric Unit(SFUI-4T-A)
               Add: virent600DEVCR8DSFUI4TC2(688364),    --V8R12C00 NetEngine 8000 X4 4Tbps Switch Fabric Unit(SFUIA-4T-A)
               Add: virent600DEVCR8D00EKNBCP(688365),    --V8R12C00 40-Port 100GBase-QSFP28 Integrated Line Processing Unit CM(LPUI-4T-CM)
               Add: virent600DEVCR8D00EKNBCR(688366),    --V8R12C00 40-Port 100GBase-QSFP28 Integrated Line Processing Unit CM(LPUIA-4T-CM)
               Add: virent600DEVCR8D00EKNBCQ(688367),    --V8R12C00 40-Port 100GBase-QSFP28 Integrated Line Processing Unit L(LPUI-4T-L)
               Add: virent600DEVCR8D00EKNBCS(688368),    --V8R12C00 40-Port 100GBase-QSFP28 Integrated Line Processing Unit L(LPUIA-4T-L)
               Add: virent600DEVCR8D00LRXFCP(688369),    --V8R12C00 72-Port 25GE(SFP28)/10GE(SFP+)/GE(SFP) Integrated Line Processing Unit CM(LPUI-2T-CM)
               Add: virent600DEVCR8D00LRXFCR(688370),    --V8R12C00 72-Port 25GE(SFP28)/10GE(SFP+)/GE(SFP) Integrated Line Processing Unit CM(LPUIA-2T-CM)
               Add: virent600DEVCR8D00LRXFCQ(688371),    --V8R12C00 72-Port 25GE(SFP28)/10GE(SFP+)/GE(SFP) Integrated Line Processing Unit L(LPUI-2T-L)
               Add: virent600DEVCR8D00LRXFCS(688372),    --V8R12C00 72-Port 25GE(SFP28)/10GE(SFP+)/GE(SFP) Integrated Line Processing Unit L(LPUIA-2T-L)            
            "
            REVISION    "201911200000Z"
            DESCRIPTION "V9.79,
               Add: virent8090DEVCR5DVSUIK071(676951),    -- V8R12C00 for CR5DVSUIK071(SBOM) Integrated Versatile Service Unit 400(VSUI-400-E)
               Add: virent8090DEVCR5DVSUFK073(676952),    -- V8R12C00 for CR5DVSUFK073(SBOM) Integrated Versatile Service Unit 400(VSUI-400A-E)
               Add: virent8090DEVME0DVSUIK071(676953),    -- V8R12C00 for ME0DVSUIK071(SBOM) Integrated Versatile Service Unit(VSUI-400-E)
               Add: virent8090DEVME0DVSUIK073(676954),    -- V8R12C00 for ME0DVSUIK073(SBOM) Integrated Versatile Service Unit(VSUI-400A-E)
               Add: virent8090DEVCR5DVSUFK070(676955),    -- V8R12C00 for CR5DVSUFK070(SBOM) Integrated Service Unit 400(VSUI-400)
               Add: virent8090DEVCR5DVSUFK072(676956),    -- V8R12C00 for CR5DVSUFK072(SBOM) Integrated Service Unit 400A(VSUI-400)
               Add: virent8090DEVCR5DJYSUK072(676957),    -- V8R12C00 for CR5DJYSUK072(SBOM) Public Security Service Unit(PSSU-A)
               Add: virent8090DEVME0DVSUFK070(676958),    -- V8R12C00 for ME0DVSUFK070(SBOM) Integrated Service Unit 400(VSUI-400)
               Add: virent8090DEVME0DVSUIK072(676959),    -- V8R12C00 for ME0DVSUIK072(SBOM) Integrated Versatile Service Unit(VSUI-400A)
               Add: virent8090DEVME0DJYSUK070(676960),    -- V8R12C00 for ME0DJYSUK070(SBOM) Public Security Service Unit(PSSU-A)
            "
            REVISION   "201911150000Z"
            DESCRIPTION  "V9.78,
           Add:subbname8090DEVANND0EM10F00(225789),      --10 Channels GE/FE Optical Interface Board
           "
            REVISION   "201911090000Z"
            DESCRIPTION  "V9.77,
                Add:virent8090DEVCR5D0MPUB872(676941),    -- V800R012C00 for CR5D0MPUB872(SBOM) Main Processing Unit B8C
                Add:virent8090DEVCR5DSFUIT074(676943),    -- V800R012C00 for CR5DSFUIT074(SBOM) 1Tbps Switch Fabric Unit E1(SFUI-1TC-E)
                Add:virent8090DEVCR5D0SRUAG71(676942),    -- V800R012C00 for CR5D0SRUAG71(SBOM) Switch and Route Processing Unit A15C
                Add:virent8090DEVCR5DSFUIT075(676944),    -- V800R012C00 for CR5DSFUIT075(SBOM) 1Tbps Switch Fabric Unit F1(SFUI-1TC-F)
                Add:virent8090DEVCR5D0EKGFC70(676945),    -- V800R012C00 for CR5D0EKGFC70(SBOM) 40-Port 100/1000Base-X-SFP Integrated Line Processing Unit (LPUI-52C)
                Add:virent8090DEVCR5D0EKXFC70(676946),    -- V800R012C00 for CR5D0EKXFC70(SBOM) 40-Port 10GBase LAN/WAN-SFP+ Integrated Line Processing Unit (LPUI-402C)
                Add:virent8090DEVCR5DLPUFT073(676947),    -- V800R012C00 for CR5DLPUFT073(SBOM) Flexible Card Line Processing Unit (LPUF-1T1C)
                Add:virent8090DEVCR5DLPUFM371(676948),    -- V800R012C10 for CR5DLPUFM370(SBOM) Flexible Card Line Processing Unit (LPUF-483)
                Add:virent8090DEVCR5DLPUFF371(676949),    -- V800R012C10 for CR5DLPUFF370(SBOM) Flexible Card Line Processing Unit (LPUF-243)
                Add:virent8090DEVCR5DLPUF5370(676950),    -- V800R012C10 for CR5DLPUF5370(SBOM) Flexible Card Line Processing Unit A(LPUF-53A)
                Add:fname8090NE40E-X8C-DC(562103),        --Quidway NE40E-X8C-DC FRAME,
                Add:fname8090NE40E-X16C-DC(562101),       --Quidway NE40E-X16C-DC FRAME,
                Add:fname8090NE40E-X8C(562106),           --Quidway NE40E-X8C FRAME,
                Add:fname8090NE40E-X16C(562105),          --Quidway NE40E-X16C FRAME,
                Add:fname8090NE40E-X16C-HVDC(562102),     --Quidway NE40E-X16C FRAME,HVDC
                Add:fname8090NE40E-X8C-HVDC(562104),      --Quidway NE40E-X8C FRAME,HVDC
                "
                
            REVISION   "201911080000Z"
            DESCRIPTION  "V9.76,
                Add: fnameCE686548S8CQSI(688198),             -- CloudEngine 6800, CE6865-48S8CQ-SI, CE6865-48S8CQ-SI switch
                Add: bnameCE686548S8CQSI(688348),             -- CloudEngine 6800, CE6865-48S8CQ-SI, CE6865-48S8CQ-SI switch
                Add: bnameCEMPUEHALF(688349),                 -- Finished Board Unit,CE16800,CE-MPUE-HALF,CE16800 Main Processing Unit E (half-width)
		Add: bnameCEL24LQFDAG(688350),                -- Finished Board Unit,CloudEngine 16800,CEL24LQFDA-G,24-port 40GE, 6-port 100GE interface card (FDA-G, QSFP+,QSFP28)
		Add: bnameCEMPUEFULL(688351),                 -- Finished Board Unit,CE16800,CE-MPUE-FULL,CE16800 Main Processing Unit E (full-width)
		Add: bnameCEL48GSFDG(688352),                 -- Finished Board Unit,CloudEngine 16800,CEL48GSFD-G,48-port 100M/GE interface card (FD-G, SFP)
		Add: bnameCEL18CQFDAG(688353),                -- Finished Board Unit,CloudEngine 16800,CEL18CQFDA-G,18-port 40GE, 18-port 100GE interface card (FDA-G, QSFP+,QSFP28)
                "
		
	    REVISION   "201911060000Z"
            DESCRIPTION  "V9.75,
                Modidy: fnameMA5821HH821Mabc(561669) to fnameMA5626HH821Mabc(561669),
                Modify: fnameMA5822HH821Mabc(561671) to fnameMA5620HH821Mabc(561671),
                "
            
            REVISION   "201911050000Z"
            DESCRIPTION  "V9.74,
                Add: bnamePTN7900TPA5FHD1(229556), --TPA5FHD1, 1-port 200 Gigabit Ethernet Switching Processing Board
                Add: bnamePTN7900TPA2EY16(229557), --TPA2EY16, 16-port 25 Gigabit Ethernet Switching Processing Board
                Add: bnamePTN7900TPA2EY8(229558), --TPA2EY8, 8-port 25 Gigabit Ethernet Switching Processing Board
                Add: bnamePTN7900TPA2FV8(229559),  --TPA2FV8, 8-port 50 Gigabit Ethernet Switching Processing Board
                Add: bnamePTN7900TPA3FHD2(229560),  --TPA3FHD2, 2-port 200 Gigabit Ethernet Switching Processing Board
                Add: bnamePTN7900TPA3FHD1(229561),  --TPA3FHD1, 1-port 200 Gigabit Ethernet Switching Processing Board
                Add: bnamePTN7900TPA5FH2(229562), --TPA5FH2, 2-port 100 Gigabit Ethernet Switching Processing Board
                Add: bnamePTN7900TPD3FHD4(229563), --TPD3FHD4,4-port 200 Gigabit Ethernet Switching Processing Board
                Add: bnamePTN7900TPA2EG16(229564), --TPA2EG16,16-port Gigabit Ethernet Switching Processing Board
                "

           REVISION    "201910300000Z"
 	 	    DESCRIPTION "V9.73,
                Add: bnameLE0D0G48SC01(659730),      --48-port 100/1000 SFP+ interface card for v2r19c00 S9300
                Add: bnameLE0D0G48TC01(659731),      --48-port 00/1000BASE-T interface card for v2r19c00 S9300
                Add: bnameLST3Y40SX6H0(659732),       --40-port 25GE SFP28 interface card (X6H,SFP28) for S9300X
                Add: bnameES0D0X12SA01(663680),      --12 port 10GE interface card  for V2R19C00
                Add: bnameES0D0G48SC01(663681),     --48 port 100/1000  SFP+  interface card for V2R19C00
                Add: bnameES0D0G48TC01(663682),     --48 port 10/100/1000BASE-TX  interface card for V2R19C00
                Add: fname8031S5731S-H24T4X-A(537381),                 --S5731S-H24T4X-A(24*10/100/1000BASE-T ports,4*10GE SFP+ ports,1*150W AC power)
                Add: fname8031S5731S-H48T4X-A(537382),                  --S5731S-H48T4X-A(48*10/100/1000BASE-T ports,4*10GE SFP+ ports,1*150W AC power)
                Add: fname8031S6730S-H24X6C-A(537383),                 --S6730S-H24X6C-A(24*10GE SFP+ ports,6*100GE QSFP28 ports,1*600W AC power)
                Add: fname8031S1730S-H24T4S-A(537384),                 --S1730S-H24T4S-A(24*10/100/1000BASE-T ports, 4*GE SFP ports, AC 110/220V)
                Add: fname8031S1730S-S24T4X-A(537385),                 --S1730S-S24T4X-A(24*10/100/1000BASE-T ports, 4*10GE SFP+ ports, AC 110/220V)
                Add: fname8031S1730S-H48T4S-A(537386),                 --S1730S-H48T4S-A(48*10/100/1000BASE-T ports, 4*GE SFP ports, AC 110/220V)
                Add: fname8031S5335-L48T4X-A(537387),                    --S5335-L48T4X-A(48*10/100/1000BASE-T ports, 4*10GE SFP+ ports, AC 110/220V)
                Add: fname8031S1730S-S48P4S-A(537388),                 --S1730S-S48P4S-A(48*10/100/1000BASE-T ports,4*GE SFP ports,PoE+,1*1000W PoE AC power)
                Add: fname8031S6730-H48X6C-K(537389),                 --S6730-H48X6C-K (48*10GE SFP+ ports, 6*40GE QSFP28 ports, optional license for upgrade to 6*100GE QSFP28, without power module) for V2R19C!0
                Add: fname8031S6730-H24X6C-K(537390),                 --S6730-H24X6C-K (24*10GE SFP+ ports, 6*100GE QSFP28 ports, without power module) for V2R19C!0
                Add: fname8031S5731-H48P4XC-K(537391),               --S5731-H48P4XC-K(48*10/100/1000BASE-T ports, 4*10GE SFP+ ports, 1*expansion slot, PoE+, without power module) for V2R19C!0
                Add: fname8031S5731-H24T4XC-K(537392),               --S5731-H24T4XC-K (24*10/100/1000BASE-T ports, 4*10GE SFP+ ports, 1*expansion slot, without power module) for V2R19C!0
                Add: fname8031S5731-H24P4XC-K(537393),               --S5731-H24P4XC-K (24*10/100/1000BASE-T ports, 4*10GE SFP+ ports, 1*expansion slot, PoE+, without power module) for V2R19C!0
                Add: fname8031S5732-H24S6Q-K(537394),                 --S5732-H24S6Q-K (20*GE SFP ports,4*10GE SFP+ ports,6*40GE QSFP ports,with Pluggable dual power module) for V2R19C!0
                Add: fname8031S5732-H48S6Q-K(537395),                 --S5732-H48S6Q-K (44*GE SFP ports,4*10GE SFP+ ports,6*40GE QSFP ports,with pluggable dual power module) for V2R19C!0
                Add: bname8031S5731S-H24T4X-A(537565),                      --S5731S-H24T4X-A(24*10/100/1000BASE-T ports,4*10GE SFP+ ports,1*150W AC power)
                Add: bname8031S5731S-H48T4X-A(537566),                      --S5731S-H48T4X-A(48*10/100/1000BASE-T ports,4*10GE SFP+ ports,1*150W AC power)
                Add: bname8031S6730S-H24X6C-A(537567),                      --S6730S-H24X6C-A(24*10GE SFP+ ports,6*100GE QSFP28 ports,1*600W AC power)
                Add: bname8031S1730S-H24T4S-A(537568),                       --S1730S-H24T4S-A(24*10/100/1000BASE-T ports, 4*GE SFP ports, AC 110/220V)
                Add: bname8031S1730S-S24T4X-A(537569),                       --S1730S-S24T4X-A(24*10/100/1000BASE-T ports, 4*10GE SFP+ ports, AC 110/220V)
                Add: bname8031S1730S-H48T4S-A(537570),                       --S1730S-H48T4S-A(48*10/100/1000BASE-T ports, 4*GE SFP ports, AC 110/220V)
                Add: bname8031S5335-L48T4X-A(537571),                          --S5335-L48T4X-A(48*10/100/1000BASE-T ports, 4*10GE SFP+ ports, AC 110/220V)
                Add: bname8031S1730S-S48P4S-A(537572),                       --S1730S-S48P4S-A(48*10/100/1000BASE-T ports,4*GE SFP ports,PoE+,1*1000W PoE AC power)
                Add: bname8031S6730-H48X6C-K(537573),                         --S6730-H48X6C-K (48*10GE SFP+ ports, 6*40GE QSFP28 ports, optional license for upgrade to 6*100GE QSFP28, without power module) for V2R19C!0
                Add: bname8031S6730-H24X6C-K(537574),                         --S6730-H24X6C-K (24*10GE SFP+ ports, 6*100GE QSFP28 ports, without power module) for V2R19C!0
                Add: bname8031S5731-H48P4XC-K(537575),                        --S5731-H48P4XC-K(48*10/100/1000BASE-T ports, 4*10GE SFP+ ports, 1*expansion slot, PoE+, without power module) for V2R19C!0
                Add: bname8031S5731-H24T4XC-K(537576),                        --S5731-H24T4XC-K (24*10/100/1000BASE-T ports, 4*10GE SFP+ ports, 1*expansion slot, without power module) for V2R19C!0
                Add: bname8031S5731-H24P4XC-K(537577),                        --S5731-H24P4XC-K (24*10/100/1000BASE-T ports, 4*10GE SFP+ ports, 1*expansion slot, PoE+, without power module) for V2R19C!0
                Add: bname8031S5732-H24S6Q-K(537578),                          --S5732-H24S6Q-K (20*GE SFP ports,4*10GE SFP+ ports,6*40GE QSFP ports,with Pluggable dual power module) for V2R19C!0
                Add: bname8031S5732-H48S6Q-K(537579),                          --S5732-H48S6Q-K (44*GE SFP ports,4*10GE SFP+ ports,6*40GE QSFP ports,with pluggable dual power module) for V2R19C!0
                Add: subnamePDC1000S12(536798),                 --Function Module,DC PSU,PDC1000S12-D for V2R19C00
                Add: subnamePAC150S12(536799),                   --Function Module, AC PSU, PAC150S12-R, 150W AC Power Module for V2R19C00
                Add: subnamePAC60S12AR(536800),                --Function Module,AC PSU,PAC60S12-AR,60W AC Power Module for V2R19C00
                Add: subnameS7Q02000(536801),                      --subcard S7Q02000 for V2R19C00
                Add: subnameS7M08000(536802),                     --subcard S7M08000 for V2R19C00
                Add: bname8031S5732-H48UM2CC(537580),                          --S5732-H48UM2CC(48 Ethernet 100M/1/2.5/5/10G ports, 4*25GE SFP28 ports + 2*40GE or 2*100GE QSFP28 ports, 1*expansion slot, PoE++, without power module) for V2R19C20
                Add: bname8031S5732-H24UM2CC(537581),                          --S5732-H24UM2CC(24 Ethernet 100M/1/2.5/5/10G ports, 4*25GE SFP28 ports + 2*40GE or 2*100GE QSFP28 ports, 1*expansion slot, PoE++, without power module) for V2R19C20
                Add: bname8031S5332-H24UM2CC(537582),                          --S5332-H24UM2CC (24*100M/1G/2.5G/5G/10G Ethernet ports, 4*25GE SFP28 + 2*40GE ports or 2*100GE QSFP28 ports, 1*expansion slot, PoE++, without power module) for V2R19C20
                Add: bname8031S5732-H48XUM2CC(537583),                          --S5732-H48XUM2CC (24*100M/1G/2.5G/5G/10G Ethernet ports, 24*10GE SFP+ ports, 4*25GE SFP28 + 2*40GE ports or 2*100GE QSFP28 ports, 1*expansion slot, PoE++, without power module) for V2R19C20
                Add: bname8031S5735-S24T4X-I(537584),                              --S5735-S24T4X-I (24*10/100/1000BASE-T ports, 4*10GE SFP+ ports, without power module) for V2R19C20
                Add: bname8031S5735S-S24T4X-A(537599),                              --S5735S-S24T4X-A(24*10/100/1000BASE-T ports, 4*10GE SFP+ ports, 1*60W AC power module) for V2R19C20
                Add: bname8031S5735S-S48T4X-A(537600),                               --S5735S-S48T4X-A(48*10/100/1000BASE-T ports, 4*10GE SFP+ ports, 1*60W AC power module) for V2R19C20
                Add: bname8031S5735S-S24P4X-A(537601),                               --S5735S-S24P4X-A(24*10/100/1000BASE-T ports, 4*10GE SFP+ ports, PoE+, one AC power module) for V2R19C20
                Add: bname8031S5735S-S48P4X-A(537602),                               --S5735S-S48P4X-A(48*10/100/1000BASE-T ports, 4*10GE SFP+ ports, PoE+, one AC power module) for V2R19C20
                Add: bname8031S5735S-L48T4S-MA(537603),                               --S5735S-L48T4S-MA(48*10/100/1000BASE-T ports, 4*GE SFP ports, AC power) for V2R19C20
                Add: bname8031S1730S-S24T4S-MA(537604),                               --S1730S-S24T4S-MA(24*10/100/1000BASE-T ports, 4*GE SFP ports, AC power) for V2R19C20
                Add: bname8031S1730S-S24P4S-MA(537605),                              --S1730S-S24P4S-MA(24*10/100/1000BASE-T ports, 4*GE SFP ports, PoE+, AC power) for V2R19C20
                Add: bname8031S6730-H28Y4C(537585),                                      --S6730-H28Y4C (28*25GE SFP28 ports, 4*100GE QSFP28 ports, without power module) for V2R20C00
                Add: bname8031S6330-H28Y4C(537586),                                      --S6330-H28Y4C (28*25GE SFP28 ports, 4*100GE QSFP28 ports, without power module) for V2R20C00
                Add: bname8031S6730-H24X4Y4C(537587),                                  --S6730-H24X4Y4C (24*10GE SFP+ ports, 4*25GE SFP28 ports, 4*100GE QSFP28 ports, without power module) for V2R20C00
                Add: bname8031S6330-H24X4Y4C(537588),                                  --S6330-H24X4Y4C (24*10GE SFP+ ports, 4*25GE SFP28 ports, 4*100GE QSFP28 ports, without power module) for V2R20C00
                Add: bname8031S6730S-H24X4Y4C-A(537589),                                  --S6730S-H24X4Y4C bundle (24*10GE SFP+ ports, 4*25GE SFP28 ports, 4*100GE QSFP28 ports, 1*300W AC power module) for V2R20C00
                Add: bname8031S6730S-S24X4Y4Q-A(537590),                                  --S6730S-S24X4Y4Q bundle (24*10GE SFP+ ports, 4*25GE SFP28 ports, 4*40GE QSFP+ ports, 1*300W AC power module) for V2R20C00
                Add: bname8031S5732-H24S4Y4Q(537591),                                        --S5732-H24S4Y4Q (24*GE SFP ports, 4*25GE SFP28 ports, 4*40GE QSFP+ ports, without power module) for V2R20C00
                Add: bname8031S5332-H24S4Y4Q(537592),                                        --S5232-H24S4Y4Q (24*GE SFP ports, 4*25GE SFP28 ports, 4*40GE QSFP+ ports, without power module) for V2R20C00
                Add: bname8031S5735-L24T4X-D(537593),                                          --S5735-L24T4X-D (24*10/100/1000BASE-T ports, 4*10GE SFP+ ports, DC power) for V2R20C00
                Add: bname8031S5335-L24T4X-D(537594),                                          --S5335-L24T4X-D (24*10/100/1000BASE-T ports, 4*10GE SFP+ ports, DC power, front access) for V2R20C00
                Add: bname8031S5735-L12T4S-D(537595),                                          --S5735-L12T4S-D (12*10/100/1000BASE-T ports, 4*GE SFP ports, DC power) for V2R20C00
                Add: bname8031S5335-L12T4S-D(537596),                                          --S5335-L12T4S-D (12*10/100/1000BASE-T ports, 4*GE SFP ports, DC power) for V2R20C00
                Add: bname8031S5735-L32ST4X-D(537597),                                        --S5735-L32ST4X-D (24*GE SFP ports, 8*10/100/1000BASE-T ports, 4*10GE SFP+ ports, DC power) for V2R20C00
                Add: bname8031S5335-L32ST4X-D(537598),                                        --S5335-L32ST4X-D (24*GE SFP ports, 8*10/100/1000BASE-T ports, 4*10GE SFP+ ports, DC power, front access) for V2R20C00
                Add: bname8031S6730-H28Y4C-K(537610),                                          --S6730-H28Y4C-K (24*GE SFP ports, 4*25GE SFP28 ports, 4*40GE QSFP+ ports, without power module) for V2R20C00	        
                Add: bname8031S5732-H24UM2C-K(537611),                                       --S5732-H24UM2C-K 2.5G Bundle(24*100M/1G/2.5G Ethernet ports, Optional RTU upgrade to 5/10G, 4*25GE SFP28 + 2*40GE or 2*100GE QSFP28 ports, 1*expansion slot, PoE++, 1*1000W AC power) for V2R20C00	  
                Add: bname8031S5732-H48UM2C-K(537612),                                       --S5732-H48UM2C-K 2.5G Bundle(48*100M/1G/2.5G Ethernet ports, Optional RTU upgrade to 5/10G, 4*25GE SFP28 + 2*40GE or 2*100GE QSFP28 ports, 1*expansion slot, PoE++, 1*1000W AC power) for V2R20C00	              
"

            REVISION    "201910291000Z"
 	 	    DESCRIPTION "V9.72,
                Add: subbname8090DEVGPLI40CQE2(675825),         -- 40-Port 100GBase QSFP28 Integrated Line Process Unit
                Add: subbname8090DEVGPLI72YSE2(675826),         -- 72-Port 25GE(SFP28)/10GE(SFP+)/GE(SFP) Integrated Line Processing Unit
                Add: subbname8090DEVCR5D00C8CF72(225810),       --8-Port Channelized STM-1c POS-SFP Flexible Card(P1A)
                Add: subbname8090DEVCR5D00P8CF70(225811),       --8-Port OC-3c/STM-1c POS-SFP Flexible Card(P1A)
                Add: subbname8090DEVCR5D00CFE170(225812),       --24-Port Channelized E1/T1-DB100 Flexible Card(P1A)
 	 	        "

            REVISION    "201910231000Z"
 	 	    DESCRIPTION "V9.71,
 	 	        Add: bnameH901OTSF(148677),         --  OTDR board of MA5800.
 	 	        "

			REVISION    "201910151000Z"
            DESCRIPTION "V9.70,
                Add:fnameAR111P-S(667899),         -- AR111P-S FRAME
                Add:to
                Add:fnameSRG33X0(667991),          --SRG33X0 FRAME
                Add:bnameAR111p-S(667997),                -- AR111P-S Main Control Unit
                Add:to
                Add:bnameSRG1340-9G(668093),              --SRG1340-9G Main Control Unit
                 "
            REVISION    "201910101000Z"
            DESCRIPTION "V9.69,
                 Add: subbname8090DEVCR5DE8VE4N70(225782),      --8-Port 50G/4-Port 100GBase-QSFP28 Flexible Card (P1T).
                 "
            REVISION    "201909251000Z"
            DESCRIPTION "V9.68,
                 Add: bnameH903CGHD(148678),         --  8*XG/G combo board of MA5800.
                 Add: bnameH903CSHD(148679),         --  8*XGS/G combo board of MA5800.
                 Add: bnameH902OXEG(148680),         --  24*10GE board of MA5800.
                 Add: bnameH903CGUD(148681),         --  8*XGS/G combo board of MA5800.
                 Add: bnameH902FLEF(148682),         --  16*flex-PON board of MA5800.
                 Add: bnameH902XGLF(148683),         --  16*XG GPON board of MA5800.
                 "

REVISION    "201909200000Z"
		DESCRIPTION "V9.67,
			Add:fnameUSG12004-AC-CHAS     (16715907),
			Add:fnameUSG12004-AC-CHAS-OVS (16715908),
			Add:fnameUSG12004-DC-CHAS     (16715909),
			Add:fnameUSG12004-DC-CHAS-OVS (16715910),
			Add:fnameUSG12008-AC-CHAS     (16715911),
			Add:fnameUSG12008-AC-CHAS-OVS (16715912),
			Add:fnameUSG12008-DC-CHAS     (16715913),
			Add:fnameUSG12008-DC-CHAS-OVS (16715914),
			Add:fnameE9000E-X4-AC-CHAS    (16715915),
			Add:fnameE9000E-X4-AC-CHAS-OVS(16715916),
			Add:fnameE9000E-X4-DC-CHAS    (16715917),
			Add:fnameE9000E-X4-DC-CHAS-OVS(16715918),
			Add:fnameE9000E-X8-AC-CHAS    (16715919),
			Add:fnameE9000E-X8-AC-CHAS-OVS(16715920),
			Add:fnameE9000E-X8-DC-CHAS    (16715921),
			Add:fnameE9000E-X8-DC-CHAS-OVS(16715922),
			Add:fnameAntiDDoS12004-AC-CHAS(16715923),
			Add:fnameAntiDDoS12004-DC-CHAS(16715924),
			Add:fnameAntiDDoS12008-AC-CHAS(16715925),
			Add:fnameAntiDDoS12008-DC-CHAS(16715926),
			Add:bnameLPUA-18CQ      (16748608),
			Add:bnameE9KE-LPUA-18CQ (16748609),
			Add:bnameLPUA-48XS      (16748610),
			Add:bnameE9KE-LPUA-48XS (16748611),
			Add:bnameLPUA-4CQ-24XS  (16748612),
			Add:bnameE-LPUA-4CQ-24XS(16748613),
			Add:bnameLPUA-2CQ-24XS  (16748614),
			Add:bnameE-LPUA-2CQ-24XS(16748615),
			Add:bnameMPUA-USG-X4X8  (16748616),
			Add:bnameMPUA-E9KE-X4X8 (16748617),
			Add:bnameSFUA-USG12008  (16748618),
			Add:bnameSFUA-E9KE-X8   (16748619),
			Add:bnameSPUA-USG-01    (16748620),
			Add:bnameSPUA-USG-02    (16748621),
			Add:bnameSPUA-USG-TP-01 (16748622),
			Add:bnameSPUA-USG-TP-02 (16748623),
			Add:bnameSPUA-E9KE-01   (16748624),
			Add:bnameSPUA-E9KE-02   (16748625),
			Add:bnameSPUA-E9KE-TP-01(16748626),
			Add:bnameSPUA-E9KE-TP-02(16748639),
			Add:bnameSPUA-ADS-01    (16748640),
			Add:bnameSPUA-ADS-02    (16748641),
			Add: subbnameSPCA-ADS-01    (16728127),
			Add: subbnameSPCA-ADS-02    (16728128),
			Add: subbnameSPCA-USG-01    (16728129),
			Add: subbnameSPCA-USG-02    (16728130),
			Add: subbnameSPCA-USG-TP-01 (16728131),
			Add: subbnameSPCA-USG-TP-02 (16728132),
			Add: subbnameSPCA-E9KE-01   (16728133),
			Add: subbnameSPCA-E9KE-02   (16728134),
			Add: subbnameSPCA-E9KE-TP-01(16728135),
			Add: subbnameSPCA-E9KE-TP-02(16728136),
			  "
       REVISION    "201909180000Z"
        DESCRIPTION "V9.66,
                Add: bnameH828XPUB(156095),  -- Master board of MA582xS/MA582xH
                Add: bnameH822ASMC(156096),  --MA5822S 24POTS
                Add: bnameH822ASNC(156097),  --MA5822S 16POTS
                Add: bnameH822ASLC(156098),  --MA5822S 8POTS
                Add: bnameH838VPDE(156100),  --MA5818 VPborad
                Add: fnameMA5821HH821Mabc(561669), -- Virtual frame H821MABC of MA5821H device
                Add: fnameMA5821SH821Mabc(561670), -- Virtual frame H821MABC of MA5821S device
                Add: fnameMA5822HH821Mabc(561671), -- Virtual frame H821MABC of MA5822H device
                Add: fnameMA5822SH821Mabc(561672), -- Virtual frame H821MABC of MA5821S device
                Add: fnameMA5821SPOEH821Mabc(561673), -- Virtual frame H821MABC of MA5821S-POE device
                Add: fnameP815EH821Mabc(561674),   -- Virtual frame H821MABC of P815E device
                Add: fnameP805EH821Mabc(561675),   -- Virtual frame H821MABC of P805E device
                  "
       REVISION    "201909120000Z"
        DESCRIPTION "V9.65,
                Add: virent8090DEVCX6D00EKGF10(676924),
                Add: virent8090DEVCX6DE4VE2N10(676925),
                Add: virent8090DEVCX6D00EFXF10(676926),
                Add: virent8090DEVCX6D00E4NB10(676927),
                Add: virent8090DEVCX6D00EKXF10(676928),
                Add: virent8090DEVCX6DLPUFT010(676929),
                Add: virent8090DEVCX6DE4VE2N11(676930),
                Add: virent8090DEVCX6D00E4NB11(676931),
                Add: virent8090DEVCR5DLEXEEG70(676932),
                Add: virent8090DEVCX6DSFUIT21G(676935),
                Add: virent8090DEVCX6D0SRUAG12(676936),
                Add: virent8090DEVCX6DSFUIT21F(676937),
                Add: virent8090DEVCX6D0E4VBF10(676938),
                Add: virent8090DEVCX6D0EFXFA10(676939),
                Add: virent8090DEVCX6D0E2NBF11(676940),
                Add: virent8090DEVCR2DNSP24010(562079),
                  "
       REVISION    "201909110000Z"
        DESCRIPTION "V9.64,
                Add:subbname8090DEVCX62LEXFC00(225760),       --20-Port 10GBase LAN/WAN-SFP+ Integrated Integrated Service Unit
                  "
        REVISION    "201909110000Z"
        DESCRIPTION "V9.63,
                Add:fnameCE682048S6CQ(688197),           -- CloudEngine 6800, CE6820-48S6CQ, CE6820-48S6CQ switch
		        Add:bnameCE682048S6CQ(688347),           -- CloudEngine 6800, CE6820-48S6CQ, CE6820-48S6CQ switch
                  "
		REVISION    "201909050000Z"
        DESCRIPTION "V9.62,
                Add: bnameH803X2CK(146080),         --  10GE synchronized Ethernet interface board.
                  "
        REVISION    "201909050000Z"

         DESCRIPTION "V9.61,
                Add:virent8090DEVCR5D0MPUB661(561806),         -- V8R11C10 for CR5D0MPUB661(SBOM) NE5000E Main Processing Unit B6
                  "
        REVISION    "201909040000Z"

        DESCRIPTION "V9.60,
                Add:virentANRD00CXPA00(225336),         --ATN 950D,ANR1CXPA00,System Control, Cross-connect and Multi-protocol Process Unit with 160G
                Add:virentANRD00CXPA01(225337),         --ATN 950D,ANR1CXPA10,System Control, Cross-connect and Multi-protocol Process Unit with 160G
                Add:virentANRD01CXPA00(225338),         --ATN 950D,ANR2CXPA0,System Control, Cross-connect and Multi-protocol Process Unit with 400G
                Add:virentANRD01CXPB00(225339),         --ATN 950D,ANR2CXPB0,System Control, Cross-connect and Multi-protocol Process Unit with 800G
                  "
        REVISION    "201909020000Z"

        DESCRIPTION "V9.59,
                Add:bnameLST3G48TX5S1(659728),       --48-port 10/100/1000BASE-T interface card (X5S,RJ45) for v2r19c00 S9300x
                Add:bnameLST3G48TX5E1(659729),       --48-port 10/100/1000BASE-T interface card (X5E,RJ45) for v2r19c99 S9300x
                Add:bnameLST7G48TX5S1(700517),            --48-port 10/100/1000BASE-T interface card (X5S,RJ45) for v2r19c00 12700E
                Add:bnameLST7G48TX5E1(700518),            --48-port 10/100/1000BASE-T interface card (X5E,RJ45) for v2r19c00 12700E
                  "
        REVISION    "201908280000Z"

        DESCRIPTION "V9.58,
             Add:  subbnameCARDNetEngine8000M1A(333116),    --ATN910C-G virtual card,16*10GE(o), 12*GE /GE/FE(o),4*GE/FE(e)
             Add:  subbname8090DEVCX6DE8VE4N10(225759),      --8-Port 50G/4-Port 100GBase-QSFP28 Flexible Card (P1T)
             Add:  subbname8090DEVCR5D000DE1C1(225775),      --16-Port E1 Physical Interface Card(PIC,75ohm/120ohm)
             Add:  subbname8090DEVCR5D00P4CFC1(225776),      --4-Port OC-3c/STM-1c POS-SFP Flexible Interface Card(FIC)
             Add:  subbname8090DEVCR5D00C4CFC1(225777),      --4-Port Channelized STM-1c POS-SFP Physical Interface Card(PIC)
             Add:  subbname8090DEVANND16E17500(225778),      --16 Channels E1 Interface Board
             Add:  subbname8090DEVANND00CQ1B00(225779),      --4 Channels Channelized OC-3c/STM-1c POS Optical Interface Board
             Add:  subbname8090DEVCR58EPYFA00(225780),       --60-Port 25GE-SFP28/10GE-SFP+ LAN/WAN MACSec Integrated Line Process Unit CM
             Add:  subbname8090DEVCR2D00E2NB00(225781),      --2-Port 100G/50G QSFP28 MACsec Interface Card

        "
        REVISION    "201908260000Z"

		DESCRIPTION "V9.57,
              Add:  fnameAirEngine9700D-M(692338), --WLAN R19C10 new AP ENUM_
              Add:  bnameAirEngine9700D-M(692338), --WLAN R19C10 new AP ENUM_
                 "
        REVISION    "201908230000Z"

        DESCRIPTION "V9.56,
            Add:  virent8090DEVME0DBSUFT072(598601),     -- V8R12C20 for ME0DBSUFT072(SBOM) Finished Board Unit,ME60,CR57LPUF1TQ03,Flexible Card Broadband Service Unit(BSUF-1T,2 sub-slots)
            Add:  virent8090DEVME0DMSUFT073(598602),     -- V8R12C20 for ME0DMSUFT073(SBOM) Finished Board Unit,ME60,CR57LPUF1TQ04,Flexible Card Multi Service Unit(MSUF-1T,2 sub-slots)
            Add:  virent8090DEVME0DBSUFT074(598603),     -- V8R12C20 for ME0DBSUFT074(SBOM) Finished Board Unit,ME60,CR57LPUF1TQ05,Flexible Card Broadband Service Unit(BSUF-1TA,2 sub-slots)
            Add:  virent8090DEVME0DMSUFT075(598604),     -- V8R12C20 for ME0DMSUFT075(SBOM) Finished Board Unit,ME60,CR57LPUF1TQ06,Flexible Card Multi Service Unit(MSUF-1TA,2 sub-slots)
            Add:  fnameATNDEV950D(225617),               --ATN950D chassis
            Add:  fnameATNDEV910D(225618),               --ATN910D chassis
        "
        REVISION    "201908210000Z"

        DESCRIPTION "V9.55,
             Add: subbname8090DEVGPLI40CQES1(675822),         -- 40-Port 100GBase QSFP28 Integrated Line Process Unit
             Add: subbname8090DEVGPLI72YSES1(675823),          -- 72-Port 25GE(SFP28)/10GE(SFP+)/GE(SFP) Integrated Line Processing Unit
             Add: subbname8090DEVGPLI8KQ8CQE1(675824),    -- 1x10GBase LAN/WAN-SFP+ 8x100/1000Base-X-SFP interface card
                "
        REVISION    "201908130000Z"

		DESCRIPTION "V9.54,
              Add: bnamePTN7900TPA1EX24S(229552), --TPA1EX24S, 24-port 10 Gigabit Ethernet Switching Processing Board
                 "
        REVISION    "201908050000Z"

        DESCRIPTION "V9.53,
              Add:  fnameAirEngine9700-M(692337), --WLAN R19C00 new AC ENUM_
              Add:  bnameAirEngine9700-M(692337), --WLAN R19C00 new AC ENUM_
                 "
        REVISION    "201908020000Z"

        DESCRIPTION "V9.52,
             Add: subbname8090DEVCR57E2NCF1(537493),         -- 2-Port 100GBase-CFP2 Fixed Card A
             Add: subbname8090DEVCX6D000IT372(564517),       -- 4*T3 interface card
             Add: subbname8090DEVCX6D00L1XE8GF70(564518),    -- 1x10GBase LAN/WAN-SFP+ 8x100/1000Base-X-SFP interface card
             Add: subbname8090DEVCR56L5XFB1(688346),         -- 5-Port 10GBase LAN/WAN SFP+ Flexible Card(CP1T,Occupy 1 sub-slot)
             Add: subbname8090DEVCR56L5XFK0(688347),         -- 5-Port 10GBase LAN/WAN SFP+ Flexible Card(CP1T,Occupy 1 sub-slot)
             Add: subbname8090DEVCR56E3NBA0(688348),         -- 3-Port 100GBase QSFP28 Flexible Card(CP1T,Occupy 1 sub-slot)
                "
        REVISION    "201907290000Z"

        DESCRIPTION "V9.51,
              Add:  virent8090DEVCR9D00EPYF8P(688360),
              Add:  virent8090DEVCX6DISUFT011(688316),
              Add:  virent8090DEVCR5D0E4NBA72(676921),
              Add:  virent8090DEVCR5DNKFEDY72(676922),
              Add:  virent8090DEVCR5D0EEXFA72(676923),
              Add:  virentDEVCR8DIPU480C1(800002),
              Add:  virentDEVCR8DIPU480C2(800003),
              Add:  virentDEVTNRDIPU480C1(229555),
              Add:  fnameNETENGINE-8000-M8-AC(538022),
              Add:  fnamePTN6900-2-M8C-AC(538023),
              Modify:  fnameATNDEV910C-G-DC(225613),
              Add:  fnameATNDEV910C-G-AC(225616),
              Add:  fnameNETENGINE-8000-M1A-AC(688341),
              Add:  fnameNETENGINE-8000-M1A-DC(688342),
              Add:  virentANGMHSTG0200(225614),
              Add:  virent600DEVCR8PM1ABASC5(688336),
              Add:  virent600DEVCR8PM1ABASC4(688337),
              Add:  virent600DEVCR8PM1ABASC0(688338),
              Add:  virent600DEVCR8PM1ABASC1(688339),
              Add:  virent600DEVCR8PM1ABASC2(688340),
              Add:  virent600DEVCR8PM1ABASC3(688345),
                "
        REVISION    "201907260000Z"

        DESCRIPTION "V9.50,
              Add: bnameH902XSHFE(148672),        --  16*10G XGS-PON board of EA5800.
              Add: bnameH902EPHFE(148673),        --  16 port EPON board of EA5800.
              Add: bnameH902EPHF(148674),         --  16 port EPON board of MA5800.
              Add: bnameH901MPSAE(148676),        --  control board of EA5800-X2.
                "
        REVISION    "201907191000Z"

        DESCRIPTION "V9.49,
              Add:  fnameNETENGINE-8000-M14-AC(688339),
              Add:  fnameNETENGINE-8000-M14-DC(688340),
              Add:  virent600DEVCR8D0IPU2TC1(688341),
              Add:  virent600DEVCR8D0IPU2TC2(688342),
              Add:  virent600DEVCR8DIPU1T2C3(688343),
              Add:  virent600DEVCR8DIPU1T2C4(688344),
                 "
        REVISION    "201907150000Z"

        DESCRIPTION "V9.48,
              Add:  fnameNETENGINE-8000-F1A-8H20Q(688338),
              Add:  fnameNETENGINE-8000-F1A-8H20Q-AC(688336),
              Add:  fnameNETENGINE-8000-F1A-8H20Q-DC(688337),
              Add:  virent600DEVCR8B0BKP03C0(688332),
              Add:  virent600DEVCR8B0BKP03C1(688333),
              Add:  virent600DEVCR8B0BKP03C2(688334),
              Add:  virent600DEVCR8B0BKP03C3(688335),
              Add:  virent8090DEVCR5D0SRUAC73(676900),
              Add:  virent8090DEVCR5D0SRUAC72(676901),
              Add:  virent8090DEVCX6D0SRUAG11(676902),
              Add:  virent8090DEVCR5DSFUIT070(676903),
              Add:  virent8090DEVCR5DSFUIT071(676904),
              Add:  virent8090DEVCX6DSFUIT070(676907),
              Add:  virent8090DEVTNRDSFUIT070(676908),
              Add:  virent8090DEVCX6DSFUIT21D(676909),
              Add:  virent8090DEVCR5DSFUIT072(676910),
              Add:  virent8090DEVCR5DSFUIT073(676911),
              Add:  virent8090DEVCX6DSFUIT071(676914),
              Add:  virent8090DEVTNRDSFUIT071(676915),
              Add:  virent8090DEVCX6DSFUIT21E(676916),
              Add:  virent8090DEVCR5D0SRUAC74(676917),
              Add:  virent8090DEVCR5D0SRUAC75(676918),
              Add:  virent8090DEVCX6D0SRUAC72(676919),
              Add:  virent8090DEVTNRD0SRUAC72(676920),
                 "
        REVISION    "201907110000Z"

		DESCRIPTION "V9.47,
					Add:  bname(16744473~16744492),
					Add:  bnameFW-LPUF-120SP(16748592),
					Add:  bnameFW-LPUF-240SP(16748593),
					Add:  bnameADS-SPUC-BSP(16748603),
					Add:  bnameADS-SPUD-BSP(16748604),
					Add:  bnameE8KE-X3-MPUSP(16748605),
					Add:  subname(16728094~16728126),
					Add:  subnameFW-6X10G-SFP+SP(16748594),
					Add:  subnameFW-1X100G-CFPSP(16748595),
					Add:  subnameFW-12X10G-SFP+SP(16748596),
					Add:  subnameSPC-APPSEC-FW(16748597),
					Add:  subnameADS-SPC-20-00SP(16748598),
					Add:  subnameADS-SPC-40-00SP(16748599),
					Add:  subnameADS-SPC-80-00SP(16748600),
					Add:  subnameADS-SPC-40-01SP(16748601),
					Add:  subnameADS-SPC-80-01SP(16748602),
					Add:  subnameE8KE-X-6X10G-SFP+SP(16748608),
					Add:  subnameE8KE-X-1X100G-CFPSP(16748609),
					Add:  subnameE8KE-X-12X10G-SFP(16748610),
					Add:  subnameSPC-APPSEC-E8KESP(16748611),
					"
		REVISION    "201907080000Z"



        DESCRIPTION "V9.46,
              Add: bnameH903MPLAE(148670),        --  control board of EA5800.
              Add: bnameH902OGHK(148671),         --  48 P2P board of MA5800.
              Add: bnameH902PISB(148675),         --  AC Power board of MA5800-X2.
                 "

		REVISION    "201907030000Z"

        DESCRIPTION "V9.45,
	    Modify:  virent8090DEVCR5D0SFUT2D1(561796),
	    Modify:  virent8090DEVCR5D0SFUT2D2(561797),
	    Modify:  virent8090DEVCR5D00EENBD0(561798),
                       Modify:  virent8090DEVCR5D00EENBD1(561799),
                       Delete:  virent8090DEVCR5D00EENBCP(561800),
                       Delete:  virent8090DEVCR5D00EENBCQ(561801),
                       Modify:  virent8090DEVCR5D00EPXFD0(561802),
                       Modify:  virent8090DEVCR5D00EPXFD1(561803),
                       Delete:  virent8090DEVCR5D00EPXFCP(561804),
                       Delete:  virent8090DEVCR5D00EPXFCQ(561805),
                       Add:  virent8090DEVCR9D0MPUR180(561790),
                       Add:  virent8090DEVCR5D0MPUQ1D1(567013),
                       Add:  virent8090DEVCR5D0MPUQ1D0(567014),
                       Add:  virent8090DEVCR9D0MPUQ180(561789),
                "

        REVISION    "201906250000Z"
        DESCRIPTION "V9.44,
		      Add: bnamePTN7900TPE1CXPB(229549), --TPE1CXPB,System Control Communication and Switch Fabric Process Unit,1*1
              Add: bnamePTN7900TPE1XCSB(229550), --TPE1XCSB,Switch Fabric Unit,1*1
              Add: virentPTN7900TPE1VXCSB(229547), --TPE1VXCSB,Switch Fabric Unit,1*1
              Add: virentPTN7900TPF1VXCSB(229548), --TPF1VXCSB,Switch Fabric Unit,1*1
             "

       REVISION    "201906240000Z"
       DESCRIPTION "V9.43,
              Add: fnameNETENGINE-8000-M8-DC(537997),       --NETENGINE-8000-M8-DC (fnameNETENGINE-8000-M8-DC)
              Add: fnamePTN6900-2-M8C-DC(537998),           --PTN6900-2-M8C-DC(fnamePTN6900-2-M8C-DC)
              Add: bnameANND00CXPA00(229483),               --ATN 980C,ANN1CXPA00,System Control,Cross-connect and Multi-protocol Process Unit with 800G
              Add: bnameANND00CXPA01(229484),               --ATN 980C,ANN1CXPA10,System Control,Cross-connect and Multi-protocol Process Unit with 320G
              Add: bnameANND00CXPA02(229485),               --ATN 980C,ANN1CXPA20,System Control,Cross-connect and Multi-protocol Process Unit with 480G
              Add: bnameANND00CXPA03(229541),               --ATN 980C,ANN1CXPA30
              Add: virentDEVCR8DIPU1T2C1(800000),           -- V8R11C10 for DEVCR8DIPU1T2C1(SBOM) Integrated Network Processing Unit (IPU-1T2)
              Add: virentDEVCR8DIPU1T2C2(800001) ,          -- V8R11C10 for DEVCR8DIPU1T2C2(SBOM) Integrated Network Processing Unit (IPU-1T2)
              Add: virentPTN6900DEVTNRDIPU1T2C1(229486),    -- V8R11C10 for PTN6900DEVTNRDIPU1T2C1(SBOM) Integrated Network Processing Unit (IPU-1T2)
              Add: fnameATNDEV980C-AC(225614),         --980C  chassis
              Add: fnameATNDEV980C-DC(225615),         --980C  chassis
             "


       REVISION    "201906210000Z"
       DESCRIPTION "V9.42,
               Add:  bnameLST7X48SX6S0(700510),             --48-port 10GE SFP+ interface card (X6S,SFP+) for v2r19c00 12700E
               Add:  bnameLST7X48SX6E0(700511),             --48-port 10GE SFP+ interface card (X6E,SFP+) for v2r19c00 12700E
               Add:  bnameLST7SFUHX100(700512),            --S12700E switch fabric unit H(X1) for v2r19c00 12700E
               Add:  bnameLST7SFUMX100(700513),            --S12700E switch fabric unit M(X1) for v2r19c00 12700E
               Add:  bnameLST7C24HX6S0(700514),            --24-port 100GE QSFP28 interface card (X6S,QSFP28) for v2r19c00 12700E
               Add:  bnameLST7C06HX6S0(700515),            --6-port 100GE QSFP28 interface card (X6S,QSFP28) for v2r19c00 12700E
               Add:  bnameLST7C06HX6E0(700516),            --6-port 100GE QSFP28 interface card (X6E,QSFP28) for v2r19c00 12700E
               Add:  fnameET1BS12712E1(700426),               --S12700E-12 assembly chassis for V2R19C00
               Add:  bnameLST3X04BX6E0(659719),             --4-port 10GE SFP+ interface and 44-port GE SFP interface card (X6E,SFP+) for v2r19c00
               Add:  bnameLST3X24SX6E0(659720),             --24-port 10GE SFP+ interface card (X6E,SFP+)  for v2r19c00
               Add:  bnameLST3X08BX6E0(659721),             --8-port 10GE SFP+ interface and 24-port GE SFP interface card (X6E,SFP+) for v2r19c00
               Add:  bnameLST3X16BX6E0(659722),             --16-port 10GE SFP+ interface and 24-port GE SFP interface card (X6E,SFP+)  for v2r19c00
               Add:  bnameLST3X36SX6E0(659723),             --36-port 10GE SFP+ interface card (X6E,SFP+)  for v2r19c00
               Add:  bnameLST3C04HX6E0(659724),             --4-port 100GE QSFP28 interface card (X6E,QSFP28)  for v2r19c00
               Add:  bnameLST3SFUHX100(659725),            --S12700E switch fabric unit H(X1)  for v2r19c00
               Add:  bnameLST3SFUMX100(659726),            --S12700E switch fabric unit M(X1) for v2r19c00
               Add:  bnameLST3C24HX6S0(659727),             --24-port 100GE QSFP28 interface card (X6S,QSFP28) for v2r19c00
               Add:  fnameLE3BSS9312X1(659480),              --S9300X-12 assembly chassis
              Add:   fname8031S5731-S24T4X(537307),                  --S5731-S24T4X(24*10/100/1000BASE-T ports,4*10GE SFP+ ports,without power module) for v2r19c00
              Add:   fname8031S5731S-S24T4X-A(537308),            --S5731S-S24T4X-A(24*10/100/1000BASE-T ports,4*10GE SFP+ ports,1*600W AC power) for v2r19c00
              Add:   fname8031S5331-H24T4XC(537309),               --S5331-H24T4XC(24*10/100/1000BASE-T ports,4*10GE SFP+ ports,1*expansion slot,without power module)  for v2r19c00
              Add:   fname8031S5731-S24P4X(537310),                 --S5731-S24P4X(24*10/100/1000BASE-T ports,4*10GE SFP+ ports,1*expansion slot,PoE+, without power module)  for v2r19c00
              Add:   fname8031S5731S-S24P4X-A(537311),           --S5731S-S24P4X-AA (24*10/100/1000BASE-T ports,4*10GE SFP+ ports,1*expansion slot,PoE+,1*1000W PoE AC power) for v2r19c00
              Add:   fname8031S5331-H24P4XC(537312),              --S5331-H24P4XC(24*10/100/1000BASE-T ports,4*10GE SFP+ ports,1*expansion slot,PoE+,without power module)  for v2r19c00
              Add:   fname8031S5731-S48T4X(537313),                 --S5731-S48T4X(48*10/100/1000BASE-T ports,4*10GE SFP+ ports,1*expansion slot,without power module)  for v2r19c00
              Add:   fname8031S5731S-S48T4X-A(537314),           --S5731S-S48T4X-A(48*10/100/1000BASE-T ports,4*10GE SFP+ ports,1*expansion slot,1*600W AC power)   for v2r19c00
              Add:   fname8031S5331-H48T4XC(537315),              --S5331-H48T4XC(48*10/100/1000BASE-T ports,4*10GE SFP+ ports,1*expansion slot,without power module)  for v2r19c00
              Add:   fname8031S5731-S48P4X(537316),                 --S5731-S48P4X (48*10/100/1000BASE-T ports,4*10GE SFP+ ports,1*expansion slot,PoE+,without power module)
              Add:   fname8031S5731S-S48P4X-A(537317),           --S5731S-S48P4X-A(48*10/100/1000BASE-T ports,4*10GE SFP+ ports,1*expansion slot,PoE+,1*1000W PoE AC power)
              Add:   fname8031S5331-H48P4XC(537318),              --S5331-H48P4XC(48*10/100/1000BASE-T ports,4*10GE SFP+ ports,1*expansion slot,PoE+,without power module)
              Add:   fname8031S5732-H24S6Q(537319),                --5732-H24S6Q (20*GE SFP ports,4*10GE SFP+ ports,6*40GE QSFP ports,without power module)
              Add:   fname8031S5332-H24S6Q(537320),                --S5332-H24S6Q (20*GE SFP ports,4*10GE SFP+ ports,6*40GE QSFP ports,without power module)
              Add:   fname8031S5732-H48S6Q(537321),                --S5732-H48S6Q (44*GE SFP ports,4*10GE SFP+ ports,6*40GE QSFP ports,without power module)
              Add:   fname8031S5332-H48S6Q(537322),                --S5332-H48S6Q (44*GE SFP ports,4*10GE SFP+ ports,6*40GE QSFP ports,without power module)
              Add:   fname8031S6730-S24X6Q(537323),                --S6730-S24X6Q (24*10GE SFP+ ports,6*40GE QSFP ports,without power module)
              Add:   fname8031S6730S-S24X6Q-A(537324),          --S6730S-S24X6Q-A (24*10GE SFP+ ports,6*40GE QSFP ports,without power module)
              Add:   fname8031S5731S-H24T4XC-A(537325),       --S5731S-H24T4XC-A (24*10/100/1000BASE-T ports,4*10GE SFP+ ports,1*expansion slot,1*600W AC power)
              Add:   fname8031S5731S-H48T4XC-A(537326),       --S5731S-H48T4XC-A (48*10/100/1000BASE-T ports,4*10GE SFP+ ports,1*expansion slot,1*600W AC power)
              Add:   bname8031S5731-S24T4X(537491),                      --S5731-S24T4X(24*10/100/1000BASE-T ports,4*10GE SFP+ ports,without power module)
              Add:   bname8031S5731S-S24T4X-A(537492), 	--S5731S-S24T4X-A(24*10/100/1000BASE-T ports,4*10GE SFP+ ports,1*600W AC power)
              Add:   bname8031S5331-H24T4XC(537493),   	--S5331-H24T4XC(24*10/100/1000BASE-T ports,4*10GE SFP+ ports,1*expansion slot,without power module)
              Add:   bname8031S5731-S24P4X(537494),    	--S5731-S24P4X(24*10/100/1000BASE-T ports,4*10GE SFP+ ports,1*expansion slot,PoE+, without power module)
              Add:   bname8031S5731S-S24P4X-A(537495), 	--S5731S-S24P4X-AA (24*10/100/1000BASE-T ports,4*10GE SFP+ ports,1*expansion slot,PoE+,1*1000W PoE AC power)
              Add:   bname8031S5331-H24P4XC(537496),   	--S5331-H24P4XC(24*10/100/1000BASE-T ports,4*10GE SFP+ ports,1*expansion slot,PoE+,without power module)
              Add:   bname8031S5731-S48T4X(537497),    	--S5731-S48T4X(48*10/100/1000BASE-T ports,4*10GE SFP+ ports,1*expansion slot,without power module)
              Add:   bname8031S5731S-S48T4X-A(537498), 	--S5731S-S48T4X-A(48*10/100/1000BASE-T ports,4*10GE SFP+ ports,1*expansion slot,1*600W AC power)
              Add:   bname8031S5331-H48T4XC(537499),   	--S5331-H48T4XC(48*10/100/1000BASE-T ports,4*10GE SFP+ ports,1*expansion slot,without power module)
              Add:   bname8031S5731-S48P4X(537500),    	--S5731-S48P4X (48*10/100/1000BASE-T ports,4*10GE SFP+ ports,1*expansion slot,PoE+,without power module)
              Add:   bname8031S5731S-S48P4X-A(537501), 	--S5731S-S48P4X-A(48*10/100/1000BASE-T ports,4*10GE SFP+ ports,1*expansion slot,PoE+,1*1000W PoE AC power)
              Add:   bname8031S5331-H48P4XC(537502),   	--S5331-H48P4XC(48*10/100/1000BASE-T ports,4*10GE SFP+ ports,1*expansion slot,PoE+,without power module)
              Add:   bname8031S5732-H24S6Q(537503),    	--S5732-H24S6Q (20*GE SFP ports,4*10GE SFP+ ports,6*40GE QSFP ports,without power module)
              Add:   bname8031S5332-H24S6Q(537504),    	--S5332-H24S6Q (20*GE SFP ports,4*10GE SFP+ ports,6*40GE QSFP ports,without power module)
              Add:   bname8031S5732-H48S6Q(537505),    	--S5732-H48S6Q (44*GE SFP ports,4*10GE SFP+ ports,6*40GE QSFP ports,without power module)
              Add:   bname8031S5332-H48S6Q(537506),    	--S5332-H48S6Q (44*GE SFP ports,4*10GE SFP+ ports,6*40GE QSFP ports,without power module)
              Add:   bname8031S6730-S24X6Q(537507),    	--S6730-S24X6Q (24*10GE SFP+ ports,6*40GE QSFP ports,without power module)
              Add:   bname8031S6730S-S24X6Q-A(537508), 	--S6730S-S24X6Q-A (24*10GE SFP+ ports,6*40GE QSFP ports,without power module)
              Add:   bname8031S5731S-H24T4XC-A(537509),	--S5731S-H24T4XC-A (24*10/100/1000BASE-T ports,4*10GE SFP+ ports,1*expansion slot,1*600W AC power)
              Add:   bname8031S5731S-H48T4XC-A(537510),	--S5731S-H48T4XC-A (48*10/100/1000BASE-T ports,4*10GE SFP+ ports,1*expansion slot,1*600W AC power)
             "

       REVISION    "201906200000Z"
       DESCRIPTION "V9.41,
        Add:  virent8090DEVCR5DLPUFT071(688314),     -- V8R12C20 for CR5DLPUFT071(SBOM) Finished Board Unit,NetEngine40E,CR57LPUF1TQ00,Flexible Card Line Processing Unit(LPUF-1T)
        Add:  virent8090DEVCR5DLPUFT072(688315),     -- V8R12C20 for CR5DLPUFT072(SBOM) Finished Board Unit,NetEngine40E,CR57LPUF1TQ01,Flexible Card Line Processing Unit E(LPUF-1TA)
        "
              REVISION    "201906190000Z"
       DESCRIPTION "V9.40,
	    Add:  virent8090DEVCR5D0SFUT2C1(561796),    -- V8R11C10 for CR5D0SFUT2C1(SBOM) NE5000E-20 2T CLC Switch Fabric Unit S for Single Chassis(SFU-2T-S)
	    Add:  virent8090DEVCR5D0SFUT2C2(561797),    -- V8R11C10 for CR5D0SFUT2C2(SBOM) NE5000E-20 2T CLC Switch Fabric Unit S for Single Chassis(SFU-2T-S)
	    Add:  virent8090DEVCR5D00EENBC0(561798),    -- V8R11C10 for CR5D00EENBC0(SBOM) 20-Port 100GE-QSFP28 Integrated Line Process Unit(NE5000E LPUI-2T)
                       Add:  virent8090DEVCR5D00EENBC1(561799),    -- V8R11C10 for CR5D00EENBC1(SBOM) 20-Port 100GE-QSFP28 Integrated Line Process Unit(NE5000E LPUI-2T)
                       Add:  virent8090DEVCR5D00EENBCP(561800),    -- V8R11C10 for CR5D00EENBCP(SBOM) 20-Port 100GE-QSFP28 Integrated Line Process Unit(NE5000E LPUI-2T-CM)
                       Add:  virent8090DEVCR5D00EENBCQ(561801),    -- V8R11C10 for CR5D00EENBCQ(SBOM) 20-Port 100GE-QSFP28 Integrated Line Process Unit(NE5000E LPUI-2T-CM)
                       Add:  virent8090DEVCR5D00EPXFC0(561802),    -- V8R11C10 for CR5D00EPXFC0(SBOM) 60-Port 10GBase LAN/WAN-SFP+  Integrated Line Process Unit(NE5000E LPUI-2T)
                       Add:  virent8090DEVCR5D00EPXFC1(561803),    -- V8R11C10 for CR5D00EPXFC1(SBOM) 60-Port 10GBase LAN/WAN-SFP+  Integrated Line Process Unit(NE5000E LPUI-2T)
                       Add:  virent8090DEVCR5D00EPXFCP(561804),    -- V8R11C10 for CR5D00EPXFCP(SBOM) 60-Port 10GBase LAN/WAN-SFP+  Integrated Line Process Unit(NE5000E LPUI-2T-CM)
                       Add:  virent8090DEVCR5D00EPXFCQ(561805),    -- V8R11C10 for CR5D00EPXFCQ(SBOM) 60-Port 10GBase LAN/WAN-SFP+  Integrated Line Process Unit(NE5000E LPUI-2T-CM)
                "
        REVISION    "201906100000Z"
       DESCRIPTION "V9.39,
	    Add:  virent8090DEVCR9D0MPUR180(561790),   -- v8r12c00 NE9000-8 Main Processing Unit R1(MPUR1)
	    Add:  virent8090DEVCR5D0MPUQ1D1(561791),   -- v8r12c00 NE5000E-20 Main Processing Unit Q1(MPUQ1)
	    Add: virent8090DEVCR5D0MPUQ1D0(561792),   -- v8r12c00 NE5000E-20 Main Processing Unit Q1(MPUQ1)
                        Add:  virent8090DEVCR9D0MPUQ180(561789),   -- v8r12c00 NE9000-20 Main Processing Unit Q1(MPUQ1)
                "
       REVISION    "201906091000Z"
       DESCRIPTION "V9.38,
	    Add: fnameUSG6385E(16715873),
		Add: fnameUSG6305E(16715874),
		Add: fnameUSG6309E(16715875),
		Add: fnameUSG6315E(16715876),
		Add: fnameUSG6325E(16715877),
		Add: fnameUSG6335E(16715878),
		Add: fnameUSG6355E(16715879),
		Add: fnameUSG6365E(16715880),
		Add: fnameUSG6525E(16715881),
		Add: fnameUSG6555E(16715882),
		Add: fnameUSG6565E(16715883),
		Add: fnameUSG6585E(16715884),
		Add: fnameEudemon200E-G85-AC(16715885),
		Add: fnameEudemon200E-G85-DC(16715886),
		Add: fnameUSG6395E(16715887),
		Add: fnameUSG6615E(16715888),
		Add: fnameUSG6625E(16715889),
		Add: fnameEudemon1000E-G15-AC (16715890),
		Add: fnameEudemon1000E-G15-DC(16715891),
		Add: fnameEudemon1000E-G25-AC(16715892),
		Add: fnameEudemon1000E-G25-DC(16715893),
		Add: fnameUSG6635E-AC(16715894),
		Add: fnameUSG6635E-DC(16715895),
		Add: fnameUSG6655E(16715896),
		Add: fnameAntiDDoS1825(16715897),
		Add: fnameEudemon1000E-G35-AC(16715898),
		Add: fnameEudemon1000E-G35-DC(16715899),
		Add: fnameEudemon1000E-G55-AC(16715900),
		Add: fnameEudemon1000E-G55-DC(16715901),
		Add: fnameIPS6309E-AC(16715902),
		Add: fnameIPS6315E-AC(16715903),
		Add: fnameIPS6515E-AC(16715904),
		Add: fnameIPS6555E-AC(16715905),
		Add: fnameIPS6555ED-AC(16715906),
		"
        REVISION    "201906050000Z"
        DESCRIPTION "V9.37,
                Add: bnameLST3MPUE0000(659717),            --S9300X main control unit E for v2r19c00
                Add: bnameLST3SFUEX100(659718),             --S9300X switch fabric unit E(X1) for v2r19c00
                Add: bnameLST7MPUE0000(700506),             --S12700E main control unit E for v2r19c00 12700E
                Add: bnameLST7SFUEX100(700507),             --S12700E switch fabric unit E(X1) for v2r19c00 12700E
                Add: bnameLST7G48TX5S0(700508),             --48-port 10/100/1000BASE-T interface card (X5S,RJ45) for v2r19c00 12700E
                Add: bnameLST7G48TX5E0(700509),             --48-port 10/100/1000BASE-T interface card (X5E,RJ45) for v2r19c00 12700E
                "
        REVISION    "201906030000Z"
        DESCRIPTION "V9.36,
            Add: fname8090NE20E-S4-AC(676110),            -- NE20E-S4-AC chassis
            Add: fname8090NE20E-S4-DC(676111),            -- NE20E-S4-DC chassis
            Add: fname8090PTN6900-1-M4-AC(676112),        -- PTN6900-1-M4-AC chassis
            Add: fname8090PTN6900-1-M4-DC(676113),        -- PTN6900-1-M4-DC chassis
            Add: fnameNE08E-S9-DC(704578),                -- NE08E-S9-DC chassis
            Add: fnameNE08E-S9-AC(704579),                -- NE08E-S9-AC chassis
            Add: virent8090DEVCR5D0MPUB970(567800),    -- V8R12C00 for CR5D0MPUB970(SBOM) Main Processing Unit B9(32G Memory)
            Add: virent8090DEVCX6D0MPUB970(567801),    -- V8R12C00 for CX6D0MPUB970(SBOM) Main Processing Unit B9(32G Memory)
            Add: virent8090DEVTNRD0MPUB970(567802),    -- V8R12C00 for TNRD0MPUB970(SBOM) Main Processing Unit B9(32G Memory)
            Add: virent8090DEVME0DMPUX8970(567803),    -- V8R12C00 for ME0DMPUX8970(SBOM) Main Processing Unit B9(32G Memory)
            Add: virent8090DEVCX6D0MPUB910(567804),    -- V8R12C00 for CX6D0MPUB910(SBOM) Main Processing Unit B9(32G Memory)
            Add: virent8090DEVCR5D0SRUAF70(567805),    -- V8R12C00 for CR5D0SRUAF70(SBOM) Switch and Route Processing Unit A15(32G Memory)
            Add: virent8090DEVCX6D0SRUAF70(567806),    -- V8R12C00 for CX6D0SRUAF70(SBOM) Switch and Route Processing Unit A15(32G Memory)
            Add: virent8090DEVTNRD0SRUAF70(567807),    -- V8R12C00 for TNRD0SRUAF70(SBOM) Switch and Route Processing Unit A15(32G Memory)
            Add: virent8090DEVME0D0SRUAF71(567808),    -- V8R12C00 for ME0D0SRUAF71(SBOM) Switch and Route Processing Unit A15(32G Memory)
            Add: virent8090DEVCX6D0SRUAF10(567809),    -- V8R12C00 for CX6D0SRUAF10(SBOM) Switch and Route Processing Unit A15(32G Memory)
            Add: virent8090DEVCR5D0SRUAE70(567810),    -- V8R12C00 for CR5D0SRUAE70(SBOM) Switch and Route Processing Unit A14(32G Memory)
            Add: virent8090DEVCX6D0SRUAE70(567811),    -- V8R12C00 for CX6D0SRUAE70(SBOM) Switch and Route Processing Unit A14(32G Memory)
            Add: virent8090DEVTNRD0SRUAE70(567812),    -- V8R12C00 for TNRD0SRUAE70(SBOM) Switch and Route Processing Unit A14(32G Memory)
            Add: virent8090DEVME0D0SRUAD70(567813),    -- V8R12C00 for ME0D0SRUAD70(SBOM) Switch and Route Processing Unit A14(32G Memory)
            Add: virent8090DEVCX6D0SRUAE10(567814),    -- V8R12C00 for CX6D0SRUAE10(SBOM) Switch and Route Processing Unit A14(32G Memory)
            Add: virent8090DEVCR5D0SRUAD70(567815),    -- V8R12C00 for CR5D0SRUAD70(SBOM) Switch and Route Processing Unit A13(32G Memory)
            Add: virent8090DEVCX6D0SRUAD70(567816),    -- V8R12C00 for CX6D0SRUAD70(SBOM) Switch and Route Processing Unit A13(32G Memory)
            Add: virent8090DEVTNRD0SRUAD70(567817),    -- V8R12C00 for TNRD0SRUAD70(SBOM) Switch and Route Processing Unit A13(32G Memory)
            Add: virent8090DEVCR5D0MPUB971(567818),   -- V8R12C00 for CR5D0MPUB971(SBOM) Main Processing Unit B9A(32G Memory)
            Add: virent8090DEVME0DMPUX8971(567819),    -- V8R12C00 for ME0DMPUX8971(SBOM) Main Processing Unit B9A(32G Memory)
            Add: virent8090DEVCR5D0SRUAD71(567820),    -- V8R12C00 for CR5D0SRUAD71(SBOM) Switch and Route Processing Unit A13A(32G Memory
            Add: virent8090DEVCR5DSFUIT27G(688300),     -- V8R11C10 for CR5DSFUIT27G(SBOM) 2Tbps Switch Fabric Unit E1(SFUI-2T-E)
            Add: virent8090DEVCR5DSFUIT27H(688301),     -- V8R11C10 for CR5DSFUIT27H(SBOM) 2Tbps Switch Fabric Unit E1(SFUI-2TA-E)
            Add: virent8090DEVCR5DSFUIT27I(688302),     -- V8R11C10 for CR5DSFUIT27I(SBOM) 2Tbps Switch Fabric Unit F1(SFUI-2T-F)
            Add: virent8090DEVCR5DSFUIT27J(688303),     -- V8R11C10 for CR5DSFUIT27J(SBOM) 2Tbps Switch Fabric Unit F1(SFUI-2TA-F)
            Add: virent8090DEVCR5D0EKGFA71(688304),     -- V8R11C10 for CR5D0EKGFA71(SBOM) 40-Port 100/1000Base-X-SFP MACsec Integrated Line Processing Unit (LPUI-52)
            Add: virent8090DEVCR5D0EKGFA72(688305),     -- V8R11C10 for CR5D0EKGFA72(SBOM) 40-Port 100/1000Base-X-SFP MACsec Integrated Line Processing Unit (LPUI-52A)
            Add: virent8090DEVCR5D0E2NBA70(688306),     -- V8R11C10 for CR5D0E2NBA70(SBOM) 4-Port 50G/2-Port 100GBase-QSFP28 FlexE/MACsec Integrated Line Processing Unit(LPUI-242)
            Add: virent8090DEVCR5D0EEXFA70(688307),     -- V8R11C10 for CR5D0EEXFA70(SBOM) 24-Port 10GBase LAN/WAN-SFP+ MACsec Integrated Line Processing Unit(LPUI-242)
            Add: virent8090DEVCR5D0E8YFA70(688308),     -- V8R11C10 for CR5D0E8YFA70(SBOM) 8-Port 25GBase-SFP28 MACsec Integrated Line Processing Unit(LPUI-242)
            Add: virent8090DEVCR5D0E2NBA71(688309),     -- V8R11C10 for CR5D0E2NBA71(SBOM) 4-Port 50G/2-Port 100GBase-QSFP28 FlexE/MACsec Integrated Line Processing Unit(LPUI-242A)
            Add: virent8090DEVCR5D0EEXFA71(688310),     -- V8R11C10 for CR5D0EEXFA71(SBOM) 24-Port 10GBase LAN/WAN-SFP+ MACsec Integrated Line Processing Unit(LPUI-242A)
            Add: virent8090DEVCR5D0E2NBA72(688311),     -- V8R11C10 for CR5D0E2NBA72(SBOM) 4-Port 50G/2-Port 100GBase-QSFP28 FlexE/MACsec Integrated Line Processing Unit(LPUI-242-G)
            Add: virent8090DEVCR5D0E4NBA70(688312),     -- V8R11C10 for CR5D0E4NBA70(SBOM) 4-Port 100GBase-QSFP28 FlexE/MACsec Integrated Line Processing Unit (LPUI-402)
            Add: virent8090DEVCR5D0E4NBA71(688313),     -- V8R11C10 for CR5D0E4NBA71(SBOM) 4-Port 100GBase-QSFP28 FlexE/MACsec Integrated Line Processing Unit (LPUI-402A)
            "
        REVISION    "201906030000Z"
        DESCRIPTION "V9.35,
            Add: virentANGMHSTH0100(225610),         -- ATN 910C-H,ANGMHSTH0100,ATN 910C-H DC Basic Configuration(Includes Fixed Enable Interface (4*10GE/GE/FE(o)+ 4*GE/FE(o)+4*GE/FE(e))/Dual Power/FAN/Chassis)
            Add: virentANGMHSTS0100(225611),         -- ATN 910C-S,ANGMHSTS0100,ATN 910C-S DC Basic Configuration(Includes Fixed Enable Interface (5*10GE/GE/FE(o)+3*GE/FE(o)+4*GE/FE(e))/Dual Power/FAN/Chassis)
            Add: virentANND00CXPA00(225612),         -- ATN 980C,ANN1CXPA00,System Control,Cross-connect and Multi-protocol Process Unit with 800G
            Add: virentANGMHSTG0100(225613),         -- ATN 910C-G,ANGMHSTG0100,ATN 910C-G DC Basic Configuration(16*10GE/GE/FE(o)+12*GE/FE(o)+4*GE/FE(e))/Dual DC Power Input/FAN/Chassis)
            Add: fnameATNDEV910C-H(225610),          --910C-H  chassis
            Add: fnameATNDEV910C-S(225611),          --910C-S  chassis
            Add: fnameATNDEV980C(225612),            --980C  chassis
            Add: fnameATNDEV910C-G(225613),          --910C-G  chassis
            Add: fnamePTN980(229410),                       --PTN980 chassis
            Add: fnamePTN990E(229411),                       --PTN990E chassis
            Add: bnamePTN980TPN1CXPA00(229514),           --PTN980 800G TPN1CXPA
            Add: bnamePTN980TPN1CXPB00(229515),           --PTN980 320G TPN1CXPB
            Add: bnamePTN980TPN1CXPC00(229516),           --PTN980 320G TPN1CXPC
            Add: bnamePTN990ETPN1CXPA00(229517),           --PTN990E
            "
        REVISION    "201905180000Z"
        DESCRIPTION "V9.34,
            Add: bnamePTN7900TPA2FV4(229533), --TPA2FV4, 4-port 50 Gigabit Ethernet Switching Processing Board
            Add: bnamePTN7900TPA3EG24(229534), --TPA3EG24, 24-port Gigabit Ethernet Switching Processing Board
            Add: bnamePTN7900TPF1CXPB(229535), --TPF1CXPB, System Control Communication and Switch Fabric Process Unit,1*1
            Add: bnamePTN7900TPF1XCSB(229536), --TPF1XCSB, Switch Fabric Unit,1*1
            "
	    REVISION    "201905170000Z"
        DESCRIPTION "V9.33,
            Add: fnameMA5812S-G5-AE08(561663),  --Frame MA5812S-AE08 of the MA5812S device.
            Add: bnameH82EEFKR(156093),        --Master board of MA5812S-AE08 device.
            Add: bnameHS2EEFKR(156091),        --8 G.FAST board of MA5812S-DE16 service board.
            Add: bnameH82EEFKA(156092),        --8 G.FAST board of MA5812S-DE16 service board.
            Add  fnameMA5621HH831Mabc(561664),  --Frame of the MA5621H device.
            Add  bnameH825CCIQ(156094),         --Master board of MA5621H device.
            "
        REVISION    "201905161000Z"
        DESCRIPTION "V9.32,
                    Add: fnameCE16804(688187),                    -- CloudEngine CE16804 FRAME
                    Add: fnameCE16808(688188),                    -- CloudEngine CE16808 FRAME
                    Add: fnameCE16816(688189),                    -- CloudEngine CE16816 FRAME
                    Add: fnameCE98604CEI(688191),                 -- CloudEngine 9800,CE9860-4C-EI,CE9860-4C-EI mainframe
                    Add: fnameCE686348S6CQ(688194),               -- CloudEngine 6800,CE6863-48S6CQ-F,CE6863-48S6CQ-F switch
                    Add: fnameCE688148S6CQ(688195),               -- CloudEngine 6800,CE6881-48S6CQ-F,CE6881-48S6CQ-F switch
                    Add: bnameCEMPUDHALF(688318),                 -- Finished Board Unit,CE16800,CE-MPUD-HALF,CE16800 Main Processing Unit D (half-width)
                    Add: bnameCESFUF1S(688319),                   -- Manufactured Board,CloudEngine 12800S,CE-SFUF1-S,CE12800S Switch Fabric Unit F1,1*1
                    Add: bnameCESFU08F1(688320),                  -- Manufactured Board,CloudEngine 12800,CE-SFU08F1,CE12808 Switch Fabric Unit F1,1*1
                    Add: bnameCESFU08G1(688321),                  -- Manufactured Board,CloudEngine 12800,CE-SFU08G1,CE12808 Switch Fabric Unit G1,1*1
                    Add: bnameCEL36LQFDG(688322),                 -- Finished Board Unit,CloudEngine 16800,CEL36LQFD-G,36-port 40GE interface card (FD-G, QSFP+)
                    Add: bnameCESFU08GG(688323),                  -- Finished Board Unit,CE16800,CE-SFU08G-G,CE16808 Switch Fabric Unit G
                    Add: bnameCEMPUCS(688325),                    -- Manufactured Board,CloudEngine 12800S,CE-MPUC-S
                    Add: bnameCECMUC(688326),                     -- CloudEngine 12800,CE-CMUC,Centralized Monitoring Board B,1*1
                    Add: bnameCE98604CEI(688327),                 -- Manufactured Board,CloudEngine 9800,128x100G QSFP28 Tomahawk3 x86
                    Add: bnameCESFU16F1(688328),                  -- Manufactured Board,CloudEngine 12816,CE-SFU16F1,CE12816 Switch Fabric Unit F,1*1
                    Add: bnameCESFU16G1(688329),                  -- Manufactured Board,CloudEngine 12816,CE-SFU16G1,CE12816 Switch Fabric Unit G,1*1
                    Add: bnameCESFU04G1(688330),                  -- Manufactured Board,CloudEngine 12804,CE-SFU04G1,CE12804 Switch Fabric Unit G,1*1
                    Add: bnameCEL18CQFDG(688331),                 -- Finished Board Unit,CloudEngine 16800,CEL18CQFD-G,18-port 100GE interface card (FD-G, QSFP28)
                    Add: bnameCEL36CQFDG(688332),                 -- Finished Board Unit,CloudEngine 16800,CEL36CQFD-G,36-port 100GE interface card (FD-G, QSFP28)
                    Add: bnameCESFU08FG(688333),                  -- Finished Board Unit,CE16800,CE-SFU08F-G,CE16808 Switch Fabric Unit F
                    Add: bnameCESFU04GG(688337),                  -- Finished Board Unit,CE16800,CE-SFU04G-G,CE16804 Switch Fabric Unit G
                    Add: bnameCEL48XSFDG(688338),                 -- Finished Board Unit,CloudEngine 16800,CEL48XSFD-G,48-port 10GE interface card (FD-G, SFP+)
                    Add: bnameCE686348S6CQ(688339),               -- CloudEngine 6800,CE6863-48S6CQ-F,CE6863-48S6CQ-F switch
                    Add: bnameCE688148S6CQ(688340),               -- CloudEngine 6800,CE6881-48S6CQ-F,CE6881-48S6CQ-F switch
                    Add: bnameCESFU16GG(688341),                  -- Finished Board Unit,CE16800,CE-SFU16G-G,CE16816 Switch Fabric Unit G
                    Add: bnameCESFU16FG(688342),                  -- Finished Board Unit,CE16800,CE-SFU16F-G,CE16816 Switch Fabric Unit F
                    Add: bnameCEL24LQFDG(688343),                 -- Finished Board Unit,CloudEngine 16800,CEL24LQFD-G,24-port 40GE interface card (FD-G, QSFP+)
                    Add: bnameCEMPUDFULL(688344),                 -- Finished Board Unit,CE16800,CE-MPUD-FULL,CE16800 Main Processing Unit D (full-width)
                    Add: bnameCESFU04FG(688345),                  -- Finished Board Unit,CE16800,CE-SFU04F-G,CE16804 Switch Fabric Unit F
                    Add: subbnameCED24S2CQ1(688142),              -- Manufactured Board,CloudEngine 8800,CE88-D24S2CQ1,CE88:24-port 25GE SFP28 and 2-port 100GE QSFP28 interface card (supporting MACsec),1*1
                    Add: subbnameCED32CQ(688143),                 -- Manufactured Board,CloudEngine 9800,CE98-D32CQ,CE9860X:32 Port 100GE QSFP28 Interface Card,1*1
                    "

		REVISION    "201905141000Z"
        DESCRIPTION "V9.31,
                    Add: bnamePTN7900TPA2EX24S(229516), --TPA2EX24S, 24-port 10 Gigabit Ethernet Switching Processing Board
                    Add: bnamePTN7900TPD2EX24S(229517), --TPD2EX24S, 24-port 10 Gigabit Ethernet Switching Processing Board
                    Add: bnamePTN7900TPA2EX16S(229518), --TPA2EX16S, 16-port 10 Gigabit Ethernet Switching Processing Board
                    Add: bnamePTN7900TPD2EX16S(229519), --TPD2EX16S, 16-port 10 Gigabit Ethernet Switching Processing Board
                    Add: bnamePTN7900TPD1FH12(229520), --TPD1FH12, 12-port 100 Gigabit Ethernet Switching Processing Board
                    Add: bnamePTN7900TPD1FH8(229521), --TPD1FH8, 8-port 100 Gigabit Ethernet Switching Processing Board
                    Add: bnamePTN7900TPA2FH4(229522), --TPA2FH4, 4-port 100 Gigabit Ethernet Switching Processing Board
                    Add: bnamePTN7900TPD2FH4(229523), --TPD2FH4, 4-port 100 Gigabit Ethernet Switching Processing Board
                    Add: bnamePTN7900TPA3FH2(229524), --TPA3FH2, 2-port 100 Gigabit Ethernet Switching Processing Board
                    Add: bnamePTN7900TPD3FH2(229525), --TPA3FH2, 2-port 100 Gigabit Ethernet Switching Processing Board
                    Add: bnamePTN7900TPA2FH1(229526), --TPA2FH1, 1-port 100 Gigabit Ethernet Switching Processing Board
                    Add: bnamePTN7900TPD2FH1(229527), --TPD2FH1, 1-port 100 Gigabit Ethernet Switching Processing Board
                    Add: bnamePTN7900TPA2FHD2(229528), --TPA2FHD2, 2-port 200 Gigabit Ethernet Switching Processing Board
                    Add: bnamePTN7900TPD2FHD2(229529), --TPD2FHD2, 2-port 200 Gigabit Ethernet Switching Processing Board
                    Add: bnamePTN7900TPA1FHL1(229530), --TPA1FHL1, 1-port 400 Gigabit Ethernet Switching Processing Board
                    Add: bnamePTN7900TPD1SCAB(229531), --TPD1SCAB, System Control, Communication and Auxiliary Processing Unit,1*1
                    Add: bnamePTN7900TPD1XCSB(229532), --TPD1XCSB, Switch Fabric Unit,1*1
                    "

        REVISION    "201905141000Z"
        DESCRIPTION "V9.30,
              Add: fname8090CX600-X1-M4-AC(537991),           --Quidway CX600-X1-M4-AC FRAME for V8R11C10
              Add: fname8090CX600-X1-M4-DC(537992),           --Quidway CX600-X1-M4-DC FRAME for V8R11C10
              Add: fname8090CX600-M4-AC(537993),              --Quidway CX600-M4-AC FRAME for V8R11C10
              Add: fname8090CX600-M4-DC(537994),              --Quidway CX600-M4-DC FRAME for V8R11C10
              Add: fname8090NE40E-X1-M4-AC(537995),           --Quidway NE40E-X1-M4-AC FRAME for V8R11C10
              Add: fname8090NE40E-X1-M4-DC(537996),           --Quidway NE40E-X1-M4-DC FRAME for V8R11C10
                    "
        REVISION    "201905131000Z"
        DESCRIPTION "V9.29,
              Add: 400A-picOM.
                    "

        REVISION    "201905071000Z"
        DESCRIPTION "V9.28,
              Add: bnameH902FLHFE(148669),         --  16*flex-PON board of EA5800.
                    "

        REVISION    "201905070000Z"
        DESCRIPTION "V9.27,
                Add: virent8090DEVCR5D00EDNB63(561793),    -- V8R11C10 for CR5D00EDNB63(SBOM) 16-Port 100GBase QSFP28 Integrated Line Process Unit CM(NE5000E LPUI-1T6-CM)
                Add: virent8090DEVCR5D00E4KB61(561794),    -- V8R11C10 for CR5D00E4KB61(SBOM) 4-Port 400GBase QSFP-DD Integrated Line Process Unit CM(NE5000E LPUI-1T6-CM)
                Add: virent8090DEVCR5D00NDNC61(561795),    -- V8R11C10 for CR5D00NDNC61(SBOM) 16-Port 100G OTN/ETH QSFP28 Integrated Line Process Unit(NE5000E LPUI-1T6-CM)
                Add: virent8090DEVCR5D00LRXF61(561792),    -- V8R11C10 for CR5D00LRXF61(SBOM) 72-Port 10GBase LAN/WAN-SFP+ Integrated Line Process Unit CM(NE5000E LPUI-1T6-CM)"

        REVISION    "201905060000Z"

        DESCRIPTION "V9.26,
                Add: bnameH902GPSF(148662),         --  16*GPON board of MA5800.
                Add: bnameH902GPHFE(148668),         --  16*GPON board of MA5800."

        REVISION    "201905060000Z"
         DESCRIPTION "V9.25,
		 	Add: fnameAP5760-10(692336),        --WLAN R19C00 new AC ENUM_
			Add: fnameAC6507S-B(692335),         --WLAN R19C00 new AC ENUM_
			Add: fnameAC6508-B(692334),        --WLAN R19C00 new AC ENUM_
			Add: bnameAP5760-10(692336),        --WLAN R19C00 new AC ENUM_
            Add: bnameAC6507S-B(692335),         --WLAN R19C00 new AC ENUM_
            Add: bnameAC6508-B(692334),        --WLAN R19C00 new AC ENUM_
            "

        REVISION    "201905050000Z"
         DESCRIPTION "V9.24,
            Add: virent8090DEVCX6D0E2NBF10(675998),     -- V8R11C10 for CX6D0E2NBF10(SBOM) 2-Port 100GBase-QSFP28 FlexE/MACsec Integrated Integrated Service Unit (ISUI-201)
            Add: virent8090DEVCX6D0E4NBF10(675995),     -- V8R11C10 for CX6D0E4NBF10(SBOM) 4-Port 100GBase-QSFP28 FlexE/MACsec Integrated Integrated Service Unit(ISUI-401)
            Add: virent8090DEVCX6D0E8YFA10(675831),   -- v8r11c10 for CX6D0E8YFA10(SBOM) 8-Port 25GBase-SFP28 Integrated Integrated Service Unit (ISUI-201)
            Add: virent8090DEVCR5DEDVE8N70(676991),      -- V8R11C10 for CR5DEDVE8N70(SBOM) 16-Port 50G/8-Port 100GBase-QSFP28 Integrated Line Processing Unit L(LPUI-1T-L)
            Add: virent8090DEVCR5D00EENB72(676992),      -- V8R11C10 for CR5D00EENB72(SBOM) 20-Port 100GBase-QSFP28 Integrated Line Processing Unit L(LPUI-2T-L)
            "
		REVISION    "201904230000Z"
        DESCRIPTION "V9.23,
       	      Add:bnamePTN7900TPD2FHD1(229514), --TPD2FHD1,1-port 200 Gigabit Ethernet Switching Processing Board
              Add:bnamePTN7900TPA2FHD1(229515), --TPA2FHD1,1-port 200 Gigabit Ethernet Switching Processing Board
                    "


        REVISION    "201904220000Z"
        DESCRIPTION "V9.22,
       	      Add: subnameFAN023AB(536797),                     --FAN-023A-B for V2R13C02
                    "

        REVISION    "201904120000Z"

		DESCRIPTION "V9.21,
       	      Add: bnameH902XSHF(148664),         --  16*10G XGS-PON board of MA5800.
       	      Add: bnameH902FLHF(148665),         --  16*flex-PON board of MA5800.
       	      Add: bnameH902CGUF(148666),         --  16*XG GPON and GPON combo board of MA5800.
       	      Add: bnameH902OXHD(148667),         --  8*10GE P2P board of MA5800.
                    "
        REVISION    "201904100000Z"

		DESCRIPTION "V9.20,
       	      Add: virent8090DEVCR9D00EPXF81(675997),    -- V8R11C10 for CR9D00EPXF81(SBOM) 60-Port 10GBase LAN/WAN-SFP+ MACSec Integrated Line Process Unit CM(LPUI-1T-CM)
       	      Add: virent8090DEVCR9D000CMU61(675994),    -- V8R11C10 for CR9D000CMU61(SBOM) Finished Board,CR58CMUBA03,Centralized Monitoring Module
       	      Add: virent8090DEVCR9D000CMU62(675996),    -- V8R11C10 for CR9D000CMU62(SBOM) Finished Board,CR58CMUBA02,Centralized Monitoring Module
       	      Add: virent8090DEVCR5DNKFEDY70(675988),     -- V8R11C10 for CR5DNKFEDY70(SBOM) 40-Port 10Gase LAN/WAN-SFP+ MACsec Integrated Line Processing Unit (LPUI-400)
       	      Add: virent8090DEVCR5DNKFEDY71(675993),     -- V8R11C10 for CR5DNKFEDY71(SBOM) 40-Port 10Gase LAN/WAN-SFP+ MACsec Integrated Line Processing Unit (LPUI-400A)
                    "
		REVISION    "201904091000Z"
       DESCRIPTION "V9.19,
       	      Add: fnameUSG6391E-AC(16715865),
       	      Add: fnameUSG6610E-AC(16715866),
       	      Add: fnameUSG6620E-AC(16715867),
       	      Add: fnameEudemon1000E-G1-AC(16715868),
       	      Add: fnameEudemon1000E-G1-DC(16715869),
       	      Add: fnameEudemon1000E-G2-AC(16715870),
       	      Add: fnameEudemon1000E-G2-DC(16715871),
       	      Add: fnameAntiDDoS1820-N(16715872),
       	      "
               REVISION    "201904011000Z"
            DESCRIPTION "V9.18,
                    Add: subbname8090DEVCR57E8YFA0(225750),        --8-Port 25GBase-SFP28 Integrated Integrated Service Unit (ISUI-201)
                    "
		REVISION    "201903281000Z"
        DESCRIPTION "V9.17,
                    Add: virent8090DEVCX6D0MPUB871(675989),    -- V8R11C10 for CX6D0MPUB871(SBOM) Main Processing Unit B8
					Add: virent8090DEVCX6D0SRUAC71(675990),    -- V8R11C10 for CX6D0SRUAC71(SBOM) Switch and Route Processing Unit A16
					Add: virent8090DEVTNRD0MPUB871(675991),    -- V8R11C10 for TNRD0MPUB871(SBOM) Main Processing Unit B8
					Add: virent8090DEVTNRD0SRUAC71(675992),    -- V8R11C10 for TNRD0SRUAC71(SBOM) Switch and Route Processing Unit A16
                    "
		REVISION    "201903271000Z"
        DESCRIPTION "V9.16,
                    "

        REVISION    "201903251000Z"
        DESCRIPTION "V9.15,
            Add:fname8031CX600-M2K-DC(580932),             --Quidway CX600-M2K-DC FRAME for V8R11C10
                fname8031CX600-M2K-B-DC(580940),           --Quidway CX600-M2K-B-DC FRAME for V8R11C10
                fnamePTN6900-M2K-DC(580936),               --Quidway PTN6900-M2K-DC FRAME for V8R11C10
                fnamePTN6900-M2K-B-DC(580944),             --Quidway PTN6900-M2K-B-DC FRAME for V8R11C10
                fname8090CX6602-B-DC(580946),              --Quidway CX6602-B-DC FRAME for V8R11C10
                fname8090CX6602-DC(580938),                --Quidway CX6602-DC FRAME for V8R11C10
                fname8090NE40E-M2K-B-DC(580942),           --Quidway NE40E-M2K-B-DC FRAME for V8R11C10
                fname8090NE40E-M2K-DC(580934),             --Quidway NE40E-M2K-DC FRAME for V8R11C10
                fnamePTN6900-M2K-AC(580935),               --Quidway PTN6900-M2K-AC FRAME for V8R11C10
                fname8031CX600-M2K-AC(580931),             --Quidway CX600-M2K-AC FRAME for V8R11C10
                fname8031CX600-M2K-B-AC(580939),           --Quidway CX600-M2K-B-AC FRAME for V8R11C10
                fname8090CX6602-AC(580937),                --Quidway CX6602-AC FRAME for V8R11C10
                fnamePTN6900-M2K-B-AC(580943),             --Quidway PTN6900-M2K-B-AC FRAME for V8R11C10
                fname8090NE40E-M2K-B-AC(580941),           --Quidway NE40E-M2K-B-AC FRAME for V8R11C10
                fname8090NE40E-M2K-AC(580933),             --Quidway NE40E-M2K-AC FRAME for V8R11C10
                fname8090CX6602-B-AC(580945),              --Quidway CX6602-B-AC FRAME for V8R11C10
                fname8031CX600-M2E-AC(580911),             --Quidway CX600-M2E-AC FRAME for V8R11C10
                fname8090NE40E-M2E-AC(580913),             --Quidway NE40E-M2E-AC FRAME for V8R11C10
                fnameNE20E-S2E-AC(580917),                 --Quidway NE20E-S2E-AC FRAME for V8R11C10
                fnamePTN6900-M2E-AC(580915),               --Quidway PTN6900-M2E-AC FRAME for V8R11C10
                fname8031CX600-M2E-DC(580912),             --Quidway CX600-M2E-DC FRAME for V8R11C10
                fname8090NE40E-M2E-DC(580914),             --Quidway NE40E-M2E-DC FRAME for V8R11C10
                fnameNE20E-S2E-DC(580918),                 --Quidway NE20E-S2E-DC FRAME for V8R11C10
                fnamePTN6900-M2E-DC(580916),               --Quidway PTN6900-M2E-DC FRAME for V8R11C10
                fname8031CX600-M2F-AC(580919),             --Quidway CX600-M2F-AC FRAME for V8R11C10
                fname8090NE40E-M2F-AC(580921),             --Quidway NE40E-M2F-AC FRAME for V8R11C10
                fnameNE20E-S2F-AC(580925),                 --Quidway NE20E-S2F-AC FRAME for V8R11C10
                fnamePTN6900-M2F-AC(580923),               --Quidway PTN6900-M2F-AC FRAME for V8R11C10
                fname8031CX600-M2F-DC(580920),             --Quidway CX600-M2F-DC FRAME for V8R11C10
                fname8090NE40E-M2F-DC(580922),             --Quidway NE40E-M2F-DC FRAME for V8R11C10
                fnameNE20E-S2F-DC(580926),                 --Quidway NE20E-S2F-DC FRAME for V8R11C10
                fnamePTN6900-M2F-DC(580924),               --Quidway PTN6900-M2F-DC FRAME for V8R11C10
                fname8031CX600-M2H-AC(580927),             --Quidway CX600-M2H-AC FRAME for V8R11C10
                fname8090NE40E-M2H-AC(580929),             --Quidway NE40E-M2H-AC FRAME for V8R11C10
                fname8031CX600-M2H-DC(580928),             --Quidway CX600-M2H-DC FRAME for V8R11C10
                fname8090NE40E-M2H-DC(580930),             --Quidway NE40E-M2H-DC FRAME for V8R11C10
            "
         REVISION    "201903201000Z"
        DESCRIPTION "V9.14,
        Add:subbname8090DEVCR5D00EDYB70(225748),    --16-Port 25GBase-SFP28 Flexible Card E(P1T-E)
			"
        REVISION    "201903181000Z"
        DESCRIPTION "V9.13,
        add wlan device
        Add:virent8090DEVCR9D00MPUS80(562165),   -- v8r11c10 NE9000-20 Main Processing Unit S(MPUS)
			"
		REVISION    "201903121000Z"
        DESCRIPTION "V9.12,
        add wlan device
        ADD:fnameWAC9600S-S(692331),         --WLAN new wac ENUM_
            fnameAP6750-10T(692332),         --WLAN new apENUM_
            fnameAP5760S-10(692333),        --WLAN new ap ENUM_
			"
		REVISION    "201903080000Z"
        DESCRIPTION "V9.11,
					Add: virent8090DEVCX6DSFUIU07F(675983), 	 -- V8R11C10 for 2Tbps Switch Fabric Unit E(SFUI-2T-E)
					Add: virent8090DEVTNRDSFUIT27E(675984),		 -- V8R11C10 for 2Tbps Switch Fabric Unit E(SFUI-2T-E)
					Add: virent8090DEVCX6DSFUIU07F(675985), 	 	 -- V8R11C10 for 2Tbps Switch Fabric Unit F(SFUI-2T-F)
					Add: virent8090DEVTNRDSFUIU07F(675986), 	     -- V8R11C10 for 2Tbps Switch Fabric Unit F(SFUI-2T-F)
					Add: virent8090DEVCR5DEDVE8N7P(675978),      -- V8R11C10 for 16-Port 50G/8-Port 100GBase-QSFP28 FlexE/MACsec Integrated Line Processing Unit CM(LPUI-1T-CM)
					Add: virent8090DEVCR5D00EIYB7P(675979),       -- V8R11C10 for 32-Port 25GBase-SFP28 MACsec Integrated Line Processing Unit CM(LPUI-1T-CM)
					Add: virent8090DEVCR5D00EENB73(675987),      -- V8R11C10 for 20-Port 100GBase-QSFP28 Integrated Line Processing Unit (LPUI-2TA)
					"
        REVISION    "201903050000Z"
        DESCRIPTION "V9.10,
                    Add:fname8031S5731-H24T4XC(537300),                 --S5731-H24T4XC for v2r19c00
                    Add:fname8031S5731-H48T4XC(537301),                 --S5731-H48T4XC for v2r19c00
                    Add:fname8031S5731-H24P4XC(537302),                 --S5731-H24P4XC for v2r19c00
                    Add:fname8031S5731-H48P4XC(537303),                --S5731-H48P4XC for v2r19c00
                    Add:fname8031S5720I-S4T2S-A(537304),                --S5720I-S4T2S-A for v2r19c00
                    Add:fname8031S5720I-S8U2X-A(537305),               --S5720I-S8U2X-A for v2r19c00
                    Add:fname8031S5720I-S8U2X-A1(537306),             --S5720I-S8U2X-A1 for v2r19c00
                    Add:fnameLE3BSS9308X0(659477),               --S9300X-8 assembly chassis
                    Add:fnameLE3BSS9312X0(659478),              --S9300X-12 assembly chassis
                    Add:fnameLE3BSS9304X0(659479),              --S9300X-4 assembly chassis
                    Add:bname8031S5731-H24T4XC(537484),                    --S5731-H24T4XC for V2R19C00 +-
                    Add:bname8031S5731-H48T4XC(537485),                    --S5731-H48T4XC for V2R19C00
                    Add:bname8031S5731-H24P4XC(537486),                    --S5731-H24P4XC for V2R19C00
                    Add:bname8031S5731-H48P4XC(537487),                    --S5731-H48P4XC for V2R19C00
                    Add:bname8031S5720I-S4T2S-A(537488),                    --S5720I-S4T2S-A for V2R19C00
                    Add:bname8031S5720I-S8U2X-A(537489),                   --S5720I-S8U2X-A for V2R19C00
                   Add:bname8031S5720I-S8U2X-A1(537490),                 --S5720I-S8U2X-A1 for V2R19C00
                   Add:subnamePAC600S12CF(536794),              --600W AC Power Module (Front to Back,Power panel side intake) for V2R19C00
                   Add:subnamePAC1000S56CB(536795),            --1000W AC PoE Power Module for V2R19C00
                   Add:subnameFAN031AB(536796),                     --FAN-031A-B for V2R19C00
                   "

        REVISION    "201903020000Z"
        DESCRIPTION "V9.09,
                    Modify: virent8090DEVCX6DSFUIT27C(675974),    -- V8R11C00 for CX6DSFUIT27C(SBOM) 2Tbps Switch Fabric Unit E(SFUI-E)
                    Modify: virent8090DEVCX6DSFUIU01F(675976),    -- V8R11C00 for CX6DSFUIU01F(SBOM) 2Tbps Switch Fabric Unit F(SFUI-F)
                    Delete: virent8090DEVCX6D00E8NB70(675977),    -- V8R11C00 for CX6D00E8NB70(SBOM) 8-Port 100GBase-QSFP28 Integrated Integrated Service Unit(ISUI-1T)
                    "
        REVISION    "201902280000Z"
        DESCRIPTION "V9.08,
                    Add: subbname8090DEVANKD001EV103(225735),      --1 Channel 50G Base QSFP28 High Speed Interface
                    "
        REVISION    "201902230000Z"
        DESCRIPTION "V9.07,
                    Add: virent8090DEVCX6D0MPUB810(675973),    -- V8R11C00 for CX6D0MPUB810(SBOM) Main Processing Unit B8A(32G Memory)
                    Add: virent8090DEVCX6DSFUIT27C(675974),    -- V8R11C00 for CX6DSFUIT27C(SBOM) 2Tbps Switch Fabric Unit E(SFUI-2T-E)
                    Add: virent8090DEVCX6D0SRUAG10(675975),    -- V8R11C00 for CX6D0SRUAG10(SBOM) Switch and Route Processing Unit A16A(32G Memory)
                    Add: virent8090DEVCX6DSFUIU01F(675976),    -- V8R11C00 for CX6DSFUIU01F(SBOM) 2Tbps Switch Fabric Unit F(SFUI-2T-F)
                    Add: virent8090DEVCX6D00E8NB70(675977),    -- V8R11C00 for CX6D00E8NB70(SBOM) 8-Port 100GBase-QSFP28 Integrated Integrated Service Unit(ISUI-1T)
                    "
        REVISION    "201902210000Z"
        DESCRIPTION "V9.06,
                    Add: virent8090DEVCR9D00EENB83(675971),   -- V8R11C10 for 20-Port 100GE-QSFP28 FlexE/MACSec Integrated Line Process Unit CM(LPUI-2T-CM)
					Add: virent8090DEVCR9D00EKNB8M(675972)    -- V8R11C10 for 40-Port 40GE/100GE QSFP28 Integrated Line Process Unit L(LPUI-4T-L)

                    "

        REVISION    "201902130000Z"
        DESCRIPTION "V9.05,
                    Add: virent8090DEVCR5D00EENB7Q(675970),     -- V8R11C10 for CR5D00EENB7Q(SBOM) 20-Port 100GBase-QSFP28 FlexE/MACsec Integrated Line Processing Unit CM(LPUI-2T-CM)
                    Add: fname8090NE40E-X16A-LS(570076),      --Quidway NE40E-X16A-LS FRAME
                    Add: fname8090NE40E-X8A-LS(570075),       --Quidway NE40E-X8A-LS FRAME
                    Add: fname8090NE9000-20-LS(570072),       --Quidway NE9000-20-LS FRAME
                    Add: fname8090NE9000-8-LS(570071),        --Quidway NE9000-8-LS FRAME
                    Add: virent8090DEVCR5DMPUX8670-VMPU(577001),       -- for V800R011C10 CR5DMPUX8670-VMPU, VMPU In Main Processing Unit B6
                    Add: virent8090DEVCR5D0SRUAA70-VMPU(577002),       -- for V800R011C10 CR5D0SRUAA70-VMPU, VMPU In Switch and Route Processing Unit A10(32G Memory)
                    Add: virent8090DEVCR5D0SRUAB73-VMPU(577003),       -- for V800R011C10 CR5D0SRUAB73-VMPU, VMPU In Switch and Route Processing Unit A11
                    "
        REVISION    "201901310000Z"
        DESCRIPTION "V9.04,
                    Add: bnameH902GPUF(148659),         --  16*GPON board of MA5800.
                    Add: bnameH902GPLF(148660),         --  16*GPON board of MA5800.
                    Add: bnameH902XELD(148661),         --  8*10G EPON board of MA5800.
                    "

     REVISION    "201901280000Z"
        DESCRIPTION "V9.03,
                    Add: virent8090DEVME0D0MPUB771(675480),    -- V8R11C00 for ME0D0MPUB771(SBOM) Main Processing Unit B7
                    Add: virent8090DEVCR5D0MPUB773(675481),    -- V8R11C00 for CR5D0MPUB773(SBOM) Main Processing Unit B7
                    Add: virent8090DEVCR5D0SRUAC7B(675482),    -- V8R11C00 for CR5D0SRUAC7B(SBOM) Switch and Route Processing Unit A12
                    Add: virent8090DEVME0D0SRUAC7B(675483),    -- V8R11C00 for ME0D0SRUAC7B(SBOM) Switch and Route Processing Unit A12
                    Add: virent8090DEVCR5D0SRUAC71(675484),    -- V8R11C00 for CR5D0SRUAC71(SBOM) Switch and Route Processing Unit A16
                    Add: virent8090DEVCR5D0MPUB871(675485),    -- V8R11C00 for CR5D0MPUB871(SBOM) Main Processing Unit B8
                    Add: virent8090DEVCR5DMPUX8671(675486),    -- V8R11C00 for CR5DMPUX8671(SBOM) Main Processing Unit B6
                    Add: virent8090DEVME0DMPUX8671(675487),    -- V8R11C00 for ME0DMPUX8671(SBOM) Main Processing Unit B6
                    Add: virent8090DEVCR5DLPUFD07E(675819),    -- V8R11C10 for  CR5DLPUFD07E(SBOM) Flexible Card Line Processing Unit(LPUF-242-E)
                    Add: virent600DEVCR5B0BKP0381(675718),    --V8R11C00 NE40E-M2K CR5B0BKP0381(SBOM), 1T MNPUI NO POWER
                    Add: virent600DEVCR5B0BKP0383(675723),    --NE40E-M2K-B Integrated Chassis Components, CR5B0BKP0383
                    Add: virent600DEVCR5B0BKP0382(675717),    --V8R11C00 NE40E-F1A-14H24Q CR5B0BKP0382(SBOM), F1A-14H24Q

		     "

     REVISION    "201901250000Z"
        DESCRIPTION "V9.02,
                    Add: virentME60DEVME0D0LFXFB70(160520),      -- for V800R011C10 ME0D0LFXFB70(SBOM), 24-Port 10GBase LAN/WAN-SFP+ Broadband Service Unit Integrated(BSUI-240)
		     "

     REVISION    "201901240000Z"
        DESCRIPTION "V9.01,
                    Add: subbname8090DEVCR58EENBD0(225732),      --2 Channels 50G/1 Channel 100G Base QSFP28 High Speed Interface Board(1*50GE enable by default)
		     "
     REVISION    "201901220000Z"
        DESCRIPTION "V9.00,
                    Add: subbname8090DEVCR58EENBD0(225731),      --20-Port 100GE-QSFP28 FlexE/MACSec Integrated Line Process Unit CM(LPUI-2T-CM)
		     "

       REVISION    "201901160000Z"
        DESCRIPTION "V8.59,
                    Add: fname8031S2720S-12TP-EI-AC(537292),         --S2720S-12TP-EI for V2R19C00
                    Add: fname8031S2720S-12TP-PWR-EI-AC(537293),     --S2720S-12TP-PWR-EI for V2R19C00
                    Add: fname8031S2720S-52TP-EI-AC(537294),         --S2720S-52TP-EI for V2R19C00
                   Add: fname8031S2720S-52TP-PWR-EI-AC(537295),     --S2720S-52TP-PWR-EI for V2R19C00
                   Add: fname8031S2720S-28TP-PWR-EI-L-AC(537296),   --S2720S-28TP-PWR-EI-L for V2R19C00
                   Add: fname8031S2720S-28TP-PWR-EI-AC(537297),     --S2720S-28TP-PWR-EI for V2R19C00
                   Add: fname8031S2720S-28TP-EI-AC(537298),         --S2720S-28TP-EI for V2R19C00
                   Add: bname8031S2720S-12TP-EI-AC(537476),             --S2720S-12TP-EI for V2R19C00
                   Add: bname8031S2720S-12TP-PWR-EI-AC(537477),         --S2720S-12TP-PWR-EI for V2R19C00
                   Add: bname8031S2720S-52TP-EI-AC(537478),             --S2720S-52TP-EI for V2R19C00
                   Add: bname8031S2720S-52TP-PWR-EI-AC(537479),         --S2720S-52TP-PWR-EI for V2R19C00
                   Add: bname8031S2720S-28TP-PWR-EI-L-AC(537480),       --S2720S-28TP-PWR-EI-L for V2R19C00
                   Add: bname8031S2720S-28TP-PWR-EI-AC(537481),         --S2720S-28TP-PWR-EI for V2R19C00
                   Add: bname8031S2720S-28TP-EI-AC(537482),             --S2720S-28TP-EI for V2R19C00
                   Add: fnameET1BS12704E0(700423),               -- HUAWEI S12704 FRAME Speed-up for V2R19C00
                   Add: fnameET1BS12708E0(700424),               -- HUAWEI S12708 FRAME Speed-up for V2R19C00
                   Add: fnameET1BS12712E0(700425),               -- HUAWEI S12712 FRAME Speed-up for V2R19C00
                   Add: bnameLE1D2SRUHE00(659697),      --S9306/S9312 main control unit H for v2r19c00
                   Add: bnameLE1D2SFUKE00(659698),      --S9310 switch fabric unit K for v2r19c00
                   Add: bnameLX1D2SFUXE00(659699),      --S9310X switch fabric unit X for v2r19c00
                   Add: bnameLE02CMUA(659700),          --Centralized Monitoring Board for v2r19c00
                   Add: bnameES1D2SRUHE00(663667),      --S7706/S7712 main control unit H for v2r19c00
                   Add: bnameES1D2SFUKE00(663668),      --S7710 switch fabric unit K for v2r19c00
                   Add: bnameES2M2X48TX6S(663669),      --48-port 100BASE-TX/1000/2.5G/5G/10GBASE-T interface card (X6S, RJ45) for v2r19c00
                   Add: bnameES2M2X48TX6E(663670),      --48-port 100BASE-TX/1000/2.5G/5G/10GBASE-T interface card (X6E, RJ45) for v2r19c00
                   Add: bnameES1M2X24VX6S(663671),      --24-port 100BASE-TX/1000/2.5G/5G/10GBASE-T + 24-port 100BASE-TX/1000/2.5GBASE-T PoE interface card (X6S, RJ45, PoE++) for v2r19c00
                   Add: bnameES1M2X24VX6E(663672),      --24-port 100BASE-TX/1000/2.5G/5G/10GBASE-T + 24-port 100BASE-TX/1000/2.5GBASE-T PoE interface card (X6E, RJ45, PoE++) for v2r19c00
                   Add: bnameET1D2SFUBE00(700496),             --S12700 switch fabric unit B for v2r19c00
                   Add: bnameET1M2X48TX6S(700497),           	 --48-port 100BASE-TX/1000/2.5G/5G/10GBASE-T interface card (X6S, RJ45) for v2r19c00
                   Add: bnameET1M2X48TX6E(700498),           	 --48-port 100BASE-TX/1000/2.5G/5G/10GBASE-T interface card (X6E, RJ45) for v2r19c00
		     "

        REVISION    "201901100000Z"
        DESCRIPTION "V8.58,
                     Add: fnameCE88614CEI(688181),             -- CloudEngine CE8861-4C-EI Mainframe(With 4 Subcard Slots)
                     Add: fnameCE88684CEI(688182),             -- CloudEngine CE8868-4C-EI Mainframe(With 4 Subcard Slots)
                     Add: fnameCE588048T6QEI(688183),          -- CloudEngine CE5880-48T6Q-EI Switch(44*GE RJ45, 4*10GE RJ45, 6*40GE QSFP+)
                     Add: fnameCX930(688184),                  -- CX930_100G
                     Add: fnameCE685748S6CQEI(688185),         -- CloudEngine CE6857-48S6CQ-EI Switch(48*10GE SFP+, 6*100GE QSFP28)
                     Add: fnameCX930BASE(688186),              -- CX930BASE
                     Add: bnameCE88614CEI(688294),             -- Manufactured Board,CloudEngine 8800,CEM884CP02,General Switch Control Unit,1*1
                     Add: bnameCE588048T6QEI(688308),          -- Manufactured Board,CloudEngine 6800,CEM48T4Q2CQP01,48-Port 10GE RJ45,4-Port 40GE QSFP+ Optical,2-Port 100GE QSFP28 Optical Switch Control Unit,1*1
                     Add: bnameCEL24LQEDE(688309),             -- Manufactured Board,CloudEngine 12800E,CEL24LQED-E,24-Port-40GE Interface ENP Card(ED,QSFP+)
                     Add: bnameCE88684CEI(688310),             -- Manufactured Board,CloudEngine 8800,CEM884CP02,General Switch Control Unit,1*1
                     Add: bnameCEMPUB(688311),                 -- Manufactured Board,CloudEngine 12800,CE-MPUB,Main Processing Unit B,1*1
                     Add: bnameCX930(688313),                  -- CX930
                     Add: bnameCE685748S6CQEI(688314),         -- Manufactured Board,CloudEngine 6800,CEM48S6CQP03,48-Port 10GE SFP+ Optical,6-Port 100GE QSFP28 Optical Switch Control Unit,1*1
                     Add: bnameCX930BASE(688315),              -- CX930BASE
		     "

        REVISION    "201812270000Z"

        DESCRIPTION "V8.57,
                     Add: addentnamePM(688390)                -- PM  Module
                     Add: bname8090DEVCR58CMUC(562097)        -- Finished Board,NE9000,CR58CMUC,Centralized Monitoring Module
                     Add: bname8090DEVCR58LPU1TC(561995)      -- v8r9c10 NE9000 CR58LPU1TC
                     Add: bname8090DEVCR58LPU1TG(561996)      -- v8r9c10 NE9000 CR58LPU1TG
                     Add: bname8090DEVExX16Power(561990)      -- ExX16Power
                     Add: bname8090DEVNGX20POWER(561991)      -- NGX20POWER
                     Add: bname8090DEVExX16APower(561992)     -- ExX16APower
                     Add: bname8090DEVX3POWER(561993)         -- X3POWER
                     Add: bname8090DEVCOMPOWER(561994)        -- COMPOWER
                     Add: subbname8090DEVCR5DE4NE8V70(225728)    --8-Port 50G/4-Port 100GBase-QSFP28 Flexible Card E(P1T-E)
                     Add: subbname8090DEVCX6DE4NE8V10(225729)    --8-Port 50G/4-Port 100GBase-QSFP28 FlexE/MACsec Flexible Card(S1T)
                     Add: subbname8090DEVCX6D0EDYFA10(225730)    --16-Port 25GBase-SFP28 MACsec Flexible Card(S1T)
                     Add: virent8090DEVCR9DE8KE8N8R(562099)  -- for CR9DE8KE8N8R ,8-Port 400GBase-QSFP-DD + 8-Port 100GBase-QSFP28 Integrated Line Process Unit CM(NE9000 LPUI-4T-CM)
                     Add: virent8090DEVCX6D00EKNBA1(562098)  -- for CX6D00EKNBA1 ,8-Port 400GBase-QSFP-DD + 8-Port 100GBase-QSFP28 Integrated Line Process Unit CM(LPUI-4T)
                     "
        REVISION    "201812270000Z"

        DESCRIPTION "V8.56,
                 Add:--V8R11C00 NE5000E 1.6T
                "
        REVISION    "201812260000Z"
        DESCRIPTION "V8.55,
                        Add:bname8031S5720-28X-PWR-LI-ACF-740(537473),      ---S5720-28X-PWR-LI-ACF(740W) for LSW V2R13C00
                       Add:fname8031S5720-28X-PWR-LI-ACF-740(537289),       --S5720-28X-PWR-LI-ACF(740W) for LSW V2R13C00

                        "

        REVISION    "201812211000Z"

        DESCRIPTION "V8.54,
                Add: rfIpReturnPort(808),           -- IP return RF port
                "
		        REVISION    "201812121000Z"

        DESCRIPTION "V8.53,
              	Add: bnameH805SCUP(156057),         --  MA5800C control board H805SCUP.
                Add: bnameH805SCUQ(156061),         --  MA5800C control board H805SCUQ.
                Add: bnameH803OPGE(156087),         --  MA5600T H803OPGE BOARD
                Add: bnameH803EDTB(156088),         --  MA5600T H803EDTB BOARD
                Add: fnameH805MABC(147540),         -- H805MABC Frame
                Add: fnameH805MABO(147541),         -- H805MABO Frame
                "
        REVISION    "201812121000Z"

        DESCRIPTION "V8.52,
            Add:  bnameTPNM001FAN00(229511),         --TPN1FAN, Fan box
            Add:  bnameTPND001PIU00(229512),           --TPN1PIU, Power Interface Board
            Add:  bnameTPND01APIU00(229513),           --TPN1APIU, Power Interface Board
            "
       REVISION    "201812011000Z"

        DESCRIPTION "V8.51,
            Modify: virent600DEVCX6P020BKP01(675811),    --CX6602-B Integrated Chassis Components, CX6P020BKP01
            Modify: virent600DEVCR5B0BKP0393(675812),    --NE40E-M2K-B Integrated Chassis Components, CR5B0BKP0393
            Modify: virent600DEVCX6B0BKP0393(675813),    --CX600-M2K-B Integrated Chassis Components, CX6B0BKP0393
            Modify: virent600DEVTNRB0BKP0374(675814),    --PTN6900-M2K-B Integrated Chassis Components, TNRB0BKP0374            "

        REVISION    "201811301000Z"
        DESCRIPTION "V8.50,
            Add: subbnameATNANKD001EY401(225650),    -- V8R11C10 5875 pic  ATN/CX/NE/NE5000E/NE9000
            "

        REVISION    "201811231000Z"
        DESCRIPTION "V8.49,
            Add: virent8090DEVCX6D0MPUP2A0(570036),    -- V8R11C00 for CX6D0MPUP2A0(SBOM) Main Processing Unit P2
            "

        REVISION    "201811191000Z"
        DESCRIPTION "V8.48,
            Add: virent8090DEVCR9D00E8KC8P(562096),  -- 8-Port 400GBase-CFP8 Integrated Line Process Unit CM(NE9000 LPUI-4T-CM).
            Add: virent600DEVCX6B0BKP0394(675964),    --V8R11C10 CX600-F1A-8H20Q CX6B0BKP0394(SBOM), F1A-8H20Q
            Add: virent600DEVCR5B0BKP0394(675965),    --V8R11C10 NE40E-F1A-8H20Q CR5B0BKP0394(SBOM), F1A-8H20Q
            Add: virent600DEVTNRB0BKP0394(675966),    --V8R11C10 PTN6900-F1A-8H20Q TNRB0BKP0394(SBOM), F1A-8H20Q
            Add: fname8031CX600-F1A-8H20Q(675964),                --Quidway CX600-F1A-8H20Q FRAME for V8R11C00
            Add: fname8090NE40E-F1A-8H20Q(675965),                --Quidway NE40E-F1A-8H20Q FRAME for V8R11C00
            Add: fname8090PTN6900-F1A-8H20Q(675966),              --Quidway PTN6900-F1A-8H20Q FRAME for V8R11C00
            "

        REVISION    "201811160910Z"
        DESCRIPTION "V8.47,
            Add: bnameH902CGHF(148658),        --  16*XG/G GPON board of MA5800.
            "

		REVISION    "201811151020Z"
        DESCRIPTION "V8.46,
                 Add: virentANGMHSTE0110(225608),             --ATN 910C-E,ANGMHSTE0110,ATN 910C-E DC system,with 4*25GE/2*50GE combo,8*10GE+8*GE,2*25GE+2*10GE+12*GE
                 Modify: virentANGMHSTF0110(225606),          --ATN 910C-F,ANGMHSTF0110,ATN 910C-F DC system,with 6*10GE(o),20*GE/FE(o),4*GE/FE
                 Add: virent8090DEVCR5DF1EFXC7P(675821),    -- V8R11C00 for  CR5DF1EFXC7P(SBOM) 24-Port 10GBase LAN/WAN-SFP+ Integrated Line Processing Unit CM(LPUI-241-CM)
                 Add: virent8090DEVCR5DLPUF5270(675820), -- V8R11C00 for CR5DLPUF5270(SBOM) Flexible Card Line Processing Unit(LPUF-52,2 sub-slots)

                    "

        REVISION    "201811101021Z"
        DESCRIPTION "V8.45,
                Add: virent8090DEVCR5D00LRXF60(567007),    -- V8R11C00 for CR5D00LRXF60(SBOM) 72-Port 10GBase LAN/WAN-SFP+ Integrated Line Process Unit(NE5000E LPUI-1T6)
                Add: virent8090DEVCR5D00EDNB62(567008),    -- V8R11C00 for CR5D00EDNB62(SBOM) 16-Port 100GBase QSFP28 Integrated Line Process Unit(NE5000E LPUI-1T6)
                Add: virent8090DEVCR5D00E4KC60(567009),    -- V8R11C00 for CR5D00E4KC60(SBOM) 4-Port 400GBase CFP8 Integrated Line Process Unit(NE5000E LPUI-1T6)
                Add: virent8090DEVCR9D0SFUT48D(562082),    -- V8R11C10 for CR58SFU4TD(SBOM) NE9000-20 Switch Fabric Unit F for Single Chassis(SFU4T-D)
                Add: virent8090DEVCR9D0SFUT48E(562080),    -- V8R11C10 for CR58SFU4TE(SBOM) NE9000-8 Switch Fabric Unit for Single Chassis(SFU4T-E)
                Add: virent8090DEVCR5D00EDNB63(561793),    -- V8R11C10 for CR5D00EDNB63(SBOM) 16-Port 100GBase QSFP28 Integrated Line Process Unit CM(NE5000E LPUI-1T6-CM)
                Add: virent8090DEVCR5D00E4KB61(561794),    -- V8R11C10 for CR5D00E4KB61(SBOM) 4-Port 400GBase QSFP-DD Integrated Line Process Unit CM(NE5000E LPUI-1T6-CM)
                Add: virent8090DEVCR5D00NDNC61(561795),    -- V8R11C10 for CR5D00NDNC61(SBOM) 16-Port 100G OTN/ETH QSFP28 Integrated Line Process Unit(NE5000E LPUI-1T6-CM)
                Add: virent8090DEVCR5D00LRXF61(561792),    -- V8R11C10 for CR5D00LRXF61(SBOM) 72-Port 10GBase LAN/WAN-SFP+ Integrated Line Process Unit CM(NE5000E LPUI-1T6-CM)
                    "

        REVISION    "201811070000Z"
        DESCRIPTION "V8.44,
                        Add:bnameES1D2MCUDC00(659686),      --S9303 main control unit D for v2r13c99
                Add:bnameLE1D2SRUHC0X(659687),      --S9300 main control unit H for v2r13c99
                Add:bnameLE1M2G48TX5S(659688),      --48-port 10/100/1000BASE-T interface card (X5S,RJ45) for v2r13c99
                Add:bnameLE1M2G48TX5E(659689),      --48-port 10/100/1000BASE-T interface card (X5E,RJ45) for v2r13c99
                Add:bnameLE1M2X48SX6S(659690),      --48-port 10GE SFP+ interface card (X6S,SFP+) for v2r13c99
                Add:bnameLE1M2X48SX6E(659691),      --48-port 10GE SFP+ interface card (X6E,SFP+) for v2r13c99
                Add:bnameLE1M2G48SX6S(659692),      --48-port 1000BASE-X interface card (X6S,SFP) for v2r13c99
                Add:bnameLE1M2G48SX6E(659693),      --48-port 1000BASE-X interface card (X6E,SFP) for v2r13c99
                Add:bnameLE2M2X48SX6S(659694),      --48-port 10GE SFP+ interface card (X6S,SFP+) S9310/S9310X  for v2r13c99
                Add:bnameLE2M2X48SX6E(659695),      --48-port 10GE SFP+ interface card (X6E,SFP+) S9310/S9310X  for v2r13c99
                Add:bnameLE2M2X48SX6H(659696),      --48-port 10GE SFP+ interface card (X6H,SFP+) S9310/S9310X  for v2r13c99
                Add:bnameLE1D2MCUDC00(663655),      --S7703 main control unit D for v2r13c99
                Add:bnameES1D2SRUHC0X(663656),      --S7700 main control unit H for v2r13c99
                Add:bnameES1M2G48TX5S(663657),      --48-port 10/100/1000BASE-T interface card (X5S,RJ45) for v2r13c99
                Add:bnameES1M2G48TX5E(663658),      --48-port 10/100/1000BASE-T interface card (X5E,RJ45) for v2r13c99
                Add:bnameEH1D200CMU00V2(663659),      --Centralized Monitoring Board for v2r13c99 for S7700
                Add:bnameES1M2X48SX6S(663660),      --48-port 10GE SFP+ interface card (X6S,SFP+) for v2r13c99
                Add:bnameES1M2X48SX6E(663661),      --48-port 10GE SFP+ interface card (X6E,SFP+) for v2r13c99
                Add:bnameES1M2G48SX6S(663662),      --48-port 1000BASE-X interface card (X6S,SFP) for v2r13c99
                Add:bnameES1M2G48SX6E(663663),      --48-port 1000BASE-X interface card (X6E,SFP) for v2r13c99
                Add:bnameES2M2X48SX6S(663664),      --48-port 10GE SFP+ interface card (X6S,SFP+) 7710 for v2r13c99
                Add:bnameES2M2X48SX6E(663665),      --48-port 10GE SFP+ interface card (X6E,SFP+) 7710 for v2r13c99
                Add:bnameES2M2X48SX6H(663666),      --48-port 10GE SFP+ interface card (X6H,SFP+) 7710 for v2r13c99
                Add:bnameET1M2X48SX6S(700493),      --48-port 10GE SFP+ interface card (X6S,SFP+) for v2r13c99
                Add:bnameET1M2X48SX6E(700494),      --48-port 10GE SFP+ interface card (X6E,SFP+) for v2r13c99
                Add:bnameET1M2X48SX6H(700495),      --48-port 10GE SFP+ interface card (X6H,SFP+) for v2r13c99
                Add:fname8031S1820EC-8G(537271),                --S1820EC-8G           for LSW V2R12C20
                Add:fname8031S1820EC-24G(537272),               --S1820EC-24G          for LSW V2R12C20
                Add:fname8031S5820EC-10P(537273),               --S5820EC-10P          for LSW V2R12C20
                Add:fname8031S5820EC-10P-PWR(537274),           --S5820EC-10P-PWR      for LSW V2R12C20
                Add:fname8031S5820EC-28P(537275),               --S5820EC-28P          for LSW V2R12C20
                Add:fname8031S5820EC-28P-PWR(537276),           --S5820EC-28P-PWR      for LSW V2R12C20
                Add:fname8031S1720-10GF-2P(537277),             --S1720-10GF-2P        for LSW V2R12C20
                Add:fname8031S1720-10GF-PWR-2P(537278),         --S1720-10GF-PWR-2P    for LSW V2R12C20
                Add:fname8031S1720-28GFR-4P(537279),            --S1720-28GFR-4P       for LSW V2R12C20
                Add:fname8031S1720-28GFR-PWR-4P(537280),        --S1720-28GFR-PWR-4P   for LSW V2R12C20
                Add:fname8031S1720-52GFR-4P(537281),            --S1720-52GFR-4P       for LSW V2R12C20
                Add:fname8031S1720-52GFR-PWR-4P(537282),        --S1720-52GFR-PWR-4P   for LSW V2R12C20
                Add:fname8031S5720SV2-28P-LI-AC(537283),        --S5720SV2-28P-LI-AC   for LSW V2R12C20
                Add:fname8031S5720SV2-52P-LI-AC(537284),        --S5720SV2-52P-LI-AC   for LSW V2R12C20
                Add:fnameS6730-54L-HI-48S(537285),              --S6730-54L-HI-48S for LSW V2R13C99
                Add:fnameS6330-54L-HI-48S(537286),              --S6330-54L-HI-48S for LSW V2R13C99
                Add:fnameS6730-30L-HI-24S(537287),              --S6730-30L-HI-24S for LSW V2R13C99
                Add:fnameS6330-30L-HI-24S(537288),              --S6330-30L-HI-24S for LSW V2R13C99
                Add:bname8031S1820EC-8G(537455),                    --S1820EC-8G           for LSW V2R12C20
                Add:bname8031S1820EC-24G(537456),                   --S1820EC-24G          for LSW V2R12C20
                Add:bname8031S5820EC-10P(537457),                   --S5820EC-10P          for LSW V2R12C20
                Add:bname8031S5820EC-10P-PWR(537458),               --S5820EC-10P-PWR      for LSW V2R12C20
                Add:bname8031S5820EC-28P(537459),                   --S5820EC-28P          for LSW V2R12C20
                Add:bname8031S5820EC-28P-PWR(537460),               --S5820EC-28P-PWR      for LSW V2R12C20
                Add:bname8031S1720-10GF-2P(537461),                 --S1720-10GF-2P        for LSW V2R12C20
                Add:bname8031S1720-10GF-PWR-2P(537462),             --S1720-10GF-PWR-2P    for LSW V2R12C20
                Add:bname8031S1720-28GFR-4P(537463),                --S1720-28GFR-4P       for LSW V2R12C20
                Add:bname8031S1720-28GFR-PWR-4P(537464),            --S1720-28GFR-PWR-4P   for LSW V2R12C20
                Add:bname8031S1720-52GFR-4P(537465),                --S1720-52GFR-4P       for LSW V2R12C20
                Add:bname8031S1720-52GFR-PWR-4P(537466),            --S1720-52GFR-PWR-4P   for LSW V2R12C20
                Add:bname8031S5720SV2-28P-LI-AC(537467),            --S5720SV2-28P-LI-AC   for LSW V2R12C20
                Add:bname8031S5720SV2-52P-LI-AC(537468),            --S5720SV2-52P-LI-AC   for LSW V2R12C20
                Add:bnameS6730-54L-HI-48S(537469),                  --S6730-54L-HI-48S for LSW V2R13C99
                Add:bnameS6330-54L-HI-48S(537470),                  --S6330-54L-HI-48S for LSW V2R13C99
                Add:bnameS6730-30L-HI-24S(537471),                  --S6730-30L-HI-24S for LSW V2R13C99
                Add:bnameS6330-30L-HI-24S(537472),                  --S6330-30L-HI-24S for LSW V2R13C99
                Add:subnamePAC600S12CB(536793),              --600W AC power module (back to front,power panel side exhaust) for V2R13C99
                "

        REVISION    "201811011021Z"
        DESCRIPTION "V8.43,
		Add: bnameH801SCUP(156082),              -- MA5800C control board H801SCUP.
                                       Add: bnameH801SCUQ(156083),             -- MA5800C control board H801SCUQ.
		Add: bnameH832CCUE(156084),              -- Master board of MA5616 device
		Add: bnameH831CCMB(156085),   	          -- Master board of MA5818 device
		Add: bnameH831PDMB(156086),   	          -- 500W DC power board(support standby power) of the MA5818 device
		Add: portnameGNSS(811),                         -- bits T8010 add gnss port type.
                                      Add: portnameCLOCK(812),                       -- bits T8010 add clock port type.
                                      Add: portname1PPSTOD(813),                   -- bits T8010 add 1pps-TOD port type.
                                      Add: portnameClockType(814),                  -- bits T8010 add clock port type.
                    "
        REVISION    "201810311021Z"
        DESCRIPTION "V8.42,
            add wlan device
            ADD:fnameWA375DD-CE(692326),             --WLAN new ac ENUM_
                    fnameAP2051DN-L-S(692327),            --WLAN new ac ENUM_
                    fnameAP2051DE-GP(692328),             --WLAN new ac ENUM_
                    fnameAP4050DE-B-S(692329),            --WLAN new ap ENUM_
                    fnameAP3050DE(692330),                   --WLAN new ap ENUM_
                    "

		REVISION    "201810301000Z"
		DESCRIPTION "V6.38,
			 Add: fnameH821MABC-MA5620(561662), -- Virtual frame H821MABC of MA5620(sd5133) device.
			 Add: bnameH825XPUB-MA5620(156090), -- Master board H825XPUB of MA5620(sd5133)device.
			 "
	    REVISION    "201810121708Z"
        DESCRIPTION "V8.40,
				Add:bnamePTN7900TPA1EY8(229510), --TPA1EY8,8-port 25 Gigabit Ethernet Switching Processing Board
				Add:bnamePTN7900TPD1EY8(229495), --TPD1EY8,8-port 25 Gigabit Ethernet Switching Processing Board
				Add:bnamePTN7900TPA1EY16(229496), --TPA1EY16,16-port 25 Gigabit Ethernet Switching Processing Board
				Add:bnamePTN7900TPD1EY16(229497), --TPD1EY16,16-port 25 Gigabit Ethernet Switching Processing Board
				Add:bnamePTN7900TPA1FV4(229498), --TPA1FV4,4-port 50 Gigabit Ethernet Switching Processing Board
				Add:bnamePTN7900TPD1FV4(229499), --TPD1FV4,4-port 50 Gigabit Ethernet Switching Processing Board
				Add:bnamePTN7900TPA1FV8(229500), --TPA1FV8,8-port 50 Gigabit Ethernet Switching Processing Board
				Add:bnamePTN7900TPD1FV8(229501), --TPD1FV8,8-port 50 Gigabit Ethernet Switching Processing Board
				Add:bnamePTN7900TPA2FH2(229502), --TPA2FH2,2-port 100 Gigabit Ethernet Switching Processing Board
				Add:bnamePTN7900TPD2FH2(229503), --TPD2FH2,2-port 100 Gigabit Ethernet Switching Processing Board
				Add:bnamePTN7900TPA1FH4(229504), --TPA1FH4,4-port 100 Gigabit Ethernet Switching Processing Board
				Add:bnamePTN7900TPD1FH4(229505), --TPD1FH4,4-port 100 Gigabit Ethernet Switching Processing Board
				Add:bnamePTN7900TPA1FHD2(229506), --TPA1FHD2,2-port 200 Gigabit Ethernet Switching Processing Board
				Add:bnamePTN7900TPD1FHD2(229507), --TPD1FHD2,2-port 200 Gigabit Ethernet Switching Processing Board
				Add:bnamePTN7900TPD1FHD4(229508), --TPD1FHD4,4-port 200 Gigabit Ethernet Switching Processing Board
        "

       REVISION    "201810111036Z"
        DESCRIPTION "V8.39,
                   Add: virent8090DEVCR5DLPUFT264(562095),   -- v8r11c00 Finished Board,NetEngine5000E,CR59LPUF1T6AB0,1.6T Flexible Card Line Processing Unit A CM(NE5000E LPUF-1T6-A,2 sub-slots)
                       "

        REVISION    "201810091708Z"
        DESCRIPTION "V8.38,
                Add:  subbname8090DEVCR5D00N8NC60(561828), --8-Port 100G OTN/ETH QSFP28 Flexible Card CM(CP1T6,Occupy 1 sub-slot)
                Add:  subbname8090DEVCR5D00N8NC61(561829), --8-Port 100G OTN/ETH QSFP28 Flexible Card(CP1T6,Occupy 1 sub-slot)
        "
                REVISION    "201809271000Z"
        DESCRIPTION "V8.37,
                Modify: fnameCABLE(147527),              -- MDU device CABLE used as remote frame.
                Modify: fnameH821MABCV(561659),          -- Virtual frame H821MABCV of vertical MA5833 device.
                Modify: fnameH821MABCU(561660),          -- Virtual frame H821MABCU of vertical MA5833 device.
                Modify: bnameH822CCKRR(156076),       --  Master board of MA5833 new device.
                Modify: bnameHS33CDAH(156077),        --  MA5833 new sevice board HS33CDAH
                Modify: bnameHS33CDAI(156078),        --  MA5833 new sevice board HS33CDAI
        "

        REVISION    "201809251000Z"
        DESCRIPTION "V8.36,
                Add: fnameATNDEV910C-E(225608),           --ATN910C-E  chassis
                Add: fnameATNDEV910C-DAC(225609),           --ATN910C-D AC  chassis
        "

        REVISION    "201809151000Z"
        DESCRIPTION "V8.35,
                Add: bnameES1D2G48TX5L(663651),      --48-port 100/1000BASE-T interface card (X5L, RJ45) for v2r13
                Add: bnameES1D2G48SX5L(663652),     --48-port 100/1000BASE-X interface card (X5L, SFP) for v2r13
                Add: bnameES1D2G24SX5L(663653),      --24-port 100/1000BASE-X interface card (X5L, SFP) for v2r13
                Add: bnameES1D2X08SX5L(663654),      --8-port 10GE SFP+ interface card (X5L, SFP+) for v2r13
                Add: fnameES1BS7706SP0(663570),      -- S7706 PoE Assembly Chassis add for v2r13
        "

        REVISION    "201809111000Z"
        DESCRIPTION "V8.34,
		Add: fnameBT81BP2HT8010(696832),         --Frame BT81BP2H of the T8010 bits device.
		Add: bnameBT81CPOHT8010(696832),         --main control board of T8010 bits, with one slot.
		Add: bnameBT81CPRHT8010(696833),         --main control board of T8010 bits, with two slots.
		Add: bnameBT81HDOU(696834),              --32-port business board of T8010 bits.
        Add: subbname8090DEVCX6D00NBXFA0(580901),    -- V8R11C00 for CX6D00NBXFA0(SBOM) 12-Port 10G OTN/ETH-SFP+ Flexible Card
        Add: subbname8090DEVCX6D00N2NCA0(580902),    -- V8R11C00 for CX6D00N2NCA0(SBOM) 2-Port 100G OTN/ETH-CFP2 Flexible Card
        Add: virent8090DEVCR5D0SRUAC70(570042),    -- V8R11C00 for  CR5D0SRUAC70(SBOM) Switch and Route Processing Unit A12
        Add: virent8090DEVCR5D0MPUB870(570041),    -- V8R11C00 for  CR5D0MPUB870(SBOM) Main Processing Unit B8
        Add: virent8090DEVCX6DNPU1TM70(675869),    -- V8R11C00 for  CX6DNPU1TM70(SBOM) Network Processing Unit (NPU-1T)
        Add: virent8090DEVCR5DLPUFT070(675815),    -- V8R11C00 for  CR5DLPUFT070(SBOM) Flexible Card Line Processing Unit T(LPUF-1T-T)
        Add: virent8090DEVCR5D00E8NB70(675816),     -- V8R11C00 for  CR5D00E8NB70(SBOM) 8-Port 100GBase-QSFP28 Integrated Line Processing Unit(LPUI-1T-T)
		Add: virent8090DEVCX6DISUFT010(675982),     -- V8R11C10 for CX6DISUFT010(SBOM) Flexible Card Integrated Service Unit(ISUF-1T)
        Add: virent8090DEVCR5DSFUIT27E(567056),    -- V8R10C10 for CR5DSFUIT27E(SBOM) 2Tbps Switch Fabric Unit E(SFUI-2T-E)
        Add: virent8090DEVCR5DSFUIU07F(567055),    -- V8R10C10 for CR5DSFUIU07F(SBOM) 2Tbps Switch Fabric Unit F(SFUI-2T-F)
		Add: virent8090DEVCX6DLPUFK0A0(570064),     -- V8R11C00 for CX6DLPUFK0A0(SBOM) 480G Flexible Card Line Processing Unit C(CX6600 LPUF-480C,2 sub-slots)
		Add: virent8090DEVME0DBSUFT070(675980),     -- V8R11C10 for ME0DBSUFT070(SBOM) Flexible Card Broadband Service Unit(BSUF-1T,2 sub-slots)
		Add: virent8090DEVME0DMSUFT070(675981),     -- V8R11C10 for ME0DMSUFT070(SBOM) Flexible Card Multi Service Unit(MSUF-1T,2 sub-slots)
		"

        REVISION    "201809041000Z"
        DESCRIPTION "V8.33,
        add wlan device
        ADD:fnameAC6508(692321),         --WLAN new ac ENUM_
            fnameAC6805(692322),         --WLAN new ac ENUM_
            fnameAC6507S(692323),        --WLAN new ac ENUM_
            fnameAP4050DE-M(692324),     --WLAN new ap ENUM_
            fnameAP4050DE-M-S(692325),   --WLAN new ap ENUM_
                    "
            REVISION    "201808301000Z"
            DESCRIPTION "V8.32,
                                                            Add: subbname8090DEVCR53P4HF0(677001),	-- 4-port OC-12c/STM-4c POS-SFP Flexible Card
                                                            Add: subbname8090DEVCR5D00E8NB63(537503),    -- 8-Port 100G QSFP28 Flexible Card(CP1T6,Occupy 1 sub-slot)
                                                            Add: subbname8090DEVCR5D00E2KC61(537504),    -- 2-Port 400G CFP8 Flexible Card(CP1T6,Occupy 1 sub-slot)
                                                            Add: subbname8090DEVCR5D00E8NC65(537505),    -- 8-Port 100G CFP2 Flexible Card(CP1T6,Occupy 1 sub-slot)
                                                            Add: subbname8090DEVCR5D00LJXF61(537506),    -- 36-Port 10GBase LAN/WAN-SFP+ Flexible Card(CP1T6,Occupy 1 sub-slot)
                                                            Add: subbname8090DEVCR5D00E4NB63(537507),    -- 4-Port 100GBase QSFP28 Flexible Card CM(CP1T,Occupy 1 sub-slot)
                                                            Add: subbname8090DEVCR5D00LFXF63(537508),    -- 24-Port 10GBase LAN/WAN SFP+ Flexible Card CM(CP1T,Occupy 1 sub-slot)
                                                            Add: subbname8090DEVCR5D00E2NC63(537509),    -- 2-Port 100GBase-CFP2 Flexible Card CM(CP400,Occupy 1 sub-slot)
                                                            Add: subbname8090DEVCR5D00LEXF65(537510),    -- 20-Port 10GBase LAN/WAN-SFP+ Flexible Card CM(CP400,Occupy 1 sub-slot)
                                                            Modify: subbname8090DEVCR5D00E8NC64(537500),    -- 8-Port 100G CFP2 Flexible Card CM(CP1T6,Occupy 1 sub-slot)
                                                            Modify: subbname8090DEVCR5D00E8NC64(537500),    -- 8-Port 100G CFP2 Flexible Card CM(CP1T6,Occupy 1 sub-slot)
                                                            Modify: subbname8090DEVCR5D00E2KC60(537502),    -- 2-Port 400G CFP8 Flexible Card CM(CP1T6,Occupy 1 sub-slot)
                                                            Modify: subbname8090DEVCR5D00LJXF60(225640),       --36-Port 10GBase LAN/WAN-SFP+ Flexible Card CM(CP1T6,Occupy 1 sub-slot)
	                "

            REVISION    "201808061000Z"
            DESCRIPTION "V8.31,
	    		 Add: bnameH901GPHH(148656),              --32*GPON board of MA5800.
	    		 Add: bnameH901MPLE(148657),              --control board of MA5800.
	    		 Add: subbnameH902CKUB(148515),           --Clock subboard of MA5800.
	    		 Add: subbnameH902CKUA(148516),           --Clock subboard of MA5800.
	                "

            REVISION    "201808031000Z"
            DESCRIPTION "V8.30,
	    		 Add: bnameVPQ(156081),              --G.FAST vectoring serial control engine board of the MA5818 device.
	                "

            REVISION    "201808021000Z"
            DESCRIPTION "V8.29,
                         Add: bnameTPJD003CXP00(229494) , --PTN 990
	    Add: bnameTPPMHOSTA000(225440) , --PTN 910E-F
	    Add: bnameTPPMHOSTB000(225441),  --PTN 910E-F
                         Add:vrientNECD00CXPL00(704576),           -- NE05E-S2"
            REVISION    "201807251000Z"
            DESCRIPTION "V8.28,
                         Add: virentANGMHSTD0311(225606),          --ATN 910C-F,ANGM01HSTD,ATN 910C-F DC system,with 6*10GE(o),20*GE/FE(o),4*GE/FE
                         Add: fnameATNDEV910C-F(225607),           --ATN910C-F  chassis"

            REVISION    "201807251000Z"
            DESCRIPTION "V8.27,
                         Add: fname(00ff102a~00ff1058)"

            REVISION    "201807241000Z"
            DESCRIPTION "V8.26,
			  Add: fnameCE885064CQEI(688174),           -- CloudEngine CE8850-64CQ-EI Switch(64-Port 100GE QSFP28)
			  Add: fnameCE686548S8CQEI(688179),         -- CloudEngine CE6865-48S8CQ-EI Switch(48-Port 25GE SFP28,8*100GE QSFP28)
			  Add: bnameCEL18CQFDAM(688286),                -- (YDJC)Manufactured Board,CloudEngine 12800,CEL18CQFDA-M,18-Port-40GE,18-Port-100GE Interface Card(FDA-M,QSFP+,QSFP28)
			  Add: bnameCE686548S8CQEI(688287),             -- Manufactured Board,CloudEngine 6800,CEM48S8CQP04,48-Port 25GE SFP28 Optical,8-Port 100GE QSFP28 Optical Switch Control Unit,1*1
			  Add: bnameCE885064CQEI(688288),               -- Manufactured Board,CloudEngine 8800,CEM64CQP01,64-Port 100GE QSFP28 Optical,2-Port 10GE SFP+ Optical Switch Control Unit,1*1
			  Add: bnameCEL36CQFDX(688290),                 -- Manufactured Board,CloudEngine 12800E,CEL36CQFD-X,36-Port-100GE Interface XGS Card(FD,QSFP28),1*1
			  Add: bnameCESFU08GX(688291),                  -- Manufactured Board,CloudEngine 12800E,CESFU08GX,CE12808E Switch Fabric Unit G,1*1
			  Add: bnameCESFU16GX(688292),                  -- Manufactured Board,CloudEngine 12800E,CESFU16GX,CE12816E Switch Fabric Unit G,1*1
			  Add: bnameCEL36CQFD1(688296),                 -- Manufactured Board,CloudEngine 12800,CE-L36CQ-FD1,36-Port-100GE Interface Card(FD1,QSFP28)
			  Add: bnameCEL36CQSD(688297),                  -- Manufactured Board,CloudEngine 12800,CE-L36CQ-SD,36-Port-100GE Interface Card(SD,QSFP28)
			  Add: addentnamePDU(688129),                -- PDU  Module
			  Add: addentnameDMU(688130),                -- DMU  Module
			  Add: addentnameDACS(688131),               -- DACS  Module
	                "
	    REVISION    "201807131000Z"
            DESCRIPTION "V8.25,
	                 Add: hundredgeOptPort(594),          -- 100GE optical port
	                "
                           REVISION    "201807110000Z"
               DESCRIPTION "V8.24,
                    Add: subbname8090DEVCR56LEXF3(561777),       -- 20-Port 10GBase LAN/WAN-SFP+ Flexible Card(CP400,Occupy 1 sub-slot)
                    Add: subbname8090DEVCR5D00LEXF74(561778),
                    Add: subbname8090DEVCR5D00LEXF73(561779),
                    Add: subbname8090DEVCX6D00LEXF10(561780),
                    Add: subbname8090DEVME0D00LEXF70(561781),
                    Add: subbname8090DEVCR56E2NCC3(561782), -- NE40E X16B,CR56E2NCC3 , 2-Port 100GBase-CFP2 Flexible Card(CP400,Occupy 1 sub-slot)
		                  "

                        REVISION    "201807110000Z"

              DESCRIPTION "V8.23,
		                 fname8090CX6601-14H24Q(675955),                   --Quidway CX6601-14H24Q FRAME for V8R11C00
		                  "

                        REVISION    "201807060000Z"
              DESCRIPTION "V8.22,
		                 Add:virent600DEVCX6P020BKP01(675811),    --CX6602-B Integrated Chassis Components, CX6P020BKP01
		                 Add:virent600DEVCR5B0BKP0393(675812),    --NE40E-M2K-B Integrated Chassis Components, CR5B0BKP0393
		                 Add:virent600DEVCX6B0BKP0393(675813),    --CX600-M2K-B Integrated Chassis Components, CX6B0BKP0393
                         Add:virent600DEVTNRB0BKP0374(675814),    --PTN6900-M2K-B Integrated Chassis Components, TNRB0BKP0374
		                  "

                        REVISION    "201807030000Z"
		      DESCRIPTION "V8.21,
		                 Add:fname8031S5720I-6X-PWH-SI-AC(537270),        --S5720I-6X-PWH-SI-AC for V2R13C00
		                 Add:bname8031S5720I-6X-PWH-SI-AC(537454),        --S5720I-6X-PWH-SI-AC for V2R13C00
		                 Add:subnamePAC1000D5412(536792),                 --1000W AC POWER MODULE for V2R13C00
		                  "

                        REVISION    "201806300000Z"
                                             DESCRIPTION "V8.20,
                                                       Add: virent8090DEVCX6DISUFM012(675810),    -- V8R10C10 for  Flexible Card Integrated Service Unit(ISUF-400)
                                                     Add: virent8090DEVCX6D00E8NC70(675809),    -- V8R10C10 for  8-Port 100GBase-CFP2 Integrated Integrated Service Unit(ISUI-1T)
                                                   "
                         REVISION    "201806290000Z"
		         DESCRIPTION "V8.19,
                         Add: bname(0x00ff8000-0x00ff8018) subbname(0x00ff4000-0x00ff401d)
                         "

			  REVISION    "201806280000Z"
		          DESCRIPTION "V8.18,
			  Add: virent8090DEVCR5DLPUFT261(562089),   -- v8r11c00 NE5000E-20 CR5DLPUFT261(SBOM),2T Flexible Card Line Processing Unit(NE5000E LPUF-2T-A,2 sub-slots)
			  Add: virent8090DEVCR57MPUB6(562090),  --Main Processing Unit B6
			  Add: virent8090DEVCR57SFU2TE(562091), --2T Switch Fabric Unit for Single Chassis (SFU-2T-A)
			  Add: virent8090DEVCR56LPUI1T(562092), --8-Port 100GBase-QSFP28- Integrated Line Process Unit(LPUI-1T) NE40E-X16B
			  Add: virent8090DEVCR5DSFUIT250(562093),   
			  Add: virent8090DEVCR5DSFUIT26H(562094),   
							"

			  REVISION    "201806200000Z"
		      DESCRIPTION "V8.17,
					Add: bnameH806GPFD(146157),        --  16GPON board of MA5600T.
					Add: bnameH901CGUD(148641),        --  8*GE and 10GE combo board of MA5800.
					Add: bnameH901CGUF(148642),        --  16*XG GPON and GPON combo board of MA5800.
					Add: bnameH901FLHF(148645),        --  16*flex-PON board of MA5800.
					Add: bnameH902CSHF(148646),        --  16*XGS GPON and GPON combo board of MA5800.
					Add: bnameH902GPHF(148647),        --  16*10G GPON board of MA5800.
					Add: bnameH902XEHD(148648),        --  8*10G EPON board of MA5800.
					Add: bnameH902NXED(148649),        --  8*Port ETH board of MA5800.
					Add: bnameH903MPLA(148650),        --  control board of MA5800.
					Add: bnameH902MPLB(148651),        --  control board of MA5800.
					Add: bnameH902CIUA(148652),        --  GPIO board of MA5800.
					Add: bnameH902PILA(148653),        --  Power board of MA5800.
					Add: bnameH901GPUF(148654),        --  16*GPON board of MA5800.
					Add: bnameH901NCEB(148655),        --  2*100G service board of MA5800.
							"
              REVISION    "201806190000Z"
              DESCRIPTION "V8.16,
                    Add:bnameLE3D2X22SX2L(659680),      --S9300X 22-Port 10GE SFP+ Interface Card(X2L,SFP+) for v2r12c00
                    Add:bnameLE1D2X24SX2S(659681),      --S9300 24-Port 10GE SFP+ Interface Card(X2S,SFP+) for v2r12c00
                    Add:bnameLE1D2X08SX2E(659682),      --S9300 8-Port 10GE SFP+ Interface Card(X2E,SFP+) for v2r13
                    Add:bnameLE1D2S04SX2E(659683),      --S9300 4-Port 10GE SFP+ Interface and 44-Port GE SFP Interface Card(X2E,SFP+) for v2r13
                    Add:bnameLE1D2G24SX2E(659684),      --S9300 24-Port 100/1000BASE-X Interface Card(X2E,SFP) for v2r13
                    Add:bnaemLE1D2X08SX2H(659685),      --S9300 8-Port 10GE SFP+ Interface Card(X2H,SFP+) for v2r13
                    Add:bnameES1D2G48TX2H(663648),      --48-Port 100/1000BASE-T Interface Card(X2H,RJ45) for v2r13
                    Add:bnameES1D2G48SX2H(663649),      --48-Port 100/1000BASE-X Interface Card(X2H,SFP) for v2r13
                    Add:bnameES1D2X08SX2H(663650),      --8-Port 10GE SFP+ Interface Card(X2H,SFP+) for v2r13
                    Add:bnameET1D2S04SX2E(700489),      --4-Port 10GE SFP+ Interface and 44-Port GE SFP Interface Card(X2E,SFP+) for v2r13
                    Add:bnameET1D2G24SX2E(700490),      --24-Port 100/1000BASE-X Interface Card(X2E,SFP) for v2r13
                    Add:bnameET1D2G48TX2S(700491),      --48-Port 100/1000BASE-T Interface Card(X2S,RJ45) for v2r13
                    Add:bnameET1D2G48SX2S(700492),      --48-Port 100/1000BASE-X Interface Card(X2S,SFP) for v2r13
                    Add:fname8031S5720I-10X-PWH-SI-AC-Sea(537269),         --S5720I-10X-PWH-SI-AC oversea for V2R13C00
                    Add:bname8031S5720I-10X-PWH-SI-AC-Sea(537453),         --S5720I-10X-PWH-SI-AC oversea for V2R13C00
                                      "

               REVISION    "201806120000Z"
               DESCRIPTION "V7.85,
                     Add: subbname8090DEVANKD001EY200(225623),   --2 Channels 25G (SFP28)/2 Channels 10G (SFP+) High Speed Interface Board
                     Add: subbname8090DEVCR5D00E4XF25(225624),   --4-Port 25GBase-SFP28 Physical Interface Card(PIC)
                     Add: subbname8090DEVCR5D00LJXF60(225640),   --36-Port 10GBase LAN/WAN-SFP+ Flexible Card CM(CP1T6,Occupy 1 sub-slot)
                     Add: subbname8090DEVCR5D00LFXF76(537450),    --24-Port 10GBase LAN/WAN-SFP+ Flexible Card A(P481-A)
                     Add: subbname8090DEVCR5D00LFXF75(537451),    --24-Port 10GBase LAN/WAN-SFP+ Flexible Card A(P481-E)
                     Add: subbname8090DEVCX6D00LFXF10(537452),    --24-Port 10GBase LAN/WAN-SFP+ Flexible Card A(S481-A)
                     Add: subbname8090DEVME0D00LFXF70(537453),    --24-Port 10GBase LAN/WAN-SFP+ Flexible Card(BP481)
                     Add: subbname8090DEVCR5D00E2NC78(537454),    --2-Port 100GBase-CFP2 Flexible Card A(P481-E)
                     Add: subbname8090DEVCR5D00E2NC79(537464),    --2-Port 100GBase-CFP2 Flexible Card A(P481-A)
                     Add: subbname8090DEVCX6D00E2NC10(537472),    --2-Port 100GBase-CFP2 Flexible Card A(S481-A)
                     Add: subbname8090DEVME0D00E2NC78(537473),    --2-Port 100GBase-CFP2 Flexible Card(BP481)
                     Add: subbname8090DEVCR5D00E2NF71(537474),    --2-Port 100GBase-QSFP28 Flexible Card A(P481-E)
                     Add: subbname8090DEVCR5D00E2NF72(537475),    --2-Port 100GBase-QSFP28 Flexible Card A(P481-A)
                     Add: subbname8090DEVCX6D00E2NF10(537476),    --2-Port 100GBase-QSFP28 Flexible Card A(S481-A)
                     Add: subbname8090DEVME0D00E2NF71(537477),    --2-Port 100GBase-QSFP28 Flexible Card(BP481)
                     Add: subbname8090DEVCR5D00E8NC64(537500),    -- 8-Port 100G CFP2 Flexible Dauhtger Card
                     Add: subbname8090DEVCR5D00E8NB61(537501),    -- 8-Port 100GBase QSFP28 Flexible Dauhtger Card
                     Add: subbname8090DEVCR5D00E2KC60(537502),    -- 2*400GBase CFP8 Flexible Dauhtger Card
                     Add: subbname8090DEVCX6D0LEXFA12(562730),      -- 20-Port 10GBase LAN/WAN-SFP+ Flexible Card A(S480-A)
                     Add: subbname8090DEVCX68EENEFYFA(562731),   -- 20-Port 100GBase-QSFP28 + 24-Port 25GBase-Y-SFP+ A
                     Add: subbname8090DEVCR58E4K4NA0(562732),   -- 4-Port 400GBase CFP8 + 4-Port 100GBase QSFP28 Fixed Card
                     Add:subbname8090DEVCX6D0E2NCA12(562733),      -- 2-Port 100GBase-CFP2 Flexible Card A(S401-A)
                     Add: subbname8090DEVCR5D0E2NFH70(562734),      -- 2-Port 100GBase-QSFP28 Flexible Card H(P400-H)
                           "


        REVISION    "201805240000Z"
        DESCRIPTION "V8.14,
               Modify: fname8090CX6602(675944),    -- CX6602-A -> CX6602
               Modify: virent600DEVCX6P02ABAS00(675938),    -- CX6602-A -> CX6602
               Modify: virent600DEVCX6P02ABAS01(675939),    -- CX6602-A -> CX6602
               Modify: virent600DEVCX6B0BKP0292(675940),    -- CX6602-A -> CX6602
               Add:virent8090DEVCR9DLPUFT281(675808),     -- V8R10C10 2T for CR9DLPUFT281(SBOM) Flexible Card Line Processing Unit B(LPUF-2T-B,2 sub-slots)
               Add:subbname8090DEVCR5D00LMXF7P(154895),    --V8R10C10 for CR5D00LMXF7P(SBOM) 48-Port 10GBase LAN/WAN-SFP+ Integrated Line Processing Unit CM(LPUI-480-CM)
               Add:subbname8090DEVCR5DE2NLFX7P(154896),    --V8R10C10 for  CR5DE2NLFX7P(SBOM) 2-Port 100GBase-CFP2 + 24-Port 10GBase LAN/WAN-SFP+ Integrated Line Processing Unit CM(LPUI-480-CM)
               Add:virent8090DEVCR5D0SRUAB73(570062),     -- V8R11C00 for CR5D0SRUAB73(SBOM) Switch and Route Processing Unit A11
               Add:virent8090DEVME0D0SRUAB70(570063),     -- V8R11C00 for ME0D0SRUAB70(SBOM) Switch and Route Processing Unit A11
               Add:virent8090DEVCR5DEKBEBX7B(675776),    -- V8R11C00 for  CR5DEKBEBX7B(SBOM) 1-Port 100GBase-QSFP28 + 12-Port 10GBase LAN/WAN-SFP+ Integrated Line Processing Unit B(LPUI-241-B)
               Add:virent8090DEVCX6DISUFF110(675777),    -- V8R11C00 for  CX6DISUFF110(SBOM) Flexible Card Line Processing Unit(ISUF-241)
               Add:virent8090DEVCX6DISUFF11R(675778),    -- V8R11C00 for  CX6DISUFF11R(SBOM) Flexible Card Line Processing Unit(ISUF-241-R)
               Add:virent8090DEVCX6DF1E2NC10(675779),    -- V8R11C00 for  CX6DF1E2NC10(SBOM) 2-Port 100GBase-CFP2 Integrated Line Processing Unit (ISUI-241)
               Add:virent8090DEVCX6DF1E2NB10(675780),    -- V8R11C00 for  CX6DF1E2NB10(SBOM) 2-Port 100GBase-QSFP28 Integrated Line Processing Unit (ISUI-241)
               Add:virent8090DEVCX6DF1EFXC10(675781),    -- V8R11C00 for  CX6DF1EFXC10(SBOM) 24-Port 10GBase LAN/WAN-SFP+ Integrated Line Processing Unit (ISUI-241)
               Add:virent8090DEVCX6DE1KEBX10(675782),    -- V8R11C00 for  CX6DE1KEBX10(SBOM) 1-Port 100GBase-CFP2 + 12-Port 10GBase LAN/WAN-SFP+ Integrated Line Processing Unit (ISUI-241)
               Add:virent8090DEVCX6DEKBEBX10(675783),    -- V8R11C00 for  CX6DEKBEBX10(SBOM) 1-Port 100GBase-QSFP28 + 12-Port 10GBase LAN/WAN-SFP+ Integrated Line Processing Unit (ISUI-241)
               Add:virent8090DEVCX6DF1E2NC1B(675784),    -- V8R11C00 for  CX6DF1E2NC1B(SBOM) 2-Port 100GBase-CFP2 Integrated Line Processing Unit B(ISUI-241-B)
               Add:virent8090DEVCR5DLPUFF170(675785),    -- V8R11C00 for  CR5DLPUFF170(SBOM) Flexible Card Line Processing Unit(LPUF-241)
               Add:virent8090DEVCR5DLPUFF17R(675786),    -- V8R11C00 for  CR5DLPUFF17R(SBOM) Flexible Card Line Processing Unit(LPUF-241-R)
               Add:virent8090DEVCR5DL5XEFG7L(675805),    -- for V800R011C00 CR5DL5XEFG7L(SBOM),5-Port 10GBase LAN/WAN-SFP+ + 24-Port 100/1000Base-X-SFP Integrated Line Processing Unit L(LPUI-120-L)
               Add:virent8090DEVCR5DLPUFF17E(564928),     --CR5DLPUFF17E  Flexible Card Line Processing Unit(LPUF-241-E)
               Add:virent8090DEVCR5DLPUFF17Q(564929),     --CR5DLPUFF17Q  Flexible Card Line Processing Unit(LPUF-241-ER)
               Add:virent8090DEVME0DBSUFF073(675806),     --ME0DBSUFF073  Flexible Card Multi Service Unit(BSUF-241,2 sub-slots)
               Add:virent8090DEVME0DBSUFF072(675807),     --ME0DBSUFF072  Flexible Card Multi Service Unit(BSUF-241-R,2 sub-slots)
               Add:virent8090DEVCX6D0SRUA910(564932),    -- V8R11C00 for CX6D0SRUA910(SBOM), Switch and Route Processing Unit A9(16G Memory)
               Add:virent8090DEVCX6DSFUIT01C(564933),    -- V8R11C00 for CX6DSFUIT01C(SBOM) 1Tbps Switch Fabric Unit C(SFUI-1T-C)
               Add:virent8090DEVCX6DSFUIT01B(564934),    -- V8R11C00 for CX6DSFUIT01B(SBOM), 1Tbps Switch Fabric Unit B(SFUI-1T-B)
               Add:virent8090DEVCR5D0SRUAC7A(675766),    -- V8R11C00 for  CR5D0SRUAC7A(SBOM) Switch and Route Processing Unit A12
               Add:virent8090DEVCX6D0SRUAC7A(675767),    -- V8R11C00 for  CX6D0SRUAC7A(SBOM) Switch and Route Processing Unit A12
               Add:virent8090DEVTNRD0SRUAC70(675768),    -- V8R11C00 for  TNRD0SRUAC70(SBOM) Switch and Route Processing Unit A12
               Add:virent8090DEVCX6D0SRUAC10(675769),    -- V8R11C00 for  CX6D0SRUAC10(SBOM) Switch and Route Processing Unit A12
               Add:virent8090DEVME0D0SRUAC7A(675770),    -- V8R11C00 for  ME0D0SRUAC7A(SBOM) Switch and Route Processing Unit A12
               Add:virent8090DEVCR5DSFUFK070(675771),    -- V8R11C00 for  CR5DSFUFK070(SBOM) 400Gbps Switch Fabric Unit F(SFUI-400-F)
               Add:virent8090DEVCX6D0SFUF870(675772),    -- V8R11C00 for  CX6D0SFUF870(SBOM) 400Gbps Switch Fabric Unit F(SFUI-400-F)
               Add:virent8090DEVTNRDSFUFK070(675773),    -- V8R11C00 for  TNRDSFUFK070(SBOM) 400Gbps Switch Fabric Unit F(SFUI-400-F)
               Add:virent8090DEVCX6DSFUIF070(675774),    -- V8R11C00 for  CX6DSFUIF070(SBOM) 400Gbps Switch Fabric Unit F(SFUI-400-F)
               Add:virent8090DEVME0DSFUIF070(675775),    -- V8R11C00 for  ME0DSFUIF070(SBOM) 400Gbps Switch Fabric Unit F(SFUI-400-F)
               Add:virent8090DEVCR5DF1E2NC70(675796),    -- V8R11C00 for  CR5DF1E2NC70(SBOM) 2-Port 100GBase-CFP2 Integrated Line Processing Unit (LPUI-241)
               Add:virent8090DEVCR5DF1E2NB70(675797),    -- V8R11C00 for  CR5DF1E2NB70(SBOM) 2-Port 100GBase-QSFP28 Integrated Line Processing Unit (LPUI-241)
               Add:virent8090DEVCR5DF1EFXC70(675798),    -- V8R11C00 for  CR5DF1EFXC70(SBOM) 24-Port 10GBase LAN/WAN-SFP+ Integrated Line Processing Unit (LPUI-241)
               Add:virent8090DEVCR5DE1KEBX70(675799),    -- V8R11C00 for  CR5DE1KEBX70(SBOM) 1-Port 100GBase-CFP2 + 12-Port 10GBase LAN/WAN-SFP+ Integrated Line Processing Unit (LPUI-241)
               Add:virent8090DEVCR5DEKBEBX70(675800),    -- V8R11C00 for  CR5DEKBEBX70(SBOM) 1-Port 100GBase-QSFP28 + 12-Port 10GBase LAN/WAN-SFP+ Integrated Line Processing Unit (LPUI-241)
               Add:virent8090DEVCR5DF1E2NC7B(675801),    -- V8R11C00 for  CR5DF1E2NC7B(SBOM) 2-Port 100GBase-CFP2 Integrated Line Processing Unit B(LPUI-241-B)
               Add:virent8090DEVCR5DF1E2NB7B(675802),    -- V8R11C00 for  CR5DF1E2NB7B(SBOM) 2-Port 100GBase-QSFP28 Integrated Line Processing Unit B(LPUI-241-B)
               Add:virent8090DEVCR5DF1EFXC7B(675803),    -- V8R11C00 for  CR5DF1EFXC7B(SBOM) 24-Port 10GBase LAN/WAN-SFP+ Integrated Line Processing Unit B(LPUI-241-B)
               Add:virent8090DEVCR5DE1KEBX7B(675804),    -- V8R11C00 for  CR5DE1KEBX7B(SBOM) 1-Port 100GBase-CFP2 + 12-Port 10GBase LAN/WAN-SFP+ Integrated Line Processing Unit B(LPUI-241-B)
               Add:virent8090DEVCX6DF1E2NB1B(675787),    -- V8R11C00 for  CX6DF1E2NB1B(SBOM) 2-Port 100GBase-QSFP28 Integrated Line Processing Unit B(ISUI-241-B)
               Add:virent8090DEVCX6DF1EFXC1B(675788),    -- V8R11C00 for  CX6DF1EFXC1B(SBOM) 24-Port 10GBase LAN/WAN-SFP+ Integrated Line Processing Unit B(ISUI-241-B)
               Add:virent8090DEVCX6DE1KEBX1B(675789),    -- V8R11C00 for  CX6DE1KEBX1B(SBOM) 1-Port 100GBase-CFP2 + 12-Port 10GBase LAN/WAN-SFP+ Integrated Line Processing Unit B(ISUI-241-B)
               Add:virent8090DEVCX6DEKBEBX1B(675790),    -- V8R11C00 for  CX6DEKBEBX1B(SBOM) 1-Port 100GBase-QSFP28 + 12-Port 10GBase LAN/WAN-SFP+ Integrated Line Processing Unit B(ISUI-241-B)
               Add:virent8090DEVCR5DLPUFF273(675791),    -- V8R11C00 for  CR5DLPUFF273(SBOM) Flexible Card Line Processing Unit(LPUF-481)
               Add:virent8090DEVCR5DLPUFF272(675792),    -- V8R11C00 for  CR5DLPUFF272(SBOM) Flexible Card Line Processing Unit(LPUF-481-E)
               Add:virent8090DEVCX6DISUFF210(675793),    -- V8R11C00 for  CX6DISUFF210(SBOM) Flexible Card Line Processing Unit(ISUF-481)
               Add:virent8090DEVME0DBSUFM072(675794),    -- V8R11C00 for  ME0DBSUFM072(SBOM) Flexible Card Broadband Service Unit(BSUF-481,2 sub-slots)
               Add:virent8090DEVCR5DBSUIM070(675795),    -- V8R11C00 for  CR5DBSUIM070(SBOM) Integrated Broadband Service Unit(BSUI-481-E)
               Add:virent8090DEVCR5D0MPUB772(675756),    -- V8R11C00 for  CR5D0MPUB772(SBOM) Main Processing Unit B7
               Add:virent8090DEVCX6D0MPUB772(675757),    -- V8R11C00 for  CX6D0MPUB772(SBOM) Main Processing Unit B7
               Add:virent8090DEVTNRD0MPUB770(675758),    -- V8R11C00 for  TNRD0MPUB770(SBOM) Main Processing Unit B7
               Add:virent8090DEVCX6D0MPUB710(675759),    -- V8R11C00 for  CX6D0MPUB710(SBOM) Main Processing Unit B7
               Add:virent8090DEVME0D0MPUB770(675760),    -- V8R11C00 for  ME0D0MPUB770(SBOM) Main Processing Unit B7
               Add:virent8090DEVCR5DSFUGK070(675761),    -- V8R11C00 for  CR5DSFUGK070(SBOM) 400Gbps Switch Fabric Unit G(SFUI-400-G)
               Add:virent8090DEVCX6DSFUGK070(675762),    -- V8R11C00 for  CX6DSFUGK070(SBOM) 400Gbps Switch Fabric Unit G(SFUI-400-G)
               Add:virent8090DEVTNRDSFUGK070(675763),    -- V8R11C00 for  TNRDSFUGK070(SBOM) 400Gbps Switch Fabric Unit G(SFUI-400-G)
               Add:virent8090DEVCX6DSFUIG010(675764),    -- V8R11C00 for  CX6DSFUIG010(SBOM) 400Gbps Switch Fabric Unit G(SFUI-400-G)
               Add:virent8090DEVME0DSFUGK070(675765),    -- V8R11C00 for  ME0DSFUGK070(SBOM) 400Gbps Switch Fabric Unit G(SFUI-400-G)
                   "

        REVISION    "201805240000Z"
        DESCRIPTION "V8.13,
               Add:fname8031S1600-8(537248),                   --S1600-8 for lsw V2R12C10
               Add:fname8031S1600-16(537249),                  --S1600-16 for lsw V2R12C10
               Add:fname8031S1600-24(537250),                  --S1600-24 for lsw V2R12C10
               Add:fname8031S2600-10P(537251),                 --S2600-10P for lsw V2R12C10
               Add:fname8031S2600-10P-PWR(537252),             --S2600-10P-PWR for lsw V2R12C10
               Add:fname8031S2600-28P(537253),                 --S2600-28P for lsw V2R12C10
               Add:fname8031S2600-28P-PWR(537254),             --S2600-28P-PWR for lsw V2R12C10
               Add:fname8031S3600-28P(537255),                 --S3600-28P for lsw V2R12C10
               Add:fname8031S3600-28P-PWR(537256),             --S3600-28P-PWR for lsw V2R12C10
               Add:fname8031S3600-52P(537257),                 --S3600-52P for lsw V2R12C10
               Add:fname8031S3600-52P-PWR(537258),             --S3600-52P-PWR for lsw V2R12C10
               Add:fname8031S1700-16-AC(537259),               --S1700-16-AC for lsw V2R12C10
               Add:fname8031S1700-24R(537260),                 --S1700-24R for lsw V2R12C10
               Add:fname8031S5330-60C-HI-48S(537261),          --S5330-60C-HI-48S for lsw V2R13C00
               Add:fname8031S5330-36C-HI-24S(537262),          --S5330-36C-HI-24S for lsw V2R13C00
               Add:fname8031S5720-52X-LI-48S-AC(537263),       --S5720-52X-LI-48S-AC for lsw V2R13C00
               Add:fname8031S5320-52X-LI-48S-AC(537264),       --S5320-52X-LI-48S-AC for lsw V2R13C00
               Add:fname8031S5320-52X-LI-48S-DC(537265),       --S5320-52X-LI-48S-DC for lsw V2R13C00
               Add:fname8031S5320-52X-SI-48S(537266),          --S5320-52X-SI-48S for lsw V2R13C00
               Add:fname8031S5720-52X-SI-48S(537267),          --S5720-52X-SI-48S for lsw V2R13C00
               Add:bname8031S1600-8(537432),               -- Real name s1700-8G-AC               for LSW V2R12C10
               Add:bname8031S1600-16(537433),              -- Real name s1700-16G                 for LSW V2R12C10
               Add:bname8031S1600-24(537434),              -- Real name s1724G-AC                 for LSW V2R12C10
               Add:bname8031S2600-10P(537435),             -- Real name s1720-10GW-2P             for LSW V2R12C10
               Add:bname8031S2600-10P-PWR(537436),         -- Real name s1720-10GW-PWR-2P         for LSW V2R12C10
               Add:bname8031S2600-28P(537437),             -- Real name s1720-28GWR-4P            for LSW V2R12C10
               Add:bname8031S2600-28P-PWR(537438),         -- Real name s1720-28GWR-PWR-4P        for LSW V2R12C10
               Add:bname8031S3600-28P(537439),             -- Real name s1720-28GWR-4P-E          for LSW V2R12C10
               Add:bname8031S3600-28P-PWR(537440),         -- Real name s1720-28GWR-PWR-4P-E      for LSW V2R12C10
               Add:bname8031S3600-52P(537441),             -- Real name s1720-52GWR-4P-E          for LSW V2R12C10
               Add:bname8031S3600-52P-PWR(537442),         -- Real name s1720-52GWR-PWR-4P-E9     for LSW V2R12C10
               Add:bname8031S1700-16-AC(537443),           -- Real name s1700-24-AC               for LSW V2R12C10
               Add:bname8031S1700-24R(537444),             -- Real name s1700-24-AC               for LSW V2R12C10
               Add:bname8031S5330-60C-HI-48S(537445),             --S5330-60C-HI-48S for V2R13C00
               Add:bname8031S5330-36C-HI-24S(537446),             --S5330-36C-HI-24S for V2R13C00
               Add:bname8031S5720-52X-LI-48S-AC(537447),          --S5720-52X-LI-48S-AC for V2R13C00
               Add:bname8031S5320-52X-LI-48S-AC(537448),          --S5320-52X-LI-48S-AC for V2R13C00
               Add:bname8031S5320-52X-LI-48S-DC(537449),          --S5320-52X-LI-48S-DC for V2R13C00
               Add:bname8031S5320-52X-SI-48S(537450),             --S5320-52X-SI-48S for V2R13C00
               Add:bname8031S5720-52X-SI-48S(537451),             --S5720-52X-SI-48S for V2R13C00
               Add:bnameEF1D2G24SSA0(712714),                  -- s7900 24-Port 100/1000BASE-X Interface Card(SA,SFP) for v2r12c10
               Add:bnameEF1D2G24TFA0(712715),                  -- s7900 24-Port 100/1000BASE-X Interface Card(SA,RJ45) for v2r12c10
               Add:fname8031S6320-26Q-LI-24S(537268),                 --S6320-26Q-LI-24S for lsw V2R12C00
               Add:bname8031S6320-26Q-LI-24S(537452),                --S6320-26Q-LI-24S for V2R12C00
                   "

        REVISION    "201805220000Z"
        DESCRIPTION "V8.12,
                Add: bname8090DEVPSU1200A(561235),        -- PSU1200A AC Power Module
                Add: bname8090DEVPSU1600A(561236),        -- PSU1600A AC Power Module
                Add: bname8090DEVPSU2400A(561237),        -- PSU2400A AC Power Module
                "

        REVISION    "201805180000Z"
        DESCRIPTION "V8.11,
                Add: fnameH821MABC-MA5626(561661),  -- Virtual frame H821MABC of MA5626(sd5133) device.
                Add: bnameH825XPUB-MA5626(155720), -- Master board H825XPUB of MA5626(sd5133)device.
                Add: bnameH821EPFA-MA5626(155721), -- 24FE Board H821EPFA of MA5626(sd5133).
                Add: bnameH821EPFB-MA5626(155722), -- 16FE Board H821EPFB of MA5626(sd5133).
                Add: bnameH821EPFD-MA5626(155723), -- 8FE  Board H821EPFD of MA5626(sd5133).
                "

        REVISION    "201805120000Z"
        DESCRIPTION "V8.10,
                 Add: bnameH902XSHD(148644),        --  8*10G GPON board of MA5800.
                 Add: bnameH902TWHD(148643),        --  8*10G GPON board of MA5800.
				 "

        REVISION    "201805100000Z"
        DESCRIPTION "V8.09,
	Add: AC600EC AP100EC AP200EC AP300EC
                   "

        REVISION    "201805020000Z"
        DESCRIPTION "V8.08,
                Add:fname8031S5730-44C-HI-24S(537242),          --02351XFR S5730-44C-HI-24S     for lsw v2r13c00
                Add:fname8031S5730-60C-HI-48S(537243),          --02351XFS S5730-60C-HI-48S     for lsw v2r13c00
                Add:fname8031S5730-68C-HI-48S(537244),          --02351XFT S5730-68C-HI-48S     for lsw v2r13c00
                Add:fname8031S5730-36C-HI-24S(537245),          --02351XFQ S5730-36C-HI-24S     for lsw v2r13c00
                Add:fname8031S5720I-12X-PWH-SI-AC(537246),      --98010811 S5720I-12X-PWH-SI-AC for lsw v2r13c00
                Add:fname8031S5720I-10X-PWH-SI-AC(537247),      --S5720I-10X-PWH-SI-AC for lsw v2r13c00
                Add:fnameES1BS7706SP1(663567),          -- Quidway S7706 FRAME
                Add:fnameES1BS7703SP0(663568),          -- Quidway S7703 FRAME
                Add:fnameES1BS7703EP0(663569),          -- Quidway S7703 FRAME
                Add:fnameET1BS12708S0(700420),               -- HUAWEI S12708 FRAME
                Add:fnameET1BS12712S0(700421),               -- HUAWEI S12712 FRAME
                Add:fnameET1BS12703S0(700422),               -- HUAWEI S12703 FRAME
                Add:bname8031S5730-44C-HI-24S(537426),            --02351XFR S5730-44C-HI-24S     for lsw v2r13c00
                Add:bname8031S5730-60C-HI-48S(537427),            --02351XFS S5730-60C-HI-48S     for lsw v2r13c00
                Add:bname8031S5730-68C-HI-48S(537428),            --02351XFT S5730-68C-HI-48S     for lsw v2r13c00
                Add:bname8031S5730-36C-HI-24S(537429),            --02351XFQ S5730-36C-HI-24S     for lsw v2r13c00
                Add:bname8031S5720I-12X-PWH-SI-AC(537430),        --98010811 S5720I-12X-PWH-SI-AC for lsw v2r13c00
                Add:bname8031S5720I-10X-PWH-SI-AC(537431),        --S5720I-10X-PWH-SI-AC for lsw v2r13c00
                Add:bnmaeLE1D2G48TX2S(659671),      --S9300 48-Port 100/1000BASE-T Interface Card(X2S,RJ45) for v2r13
                Add:bnameLE3D2G48TX2L(659672),      --S9300X 48-Port 100/1000BASE-T Interface Card(X2L,RJ45) for v2r13
                Add:bnameLE1D2G48TX2E(659673),      --S9300 48-Port 100/1000BASE-T Interface Card(X2E,RJ45) for v2r13
                Add:bnameLE1D2G48TX2H(659674),      --S9300 48-Port 100/1000BASE-T Interface Card(X2H,RJ45) for v2r13
                Add:bnameLE1D2G48SX2S(659675),      --S9300 48-Port 100/1000BASE-X Interface Card(X2S,SFP) for v2r13
                Add:bnameLE1D2G48SX2E(659676),      --S9300 48-Port 100/1000BASE-X Interface Card(X2E,SFP) for v2r13
                Add:bnameLE1D2G48SX2H(659677),      --S9300 48-Port 100/1000BASE-X Interface Card(X2H,SFP) for v2r13
                Add:bnameLE3D2G48SX2L(659678),      --S9300X 48-Port 100/1000BASE-X Interface Card(X2L,SFP) for v2r13
                Add:bnameLE1D2MCUBC00(659679),      --S9303,Main Processing Unit B(Optional clock) for v2r13
                Add:bnameES1D2G48VX2S(663635),      --48-Port 100/1000BASE-T POE Interface Card(X2S,RJ45,POE++) for v2r13
                Add:bnameES1D2G48VX2E(663636),      --48-Port 100/1000BASE-T POE Interface Card(X2E,RJ45,POE++) for v2r13
                Add:bnameES1D2G48TX2S(663637),      --48-Port 100/1000BASE-T Interface Card(X2S,RJ45) for v2r13
                Add:bnameES1D2G48TX2E(663638),      --48-Port 100/1000BASE-T Interface Card(X2E,RJ45) for v2r13
                Add:bnameES1D2G48SX2S(663639),      --48-Port 100/1000BASE-X Interface Card(X2S,SFP)  for v2r13
                Add:bnameES1D2G48SX2E(663640),      --48-Port 100/1000BASE-X Interface Card(X2E,SFP)  for v2r13
                Add:bnameES1D2S04SX2S(663641),      --4-Port 10GE SFP+ Interface and 44-Port GE SFP Interface Card(X2S,SFP+) for v2r13
                Add:bnameES1D2S04SX2E(663642),      --4-Port 10GE SFP+ Interface and 44-Port GE SFP Interface Card(X2E,SFP+) for v2r13
                Add:bnameES1D2G24SX2S(663643),      --24-Port 100/1000BASE-X Interface Card(X2S,SFP) for v2r13
                Add:bnameES1D2G24SX2E(663644),      --24-Port 100/1000BASE-X Interface Card(X2E,SFP) for v2r13
                Add:bnameES1D2X08SX2S(663645),      --8-Port 10GE SFP+ Interface Card(X2S,SFP+) for v2r13
                Add:bnameES1D2X08SX2E(663646),      --8-Port 10GE SFP+ Interface Card(X2E,SFP+) for v2r13
                Add:bnameES1D2MCUBC00(663647),      --S7703,Main Processing Unit B(Optional clock) for v2r13
                Add:bnameET1D2SFUH000(700479),             --S12708/S12712,Switch Fabric Unit H for v2r13
                Add:bnameET1D2C32HEC0(700480),             --S12708/S12712,32-Port 100GE QSFP28 Interface Card(EC,QSFP28) for v2r13
                Add:bnameET1D2L32QEC0(700481),             --S12708/S12712,32-Port 40GE QSFP+ Interface Card(EC,QSFP+) for v2r13
                Add:bnameET1D2MPUHC00(700482),             --S12704/S12708/S12712,Main Processing Unit H(Optional clock) for v2r13
                Add:bnameET1D2G48TX2E(700483),             --48-Port 100/1000BASE-T Interface Card(X2E,RJ45) for v2r13
                Add:bnameET1D2G48TX2H(700484),             --48-Port 100/1000BASE-T Interface Card(X2H,RJ45) for v2r13
                Add:bnameET1D2G48SX2E(700485),             --48-Port 100/1000BASE-X Interface Card(X2E,SFP) for v2r13
                Add:bnameET1D2G48SX2H(700486),             --48-Port 100/1000BASE-X Interface Card(X2H,SFP) for v2r13
                Add:bnameET1D2X08SX2E(700487),             --8-Port 10GE SFP+ Interface Card(X2E,SFP+) for v2r13
                Add:bnameET1D2X08SX2H(700488),             --8-Port 10GE SFP+ Interface Card(X2H,SFP+) for v2r13
                     "

        REVISION    "201804190000Z"
        DESCRIPTION "V8.07,
	Add: subnameLND2XE2S(708627),           -- 2 Channels 10GE Optical Interface Board(SFP+)
                   "

        REVISION    "201804161000Z"
        DESCRIPTION "V8.06,
               Add:virent8090DEVCR5D0MPUK570(675954),   -- for V800R010C10 CR5D0MPUK570(SBOM), Main Processing Unit K1A
               Add:virent600DEVCX6B0BKP0392(675950),    --V8R11C00 CX600-F1A-14H24Q CX6B0BKP0392(SBOM), F1A-14H24Q
               Add:virent600DEVCR5B0BKP0392(675951),    --V8R11C00 NE40E-F1A-14H24Q CR5B0BKP0392(SBOM), F1A-14H24Q
               Add:virent600DEVTNRB0BKP0391(675952),    --V8R11C00 PTN6900-F1A-14H24Q TNRB0BKP0391(SBOM), F1A-14H24Q
               Add:virent600DEVCX6P010BKP90(675953)     --V8R11C00 CX6601-14H24Q CX6P010BKP90(SBOM), F1A-14H24Q
               Add:fnamePTN6900-M2K(675945),                  --Quidway PTN6900-M2K FRAME for V8R11C00
               Add:fname8090NE40E-M8A-AC(675946),             --Quidway NE40E-M8A-AC FRAME for V8R10C10
               Add:fname8090NE40E-M8A-DC(675947),             --Quidway NE40E-M8A-DC FRAME for V8R10C10
               Add:fname8090NE40E-M16A(675948),               --Quidway NE40E-M16A FRAME for V8R10C10
               Add:fname8031CX600-M2K-B(675949),              --Quidway CX600-M2K-B FRAME for V8R11C00
               Add:fname8090NE40E-M2K-B(675950),              --Quidway NE40E-M2K-B FRAME for V8R11C00
               Add:fname8090CX6602-B(675951),                 --Quidway CX6602-B FRAME for V8R11C00
               Add:fnamePTN6900-M2K-B(675952),                --Quidway PTN6900-M2K-B FRAME for V8R11C00
               Add:fname8031CX600-F1A-14H24Q(675953),                --Quidway CX600-F1A-14H24Q FRAME for V8R11C00
               Add:fname8090NE40E-F1A-14H24Q(675954),                --Quidway NE40E-F1A-14H24Q FRAME for V8R11C00
               Add:fname8090CX6601-14H24Q(675955),                   --Quidway CX6601-14H24Q FRAME for V8R11C00
               Add:fnamePTN6900-F1A-14H24Q(675956),                  --Quidway PTN6900-F1A-14H24Q FRAME for V8R11C00
               Add:fname8090CX600-X2-M16B(675957),            --Quidway CX600-M2K-B FRAME for V8R11C00
               Add:fname8090NE40E-X2-M16B(675958),            --Quidway NE40E-X2-M16B FRAME for V8R11C00
               Add:fname8090NE20E-S16B(675959),               --Quidway NE20E-S16B FRAME for V8R11C00
               Add:fname8090PTN6900-2-M16B(675960)            --Quidway PTN6900-2-M16B FRAME for V8R11C00
                     "

        REVISION    "201804091000Z"
        DESCRIPTION "V8.05,
                     Add:bnamePTN7900TPD1CQ1(229486), --TPD1CQ1,1 Channels STM-4 CES Optical Interface board ,1*1
	Add:bnamePTN7900TPD1CO1(229487), --TPD1CO1,1 Channels STM-4 CES Optical Interface board ,1*1
	Add:fnamePTN7900TPE1CHASSIS(229488),   --PTN 7900E-24 Integrated Chassis Components
	Add:fnamePTN7900TPF1CHASSIS(229489),   --PTN 7900E-12 Integrated Chassis Components
	Add:bnamePTN7900TPD1PSU(229490), --TPD1PSU,Power Subboard
	Add:bnamePTN7900TPF1XCS(229491), --TPF1XCS,Switch Fabric Unit,1*1
	Add:virentPTN7900TPE1VXCS(229492), --TPE1VXCS,Switch Fabric Unit,1*1
	Add:virentPTN7900TPF1VXCS(229493), --TPF1VXCS,Switch Fabric Unit,1*1
                     "

        REVISION    "201804021000Z"
        DESCRIPTION "V8.04,
                     Add: bnameH801XEUD(146156),         --  8-port 10G EPON interface board of MA5600T.
                     "

        REVISION    "201803311400Z"
        DESCRIPTION "V8.03,
                   Add: virent8090DEVCR9D00EPXF8L(562077),   -- v8r10c10 NE9000 CR58LPU1TCB for CR9D00EPXF8L(SBOM), 60-Port 10GBase LAN/WAN-SFP+ Integrated Line Process Unit L(LPUI-1T-L)
                   Add: virent8090DEVCR5DLPUFT261(562089),   -- v8r11c00 NE5000E-20 CR5DLPUFT261(SBOM),2T Flexible Card Line Processing Unit(NE5000E LPUF-2T-A,2 sub-slots)
                       "
        REVISION    "201803311000Z"
        DESCRIPTION "V8.02,
                    Add: subbname8090DEVCR58EANBA1(537448),       --10-Port 100GBase QSFP28 MACsec fixed Card
                    Add: subbname8090DEVCR9D00LFXF81(537449),    --24-Port 1000M/10GBase LAN/WAN-SFP+ Flexible Card-C
                    "
        REVISION    "201803231000Z"

        DESCRIPTION "V8.01,
                    Add: bnameH82EEFUG-DE16(156080),   --Master board of MA5811S-DE16-G5 device.
                    "
        REVISION    "201803171700Z"

        DESCRIPTION "V8.00,
                    Add:  bnameH822CCKRR(156076),      --  MA5633 mainboard H822CCKRR
                    Add:  bnameHS33CDAH(156077),       --  MA5633 bboard    HS33CDAH
                    Add:  bnameHS33CDAI(156078),       --  MA5633 bboard    HS33CDAI
                    Add:  fnameH821MABCV(561659),      --  MA5633 new frame H821MABCV
                    Add:  fnameH821MABCU(561660),      --  MA5633 new frame H821MABCU
                    "
        REVISION    "201803131000Z"

        DESCRIPTION "V7.99,
	add wlan device
	ADD: fnameAC6800V(692315),         --WLAN new ac ENUM_
                    "
        REVISION    "201803031000Z"

        DESCRIPTION "V7.91,
                    Add:  fnamePTN960E(229409),                       --PTN960E chassis
                    Add:  bnameTPLD00CXPB00(229481)
               	    Add:  bnameTNDD00CXPA00(229482)
                    "
	    REVISION    "201802281000Z"

        DESCRIPTION
                "Huawei text conventions and common  defination."
                 REVISION    "201802231000Z"
                 DESCRIPTION "V7.97,
                    Add: bnameH921MPCA(148510),        -- control board of MA5801-GP08.
                    Add: bnameH921MPCAE(148511),       -- control board of EA5801-GP08.
                    Add: bnameH921GPHD(148540),         --  8*GPON board of MA5801-GP08.
                    Add: bnameH921NXHC(148541),         --  4*10GE board of MA5801-GP08.
                    Add: bnameH921GPHDE(148542),        --  8*GPON board of EA5801-GP08.
                    Add: bnameH921PICA(148543),         --  DC Power board of MA5801-GP08.
                    Add: bnameME170-12A(148544),        --  AC Power board of MA5801-GP08.
                    Add: bnameH921CIUA(148545),         --  GPIO board of MA5801-GP08.
                    Add: bnameH921CGHC(148546),         --  4*GE and 10GE combo board of MA5801-CG04.
                    Add: bnameH921CGHCE(148547),        --  4*GE and 10GE combo board of EA5801-CG04.
                    Add: bnameH921NXHCE(148548),        --  4*10GE board of EA5801-GP08.
                    Add: fnameMA5801-CG04(148504),      --  Backplane of the MA5801-CG04
                    Add: fnameEA5801-GP08(148505),      --  Backplane of the EA5801-GP08
                    Add: fnameEA5801-CG04(148506),      --  Backplane of the EA5801-CG04
                    Add: bnameH902CRED(148638),         --  IP backhaul board of MA5800.
                    Add: bnameH901CSHDE(148639),        --  8*XGS GPON and GPON combo board of EA5800.
                    Add: bnameH901CSHFE(148640),        --  16*XGS GPON and GPON combo board of EA5800.
                    "



		REVISION    "201802051000Z"
        DESCRIPTION "V7.91,
                    Add:  bnameH832PDMSB(156075),       --  DC Power board H832PDMSB of the MA5616.
                    "

        REVISION    "201801301000Z"
        DESCRIPTION "V7.95,
	add wlan device
                   ADD: fnameAP5050DN-S(692309),       --WLAN new ap ENUM_
	ADD: fnameAP2030DN-S(692310),       --WLAN new ap ENUM_
	ADD: fnameAP2051DN-E(692311),       --WLAN new ap ENUM_
	ADD: fnameAP2051DN(692312),         --WLAN new ap ENUM_
	ADD: fnameAP2051DN-S(692313),       --WLAN new ap ENUM_
                    "
        REVISION    "201801191000Z"
        DESCRIPTION "V7.94,
                     Add:subbnameSSD240GB(536789),               --240GB SSD Card(Used in S5x30HI series)
                     Add:subbnameSSD32GB(536790),                --32GB SSD Card(Used in S5x30HI series)
                     Add:subbnamePAC-260WA-E(536791),            --260W AC Power Module(Black)
                     "

        REVISION    "201801181000Z"
        DESCRIPTION "V7.93,
                     Add:  bnameTPLD000PIU00(229477),           --TPL1PIU, Power Interface Board
                     Add:  bnameTPLM000FAN00(229478),           --TPL1FAN, Fan box
                     Add:  bnameTNDM000PIU00(229479),           --TND1PIU, Power Interface Board
                     Add:  bnameTNDM0FAN0300(229480),           --TND1FAN03, Fan box
                     Add:  fname8031CX600-M2K(675942),                  --Quidway CX600-M2K FRAME for V8R10C10
                     Add:  fname8090NE40E-M2K(675943),                  --Quidway NE40E-M2K FRAME for V8R10C10
                     Add:  fname8090CX6602-A(675944),                   --Quidway CX6602-A FRAME for V8R10C10
                     Add:  virent8090DEVCX6D00MPUK11(570058),      -- for V800R010C00 CX6D00MPUK11(SBOM), Main Processing Unit K1
                     Add:  virent8090DEVME0D0LAXXE70(675941),      --ME0D0LAXXE70,10-Port 10GBase LAN/WAN-SFP+ Broadband Service Unit Integrated E(BSUI-100-E)
                     Add:  virent8090DEVCR5D0L5XFL70(675750),      --CR5DLAXFAJ7F,10-Port 10GBase LAN/WAN-SFP+ Integrated Line Processing Unit E(LPUI-120-E)
                     Add:  virent8090DEVCR5DL4XEFG70(675751),      --CR5DLAXFAJ7F,10-Port 10GBase LAN/WAN-SFP+ Integrated Line Processing Unit E(LPUI-120-E)
                     Add:  virent8090DEVCR5D0EMGFL70(675752),      --CR5DLAXFAJ7F,10-Port 10GBase LAN/WAN-SFP+ Integrated Line Processing Unit E(LPUI-120-E)
                     Add:  virent8090DEVCR5DL2XEFG71(675753),      --CR5DLAXFAJ7F,10-Port 10GBase LAN/WAN-SFP+ Integrated Line Processing Unit E(LPUI-120-E)
                     Add:  virent8090DEVCR5D0EFGFL70(675754),      --CR5DLAXFAJ7F,10-Port 10GBase LAN/WAN-SFP+ Integrated Line Processing Unit E(LPUI-120-E)
                     Add:  virent600DEVCX6PM2KBAS90(675932),    --V8R10C10 CX600-M2K CX6PM2KBAS90(SBOM), 1T MNPUI DC
                     Add:  virent600DEVCX6PM2KBAS91(675933),    --V8R10C10 CX600-M2K CX6PM2KBAS91(SBOM), 1T MNPUI AC
                     Add:  virent600DEVCX6B0BKP0391(675934),    --V8R10C10 CX600-M2K CX6B0BKP0391(SBOM), 1T MNPUI NO POWER
                     Add:  virent600DEVCR5PM2KBAS90(675935),    --V8R10C10 NE40E-M2K CR5PM2KBAS90(SBOM), 1T MNPUI DC
                     Add:  virent600DEVCR5PM2KBAS91(675936),    --V8R10C10 NE40E-M2K CR5PM2KBAS91(SBOM), 1T MNPUI AC
                     Add:  virent600DEVCR5B0BKP0391(675937),    --V8R10C10 NE40E-M2K CR5B0BKP0391(SBOM), 1T MNPUI NO POWER
                     Add:  virent600DEVCX6P02ABAS00(675938),    --V8R10C10 CX6602-A CX6P02ABAS00(SBOM), 1T MNPUI DC
                     Add:  virent600DEVCX6P02ABAS01(675939),    --V8R10C10 CX6602-A CX6P02ABAS01(SBOM), 1T MNPUI AC
                     Add:  virent600DEVCX6B0BKP0292(675940),    --V8R10C10 CX6602-A CX6B0BKP0292(SBOM), 1T MNPUI NO POWER
                     Add:  virent8090DEVCR5DLPUFE071(675945),    -- for V800R010C10 CR5DLPUFE071(SBOM),Flexible Card Line Processing Unit(LPUF-200)
                     Add:  virent8090DEVCR5DLPUFE07C(675946),    -- for V800R010C10 CR5DLPUFE07C(SBOM),Flexible Card Line Processing Unit(LPUF-200-B)
                     Add:  virent8090DEVCX6DISUFE013(675948),    -- for V800R010C10 CX6DISUFE013(SBOM),Flexible Card Integrated Service Unit(ISUF-201)
                     Add:  virent8090DEVCX6D00MPUD30(675947),  --Main Processing Unit D3(4G Memory)
                     Add:  virent8090DEVCR5D0SRUAA70(567001),    -- V8R10C10 for CR5D0SRUAA70(SBOM) Switch and Route Processing Unit A10(32G Memory)
                     Add:  virent8090DEVCR5DSFUIU07D(567002),    -- V8R10C10 for CR5DSFUIU07D(SBOM) 2Tbps Switch Fabric Unit D(SFUI-2T-D)
                     Add:  virent8090DEVCX6D0SRUAA70(567003),    -- V8R10C10 for CX6D0SRUAA70(SBOM) Switch and Route Processing Unit A10(32G Memory)
                     Add:  virent8090DEVCX6DSFUIU07D(567004),    -- V8R10C10 for CX6DSFUIU07D(SBOM) 2Tbps Switch Fabric Unit D(SFUI-2T-D)
                     Add:  virent8090DEVTNRD0SRUAA70(567005),    -- V8R10C10 for TNRD0SRUAA70(SBOM) Switch and Route Processing Unit A10(32G Memory)
                     Add:  virent8090DEVTNRDSFUIU07D(567006),     -- V8R10C10 for TNRDSFUIU07D(SBOM) 2Tbps Switch Fabric Unit D(SFUI-2T-D)
                     Add:  virent8090DEVCX6D60T220A0(675755),     -- V8R10C10 for CX6D60T220A0(SBOM) 20-Port 100GBase-MACsec Integrated Line Processing Unit (LPUI-2T)
					 Add:  virent8090DEVCR5D0MPUN160(570061)     -- V8R10C10 for CR5D0MPUN160(SBOM) NE5000E-20 Main Processing Unit N1(MPUN1)
                     Add:  subbname8090DEVCR57E1NBA2(537735),         -- 1-Port 100GBase-QSFP28 Fixed Card
                     Add:  subbname8090DEVCR5D00T1NC70(537440),       --03032PCD,  1-Port 100G OTN/ETH-CFP2 Flexible Card(P240)
                     Add:  subbname8090DEVCR9D00EANB81(537441),       --10-Port 100GBase-QSFP28 MacSec Flexible Card
                     Add:  subbname8090DEVCR9D00EANB80(537442),       --10-Port 100GBase-QSFP28 Flexible Card
                     Add:  subbname8090DEVCR2D0EM4TP10(537443),       --4 Port 100/100Base -RJ45 with PoE Physical Interface Card
                     Add:  subbname8090DEVCR58EANBA(537444),          --10-Port 100GBase QSFP28 MACsec fixed Card
                     Add:  subbname8090DEVCR2D0L4XFM10(537445),       --4-Port 10GBase-SFP+MACsec Interface Card
                     Add:  subbname8090DEVNEDD0EX4SM00(537446),       --4 Channel 10GE Optical Interface Board with MACSec (SFP+)
                     Add:  subbname8090DEVNEDD0EM4TP00(537447),       --4 Port 100/1000Base-RJ45 with PoE Physical Interface Card
                       "
                   REVISION    "201801151000Z"
        DESCRIPTION "V7.92,
                   Add: virent8090DEVCR9DLPUFK081(570060)     -- V8R10C10 for CR9DLPUFK081(SBOM) 480G Flexible Card Line Processing Unit C(NE9000 LPUF-480C,2 sub-slots)
                       "
                   REVISION    "201801091000Z"
        DESCRIPTION "V7.91,
                   Add: bnameCEL18CQFDA(688285)        --Manufactured Board,CloudEngine 12800,CE-L18CQ-FDA,18-Port-40GE,18-Port-100GE Interface Card(FDA,QSFP+,QSFP28)
                       "
                   REVISION    "201801031000Z"
        DESCRIPTION "V7.90,
                   Add: bnamePTN7900TPE1PSU(229475),    --PTN7900E-24 power board
                   Add: bnamePTN7900TPE1FAN(229476),    --PTN7900E-24 fan board
                       "
                   REVISION    "201801031000Z"
        DESCRIPTION "V7.89,
                    Add: fnameATNDEV905-F-AC(225600),      --ATN905-F-AC chassis
                    Add: fnameATNDEV905-F-DC(225602),      --ATN905-F-DC chassis
                    Add: fnameETN500-F(708624),            --ETN500-F chassis
                    Add: fnameNE05E-SR(704571),            -- NE05E-SR chassis
                    Add: fnameNE08E-S9(704573),            -- NE08E-S9 chassis
                    Add: virentANPM001AICF0(225601),       -- ATN905-F System,AC,2*GE/FE Combo,2*GE/FE(o),2*GE/FE(e)
                    Add: virentANPM001DICF0(225603),       -- ATN905-F System,DC,2*GE/FE Combo,2*GE/FE(o),2*GE/FE(e)
                    Add: virentLNPM001AICF0(708625),       -- ETN500-F System,AC,2*GE/FE Combo,2*GE/FE(o),2*GE/FE(e)
                    Add: virentANDD03CXPA00(225604),       -- ATN950B, System Control, Cross-connect and Multi-protocol Process Unit
                    Add: virentANKD00CXPB02(225605),       -- ATN950C, System Control,Cross-connect and Multi-protocol Process Unit B
                    Modify: virentANKD00CXPB00(225569)     -- 80G -> 360G
                    Add: virentNECM000AIC01(704572),       -- NE05E-SR System,Indoor,AC,2*GE/FE Combo,2*GE/FE(o),2*GE/FE(e)
                    Add: virentNEJD00CXPA00(704574),       -- System Control,Cross-connect and Multi-protocol Process Unit A For S9
                    Add: virentNEDD00CXPB00(704575),       -- NE08E-S6E, System Control,Cross-connect and Multi-protocol Process Unit B for S6E
                       "

                   REVISION    "201712211000Z"
        DESCRIPTION "V7.88,
                   Add:fname8090NE5000E-20(561105),        --Quidway NE5000E-20 FRAME
                   Add:virent8090DEVCR5DSFUIT260(562081),                     
                   Add:virent8090DEVCR5D0MPUB760(562164),   -- v8r10c10 NE5000-20 Main Processing Unit N1(MPUN1)
                       "


                   REVISION    "201712201000Z"
           DESCRIPTION "V7.87,
                   Add:bnamePTN7900TPA1FHD1(229464), --TPA1FHD1,1-port 200 Gigabit Ethernet Switching Processing Board
                   Add:bnamePTN7900TPD1FHD1(229465), --TPD1FHD1,1-port 200 Gigabit Ethernet Switching Processing Board
                   Add:bnamePTN7900TPA1FH2(229466), --TPA1FH2,2-port 100 Gigabit Ethernet Switching Processing Board
                   Add:bnamePTN7900TPD1FH2(229467), --TPD1FH2,2-port 100 Gigabit Ethernet Switching Processing Board
                   Add:bnamePTN7900TPA1FH1(229468), --TPA1FH1,1-port 100 Gigabit Ethernet Switching Processing Board
                   Add:bnamePTN7900TPD1FH1(229469), --TPD1FH1,1-port 100 Gigabit Ethernet Switching Processing Board
                   Add:bnamePTN7900TPA1FV2(229470), --TPA1FV2,2-port 50 Gigabit Ethernet Switching Processing Board
                   Add:bnamePTN7900TPD1FV2(229471), --TPD1FV2,2-port 50 Gigabit Ethernet Switching Processing Board
                   Add:bnamePTN7900TPE1CXP(229472), --TPE1CXP,System Control Communication and Switch Fabric Process Unit,1*1
                   Add:bnamePTN7900TPF1CXP(229473), --TPF1CXP,System Control Communication and Switch Fabric Process Unit,1*1
                   Add:bnamePTN7900TPE1XCS(229474), --TPE1XCS,Switch Fabric Unit,1*1
                  "


	REVISION    "201712161000Z"
           DESCRIPTION "V7.86,
                    Add: bnameNEJD002FAN00(229010),          --NE08E-S9, FAN
                          "

                    REVISION    "201712131000Z"
               DESCRIPTION "V7.85,
                     Add: subbname8090DEVNEDD00EX4S00(225564),    --Finished Board Unit,NE08E-S6E,NED1EX4S0,4 Channels 10GE Optical Interface Board(SFP+)
                     Add: subbname8090DEVANKD001EV100(225622),       --1 Channel 50G Base QSFP28 High Speed Interface Board
                     Add:  subbname8090DEVCR5D00E1NC7D(537713),       --1-Port 100GBase-CFP2 Flexible Card A(P240-A)
                     Add: subbname8090DEVCX68E2NLHXF0(537426),       --2-Port 100GBase-QSFP28 + 30-Port 10GBase-X-SFP+
                     Add: subbname8090DEVCR5D00E4XF20(537427),       --4-Port 10GBase-SFP+MACsec Interface Card
                     Add: subbname8090DEVCR5D00E1NB20(537428),       --1-Port 100GBase-QSFP28+MACsec Interface Card
                     Add: subbname8090DEVCR5DE2NE4X10(537429),       --2-Port 100GBase-QSFP28/1-Port100GBase-QSFP28+4-Port 10GBase-SFP+MACsec Interface Card
                     Add: subbname8090DEVAND1EM8F(537430),    -- ATN 950B,AND1EM8F0,8 Channels GE/FE Optical Interface Board
                     Add: subbname8090DEVAND1EM8T(537431),    -- ATN 950B,AND1EM8T0,8 Channels GE/FE Electric Interface Board
                     Add: subbname8090DEVAND1EM4F(537432),    -- ATN 950B,AND1EM4F0,4 Channels GE/FE Optical Interface Board
                     Add: subbname8090DEVAND1EM4T(537433),    -- ATN 950B,AND1EM4T0,4 Channels GE/FE Electric Interface Board
                     Add: subbname8090DEVAND1EX1(537434),                -- 1 Channel 10 GE Optical Interface board
                     Add: subbname8090DEVAND2EM8M(537435),           -- 4 Channels GE/FE Optical Interface and 4 Channels GE/FE Electric Interface Board
                     Add: subbnameATNAND3MD1(537436),              -- 32 Channels E1 Interface Board
                     Add: subbnameATNNEDD001EM600(537437),            --6 Channels E&M Interface Board
                     Add: subbnameATNNED3MD1(537438),                       -- 32 Channels E1 Interface Board
                     Add: subbname8090DEVCR2D000EM890(537439),       --6 Channels E&M Interface Board
                     Add: virent8090DEVCR5DSFUIT27B(675921),    -- V8R10C00 for CR5DSFUIT27B(SBOM) 2Tbps Switch Fabric Unit B(SFUI-2T-B)
                     Add: virent8090DEVCR2DNSPD0010(562078),    -- V8R10C00 for CR2DNSPD0010(SBOM) Network Service Processor(NSP-D)
                           "

	REVISION    "201711271000Z"
        DESCRIPTION "V7.84,
                    Add: virent8090DEVTNRDMPUX8670(570059),      --for V800R010C00 TNRDMPUX8670(SBOM),Main Processing Unit B6
                    Add: virentPTN6900DEVTNUD00MPUK71(229407),    --for V800R007C00 TNUD00MPUK71(SBOM), Main Processing Unit K1
		    "
	REVISION    "201711231000Z"
        DESCRIPTION "V7.83,
                    Add: bnameH901CSHD(148632),        --  8*XGS GPON and GPON combo board of MA5800.
                    Add: bnameH901CGHF(148633),        --  16*XG GPON and GPON combo board of MA5800.
                    Add: bnameH901CSHF(148634),        --  16*XGS GPON and GPON combo board of MA5800.
                    Add: bnameH901XEHF(148635),        --  16*10G EPON board of MA5800.
                    Add: bnameH902CGHD(148636),        --  8*XGS GPON and GPON combo board of MA5800.
                    Add: bnameH902CSHD(148637),        --  8*XG GPON and GPON combo board of MA5800.
                    Add: fnameMA5801-GP08(148503),     -- Backplane of the MA5801-GP08.
                    Add: bnameH911MPCA(148510),        -- control board of MA5801-GP08.
                    Add: bnameH911MPCAE(148511),       -- control board of EA5801-GP08.
                    Add: bnameH911GPHD(148540),        -- 8*GPON board of MA5801-GP08.
                    Add: bnameH911NXHC(148541),        -- 4 P2P board of MA5801-GP08.
                    Add: bnameH911GPHDE(148542),       -- 8*GPON board of EA5801-GP08.
                    Add: bnameH911PICA(148543),        -- DC Power board of MA5801-GP08.
                    Add: bnameME170-12A(148544),       -- AC Power board of MA5801-GP08.
                    Add: bnameH911CIUA(148545),        -- GPIO board of MA5801-GP08.
		    "

        REVISION    "201711171000Z"
        DESCRIPTION "V7.82,
                     Add: bnameH801CGBD(146151),         --  8-port 10G GPON and GPON combo interface board of MA5600T.
                     Add: bnameH802CGBD(146152),         --  8-port 10G GPON and GPON combo interface board of MA5600T.
                     Add: bnameH801CSBD(146153),         --  8-port 10GS-PON and GPON combo interface board of MA5600T.
                     Add: bnameH802CSBD(146154),         --  8-port 10GS-PON and GPON combo interface board of MA5600T.
                     Add: bnameH801XSBD(146155),         --  8-port 10GS-PON interface board of MA5600T.
                     "

        REVISION    "201711140000Z"
        DESCRIPTION "V7.81,
                     Modify: CR9D0MPUM80 changed to CR9D0MPUP180
                     "

        REVISION    "201711020000Z"
        DESCRIPTION "V7.80,
                 	 Add: fname8031S5720I-12X-SI-AC(537231),             --98010794 S5720I-12X-SI-AC for lsw v2r12c00
                 	 Add: fname8031S5720I-12X-PWH-SI-DC(537232),   --98010795 S5720I-12X-PWH-SI-DC for lsw v2r12c00
                 	 Add: fname8031S5720I-28X-SI-AC(537233),             --98010796 S5720I-28X-SI-AC for lsw v2r12c00
                 	 Add: fname8031S5720I-28X-PWH-SI-AC(537234),   --98010797 S5720I-28X-PWH-SI-AC for lsw v2r12c00
                 	 Add: fname8031S5320-52X-SI-AC-V1(537235),        -- Real name S5320-52X-SI-AC for LSW V2R11C10 from S5320-52X-LI-AC
                 	 Add: fname8031S5320-52X-SI-DC-V1(537236),        -- Real name S5320-52X-SI-DC for LSW V2R11C10 from S5320-52X-LI-DC
                 	 Add: fname8031S5320-52P-SI-AC-V1(537237),        -- Real name S5320-52P-SI-AC for LSW V2R11C10 from S5320-52P-LI-AC
                 	 Add: fname8031S5320-52P-SI-DC-V1(537238),        -- Real name S5320-52P-SI-DC for LSW V2R11C10 from S5320-52P-LI-AC
                 	 Add: fname8031S5300-52P-LI-DC-V1(537239),        -- Real name S5300-52P-LI-DC for LSW V2R11C10 from S5320-52P-LI-AC
                 	 Add: fname8031S5320-36C-EI-28S-AC-V1(537240),    -- Real name S5320-36C-EI-28S-AC for LSW V2R11C10 from S5320-28X-LI-24S-AC
                 	 Add: fname8031S5320-36C-EI-28S-DC-V1(537241),    -- Real name S5320-36C-EI-28S-DC for LSW V2R11C10 from S5320-28X-LI-24S-DC
                 	 Add: fnameLE1BS9316S00(659476),                             -- Quidway S9316  FRAME
                 	 Add: bname8031S5720I-12X-SI-AC(537415),            --98010794 S5720I-12X-SI-AC for lsw v2r12c00
                 	 Add: bname8031S5720I-12X-PWH-SI-DC(537416),  --98010795 S5720I-12X-PWH-SI-DC for lsw v2r12c00
                 	 Add: bname8031S5720I-28X-SI-AC(537417),            --98010796 S5720I-28X-SI-AC for lsw v2r12c00
                 	 Add: bname8031S5720I-28X-PWH-SI-AC(537418),  --98010797 S5720I-28X-PWH-SI-AC for lsw v2r12c00
                 	 Add: bname8031S5320-52X-SI-AC-V1(537419),          -- Real name S5320-52X-SI-AC for LSW V2R11C10 from S5320-52X-LI-AC
                 	 Add: bname8031S5320-52X-SI-DC-V1(537420),          -- Real name S5320-52X-SI-DC for LSW V2R11C10 from S5320-52X-LI-DC
                 	 Add: bname8031S5320-52P-SI-AC-V1(537421),          -- Real name S5320-52P-SI-AC for LSW V2R11C10 from S5320-52P-LI-AC
                 	 Add: bname8031S5320-52P-SI-DC-V1(537422),          -- Real name S5320-52P-SI-DC for LSW V2R11C10 from S5320-52P-LI-AC
                 	 Add: bname8031S5300-52P-LI-DC-V1(537423),          -- Real name S5300-52P-LI-DC for LSW V2R11C10 from S5320-52P-LI-AC
                 	 Add: bname8031S5320-36C-EI-28S-AC-V1(537424),      -- Real name S5320-36C-EI-28S-AC for LSW V2R11C10 from S5320-28X-LI-24S-AC
                 	 Add: bname8031S5320-36C-EI-28S-DC-V1(537425),      -- Real name S5320-36C-EI-28S-DC for LSW V2R11C10 from S5320-28X-LI-24S-DC
                	 Add: bnameLE1D2SRUKC01(659667),      --S9310,Main Processing Unit K(Support Security Startup) for v2r12
                	 Add: bnameLE1D2SRUH002(659668),      --S9306/S9312,Main Control Unit H(Support Security Startup) for v2r12
                	 Add: bnameLE1D2MPUA000(659669),      --S9316 Main Processing Unit A(Optional clock) for v2r12
                	 Add: bnameLE1D2SFUD000(659670),      --S9316 Switch Fabric Unit D for v2r12
                	 Add: bnameES1D2SRUKC01(663633),      --S7710,Main Processing Unit K(Support Security Startup) for v2r12
                	 Add: bnameES1D2SRUH002(663634),      --S7706/S7712,Main Control Unit H(Support Security Startup) for v2r12
                	 Add: bnameET1D2MPUBC01(700478),     --S12710,Main Processing Unit B(Support Security Startup) for v2r12
                    "

        REVISION    "201711011000Z"
        DESCRIPTION "V7.79,
                     Add: bnameH802GICK(146079),        -- GE synchronized Ethernet interface board of MA5600T
                     "

        REVISION    "201710310000Z"
        DESCRIPTION "V7.78,
                 	 Add: subbname8090DEVCX6D0E2NCA11(537491),    -- 2-Port 100GBase-CFP2 Flexible Card A(S480-A)
                 	 Add: subbname8090DEVME0M0E2NCB72(537492),    -- 2-Port 100GBase-CFP2 Flexible Card(BP480)
                 	 Add: subbname8090DEVCR2D04OTU210(561735),    -- 4-Port 10G OTU2-XFP Physical Interface Card(PIC)
                 	 Add: subbname8090DEVCR2D0E5XMF10(561736),    -- 2-Port 50GBase/1-Port 100GBase-QSFP28 Physical Interface Card(PIC)
                    Add: subbname8090DEVCR2D00LAXF11(561737),    -- 10-Port 10GBase-X-SFP+ Physical Interface Card(PIC)
 	 Add: subbname8090DEVCR2D00E1NC11(561738),    -- 1-Port 100GBase-CFP2 Physical Interface Card(PIC)
                 	 Add: subbname8090DEVCR2D00E2NF10(561739),    -- 2-Port 100GBase-QSFP28 Physical Interface Card(PIC)
                    Add: subbname8090DEVCX6D0E2NBA10(561740),      -- 2-Port 100GBase-QSFP28 Flexible Card A(S480-A)
                    Add: subbname8090DEVME0M0E2NFB70(561741),      -- 2-Port 100GBase-QSFP28 Flexible Card H(BP400-H)
	 Add: subbname8090DEVME0M0E2NFB71(561742),      -- 2-Port 100GBase-QSFP28 Flexible Card(BP480)
                    "

		REVISION    "201710230000Z"
        DESCRIPTION "V7.77,
                    Add: bnameH901TWEDE(148628),        --  8*10G GPON board of MA5800.
                    Add: bnameH902TWED(148629),          --  8*10G Flex-PON board of MA5800 support TWDM-PON XGS-PON.
	 Add: bnameH903XSHD(148630),          --  8*10G GPON board of MA5800.
	 Add: bnameH901XSHF(148631),          --  16*10G XGS-PON board of MA5800.
	"
        REVISION    "201710190000Z"
        DESCRIPTION "V7.76,
                     Add: subbnameH823CUVC(156064),       -- 8SV uplink Subboard of MA5811S-AE16(8SV uplink) device.
                     Add: bnameH82EBFVM(156073),        --Master board of MA5811S-AE16(8SV uplink) device.
                     Add: bnameHS2EBFVM(156074),        --16 G.FAST service board of MA5811S-AE16(8SV uplink) device.
                     Add: fnameMA5811S-G5-8SV-AE16(561658),  --Virtual frame MA5811S-AE16 of MA5811S_AE16(8SV uplink) device.
                     "

        REVISION    "201710190000Z"
        DESCRIPTION "V7.75,
                    add:fnameCX916(688173),                      -- CX916
                    add:fnameCE685648S6QHI(688175),              -- CloudEngine CE6856-48S6Q-HI Switch(48-Port 10G SFP+,6-Port 40GE QSFP+)
                    add:fnameCE685648T6QHI(688176),              -- CloudEngine CE6856-48T6Q-HI Switch(48-Port 10GE RJ45,6-Port 40GE QSFP+)
                    add:fnameCE687548S4CQEI(688178),             -- CloudEngine CE6875-48S4CQ-EI Switch(48-Port 10GE SFP+,4*100GE QSFP28)
                    add:bnameCEL24XSEC1(688260),                 -- (DXJC)Manufactured Board,CloudEngine 12800,CE-L24XS-EC1
                    add:bnameCEL04CFEC1(688261),                 -- (DXJC)Manufactured Board,CloudEngine 12800,CE-L04CF-EC1,4-Port-100GE Interface Card(EC1,CFP)
                    add:bnameCEL04CFEC1B(688264),                -- Manufactured Board,CloudEngine 12800,CE-L04CF-EC1,4-Port-100GE Interface Card(EC1,CFP)
                    add:bnameCEL06CQFD(688266),                  -- (YDJC)Manufactured Board,CloudEngine 12800,CEL06CQFD,6-Port-100GE Interface Card(FD,QSFP28)
                    add:bnameCEL06CQFDM(688267),                 -- (YDJC)Manufactured Board,CloudEngine 12800,CEL06CQFD-M,6-Port-100GE Interface Card(FD-M,QSFP28)
                    add:bnameNSEL32XSEGA(688268),                -- Board for wangan
                    add:bnameCEL36CQFG(688269),                  -- Manufactured Board,CloudEngine 12800,CE-L36CQ-FG,36-Port-100GE Interface Card(FG,QSFP28)
                    add:bnameCEL48XSFG(688270),                  -- Manufactured Board,CloudEngine 12800,CE-L48XS-FG,48-Port-10GE Interface Card(FG,SFP+)
                    add:bnameCEL48GTEGAE(688271),                -- Manufactured Board,CloudEngine 12800E,CEL48GTEGA-E,48-Port-GE,4-Port-10GE Interface ENP Card(EGA,RJ45,SFP+)
                    add:bnameCE685648S6QHI(688273),              -- Manufactured Board,CloudEngine 6800,CEM48S6QP05,48-Port SFP+ Optical,6-Port 40GE QSFP+ Optical Switch Control Unit,1*1
                    add:bnameCE685648T6QHI(688274),              -- Manufactured Board,CloudEngine 6800,CEM48T6QP02,48 Port 10GE RJ45, 6 Port 40GE QSFP+ Optical Switch Control Unit,1*1
                    add:bnameCX916(688275),                      -- CX916
                    add:bnameCEL08CFFG1(688276),                 -- Manufactured Board,CloudEngine 12800,CE-L08CF-FG1,8-Port-100GE Interface Card(FG1,CFP2)
                    add:bnameCEL16CQFD(688277),                  -- Manufactured Board,CloudEngine 12800,CE-L16CQ-FD,16-Port-100GE Interface Card(FD,QSFP28)
                    add:bnameCEL48XSFD1(688279),                 -- Manufactured Board,CloudEngine 12800,CE-L48XS-FD1,48-Port-10GE Interface Card(FD1,SFP+)
                    add:bnameCE687548S4CQEI(688280),             -- Manufactured Board,CloudEngine 6800,CEM48S4CQP01,48-Port 10GE SFP+,4-Port 100GE QSFP28 Optical Switch Control Unit,1*1
                    add:bnameCEMPUBS(688283),                    -- Manufactured Board,CloudEngine 12800S,CE-MPUB-S
                    add:bnameCESFUGS(688284),                    -- Manufactured Board,CloudEngine 12800S,CE-SFUG-S,CE12800S Switch Fabric Unit G,1*1
                    add:subbnameCED24S2CQU(688141),       -- Manufactured Board,CloudEngine 8800,CE88-D24S2CQ-U,CE8860:24-Port-25GE/32G FC(SFP28),2-Port-100GE(QSFP28) Interface Card,1*1
                  "

        REVISION    "201710090000Z"
        DESCRIPTION "V7.74,
                 Add:  virentME60DEVME0DL6XE8G70(161614),    -- for V800R010C00 ME0DL6XE8G70(SBOM),6-Port 10GBase LAN/WAN-SFP+ + 8-Port 100/1000Base-X-SFP Broadband Service Unit Integrated(BSUI-120)
                 Add:  virent8090DEVCR5DL6XE8G70(161615),    -- for V800R010C00 CR5DL6XE8G70(SBOM),6-Port 10GBase LAN/WAN-SFP+ + 8-Port 100/1000Base-X-SFP Integrated Line Processing Unit (LPUI-120)
                 Add:  virent8090DEVCR5D000VSE70(161616),    -- for V800R010C00 CR5D000VSE70(SBOM),Value-added Service Engine Unit(VSE-A)
                 Add:  subbname8090DEVCR57L6XE4GF0(537714),  -- 6-Port 10GBase LAN/WAN-SFP+ + 4-Port 100/1000Base-X-SFP Fixed Card
                 Add:  subbname8090DEVCR57E4GFC0(537715),    -- 4-Port 100/1000Base-X-SFP Fixed Card A
				 "

				REVISION    "201709260000Z"
        DESCRIPTION "V7.73,
                 Add:   virent8090DEVCR9DLPUFT280(675926),  -- 2T Flexible Card Line Processing Unit(NE9000E LPUF-2T,2 sub-slots)
                 Add:   virent8090DEVCR9D00DDNC80(675927),  -- 16-Port 100G ETH/DWDM CFP2 Integrated Line Process Unit(NE9000 LPUI-2T)
                 Add:   virent8090DEVCR9D00DDNC8P(675928),  -- 16-Port 100G ETH/DWDM CFP2 Integrated Line Process Unit CM(NE9000 LPUI-2T-CM)
                 Add:   virent8090DEVCR9D00EENB80(675923),  -- 20-Port 100GBase-QSFP28 Integrated Line Process Unit (NE9000 LPUI-2T)
                 Add:   virent8090DEVCR9D00EENB8P(675929),  -- 20-Port 100GBase-QSFP28 Integrated Line Process Unit CM(NE9000 LPUI-2T-CM)
                 Add:   virent8090DEVCR9D00DDNC8L(675930),  -- 16-Port 100GBase ETH/DWDM-CFP2 Integrated Line Process Unit L(NE9000 LPUI-2T-L)
                 Add:   virent8090DEVCR9D00EENB8L(675931)  -- 20-Port 100GBase-QSFP28 Integrated Line Process Unit L(NE9000 LPUI-2T-L)
                    "
        REVISION    "201709210000Z"
        DESCRIPTION "V7.72,
	Add: subbname8090DEVCR5D04OTU290(537488),    -- 4-Port 10G OTU2-XFP Physical Interface Card(PIC)
                   Add: subbname8090DEVCR9D00N2NC80(537489),    -- 2-Port 100G OTN/ETH-CFP2 Flexible Card
                   Add: subbname8090DEVCR5D00E2NC77(537490),    -- 2-Port 100GBase-CFP2 Flexible Card A(P480-A)
                   	Add: subbname8090DEVCR5D00LAXF90(561523),     -- 10-Port 10GBase-X-SFP+ Physical Interface Card(PIC)
	Add: subbname8090DEVCR5D00E1NC99(561524),     -- 1-Port 100GBase-CFP2 Physical Interface Card(PIC)
	Add: subbname8090DEVCR5D00E2NB91(561525),     -- 2-Port 100GBase-QSFP28 Physical Interface Card(PIC)
                   Add: subbname8090DEVANKD01EXAS00(561526),    -- Finished Board Unit,ATN 950C,ANK1EXAS0,10 Channels 10GE Optical Interface Board(SFP+)
                   Add: subbname8090DEVANKD001EH100(561527),    -- Finished Board Unit,ATN 950C,ANK1EH1,1 Channel 100GE Optical Interface Board(CFP2)
                   Add: subbname8090DEVCR5D00P4XX60(561528),    -- 4-Port OC-192c/STM-64c POS-XFP Flexible Card(CP400,Occupy 1 sub-slot)
	Add: subbname8090DEVCR58EANBB0(561529),        -- 10-Port 100GBase-QSFP28 Integrated Card
                    "
        REVISION    "201709120000Z"
        DESCRIPTION "V7.71,
	Add: virent8090DEVCX6D00DDNCA0(570054),    -- V8R10C00 for CX6D00DDNCA0(SBOM) 16-Port 100G ETH/DWDM CFP2 Integrated Line Processing Unit (LPUI-2T)
	Add: virent8090DEVCX6D00EENBA0(570055),    -- V8R10C00 for CX6D00EENBA0(SBOM) 20-Port 100GBase-QSFP28 Integrated Line Processing Unit (LPUI-2T)
	Add: virent8090DEVCX6D00EKNBA0(570056),    -- V8R10C00 for CX6D00EKNBA0(SBOM) 40-Port 100GBase-QSFP28 Integrated Line Processing Unit (LPUI-4T)
	Add: virent8090DEVCX6D00EPXFA0(570057),    -- V8R10C00 for CX6D00EPXFA0(SBOM) 60-Port 10GBase LAN/WAN-SFP+ Integrated Line Process Unit (LPUI-1T)
	Add: virent8090DEVCR9D00EDNB8L(562076),    -- V8R10C00 for CR9D00EDNB8L(SBOM) 16-Port 100GBase-QSFP28 Integrated Line Process Unit L(NE9000 LPUI-2T-L)
                    "
        REVISION    "201709040000Z"
        DESCRIPTION "V7.70,
	Add: subnameLND1XE2S(708624),           -- 2 Channels 10GE Optical Interface Board
	Add: subnameLND1LM1A(708625),           -- 16 Channels E1 Interface Board(75ohm)
	Add: subnameLND1LM1B(708626),           -- 16 Channels E1 Interface Board(120ohm)
                    "
        REVISION    "201708310000Z"
        DESCRIPTION "V7.69,
	add wlan device
                    ADD: fnameAD9431DN-24X(692299),       --WLAN new ap ENUM_
	ADD: fnameAP7152DN(692300),           --WLAN new ap ENUM_
	ADD: fnameAP6052DN(692301),           --WLAN new ap ENUM_
	ADD: fnameAP8082DN(692302),           --WLAN new ap ENUM_
	ADD: fnameAP8182DN(692303),           --WLAN new ap ENUM_
	ADD: fnameAP7052DE(692304),           --WLAN new ap ENUM_
	ADD: fnameAP7052TN-WI(692305),        --WLAN new ap ENUM_
	ADD: fnameAP8050TN-HD(692306),        --WLAN new ap ENUM_
	ADD: fnameAP4051TN(692307),           --WLAN new ap ENUM_
	ADD: fnameAP7052DN(692308),           --WLAN new ap ENUM_
                    "
 		REVISION    "201708260000Z"
        DESCRIPTION "V7.68,
                    Add: subbnameH836ASDJ(156063),   --VOIP DSP Subboard H836ASDJ.

		    Add: bnameH82EEFUG(156066),   --Master board of MA5811S-AE08/AE16/DE16 device.
		    Add: bnameHS2EEFUG(156067),   --16 G.FAST board of MA5811S-DE16 service board.
		    Add: bnameH82EEFMG(156068),   --Master board of MA5811S-DE48 device.
		    Add: bnameHS2EEFMG(156069),   --48 G.FAST board of MA5811S-DE48 service board.
		    Add: bnameHS2EEFUR(156071),   --16 G.FAST remote board of MA5811S-AE16 service board.
		    Add: bnameHS2EEFJR(156072),   --8 G.FAST remote board of MA5811S-AE08 service board.

		    Add: fnameMA5811S-G5-AE08(561654),  --Virtual frame MA5811S-AE08 of MA5811S_AE08 device.
		    Add: fnameMA5811S-G5-DE48(561655),  --Virtual frame MA5811S-DE48 of MA5811S_DE48 device.
		    Add: fnameMA5811S-G5-AE16(561656),  --Virtual frame MA5811S-AE16 of MA5811S_AE16 device.
		    Add: fnameMA5811S-G5-DE16(561657),  --Virtual frame MA5811S-DE16 of MA5811S_DE16 device.
                    "

		REVISION    "201708220000Z"
        DESCRIPTION "V7.67,
                    Add: bnameH806VPED(156070),   -- support super vector board.
                    "

        REVISION    "201708210000Z"
        DESCRIPTION "V7.66,
                    add:subbnameFAN40HAB(536788),     --2359097 Fan box(HA,Back to Front,FAN panel side exhaust)
                  "


        REVISION    "201708160000Z"
        DESCRIPTION "V7.65,
                    add:subbname8090DEVCR2D00MPAA90(561651),       --4-Channel FXS/FXO+2-Channel E&M+2-Channel RS232+2-Channel RS485 Board
                    add:subbname8090DEVCR2D000SA890(561652),        --8-Channel V.35/X.21/V.24 Board
                    add:subbname8090DEVCR2D00MP8A90(561653),       --4 Channels C37.94 Optical Interface and 4 Channels CoDir64K Electric Interface Board

                    add:subbnameATNNEDD01MPAA00(225597),                --4-Channel FXS/FXO+2-Channel E&M+2-Channel RS232+2-Channel RS485 Board
                    add:subbnameATNNEDD001SA800(225598),                 --8-Channel V.35/X.21/V.24 Board
                    add:subbnameATNNEDD01MP8A00(225599),                --4 Channels C37.94 Optical Interface and 4 Channels CoDir64K Electric Interface Board
                  "

        REVISION    "201708100000Z"
        DESCRIPTION "V7.64,
                     add:virent8090DEVCR5D0MPUKA90(565042),      -- for V800R010C00 CR5D0MPUKA90(SBOM) Main Processing Unit KA
                     add:virent8090DEVCX6D0MPUKA90(565043),      -- for V800R010C00 CX6D0MPUKA90(SBOM) Main Processing Unit KA
                     add:virent8090DEVTNUD0MPUKA90(565044),     -- for V800R010C00 TNUD0MPUKA90(SBOM) Main Processing Unit KA
                     add:virent8090DEVCR2D0MPUEA00(565045),     -- for V800R010C00 CR2D0MPUEA00(SBOM),Main Processing Unit EA
                     "

        REVISION    "201708070000Z"
        DESCRIPTION "V7.63,
                     Add:bnamePTN7900TPD1EHD1(229453), --TPD1EHD1,1-port 200 Gigabit Ethernet Switching Processing Board
                     Add:bnamePTN7900TPD1EXL2(229454), --TPD1EXL2,2-port 40 Gigabit Ethernet Switching Processing Board
                     Add:bnamePTN7900TPD1EX8S(229455), --TPD1EX8S,8-port 10 Gigabit Ethernet Switching Processing Board
                     Add:bnamePTN7900TPD1EX16S(229456), --TPD1EX16S,16-port 10 Gigabit Ethernet Switching Processing Board
                     Add:bnamePTN7900TPD1EG24(229457), --TPD1EG24,24-port Gigabit Ethernet Switching Processing Board
                     Add:bnamePTN7900TPD1MQ1(229458), --TPD1MQ1,63 Channels E1 Interface Processing Board
                     Add:bnamePTN7900TPD1EV4(229459), --TPD1EV4,4-port 50 Gigabit Ethernet Switching Processing Board
                     Add:bnamePTN7900TPD1EH4(229460), --TPD1EH4,4-Port 100 Gigabit Ethernet Switching Processing Board
                     Add:bnamePTN7900TPD1EH2A(229461), --TPD1EH2A,2-port 100 Gigabit Ethernet Switching Processing Board
                     Add:bnamePTN7900TPA1EH2A(229462), --TPA1EH2A,2-Port 100 Gigabit Ethernet Switching Processing Board
                     Add:bnamePTN7900TPA1EX20A(229463), --TPA1EX20A,20-port 10 Gigabit Ethernet Switching Processing Board
                     "
         REVISION    "201708040000Z"
         DESCRIPTION "V7.62,
            add:virent8090DEVCX6D0MPUP1A0(570050),    -- V8R10C00 for CX6D0MPUP1A0(SBOM) Main Processing Unit P1
            add:virent8090DEVCX6DSFUIT4AA(570051),    -- V8R10C00 for CX6DSFUIT4AA(SBOM) 4Tbps Switch Fabric Unit A(SFUI-4T-A)
            add:virent8090DEVCX6D0MPUN1A0(570052),    -- V8R10C00 for CX6D0MPUN1A0(SBOM) Main Processing Unit N1
            add:virent8090DEVCX6DSFUIT4AB(570053),    -- V8R10C00 for CX6DSFUIT4AB(SBOM) 4Tbps Switch Fabric Unit B(SFUI-4T-B)
            add:fname8090CX6620(562055),       --Quidway CX6620 FRAME
            add:fname8090CX6608(562056),       --Quidway CX6608 FRAME

            add:virent8090DEVCR5D00E2NB70(566121),    -- for V800R010C00 CR5D00E2NB70(SBOM),2-Port 100GBase-QSFP28 Integrated Line Processing Unit(LPUI-200)
            add:virent8090DEVCR5DE1NLAX78(566122),    -- for V800R010C00 CR5DE1NLAX78(SBOM),1-Port 100GBase-QSFP28 + 10-Port 10GBase LAN/WAN-SFP+ Integrated Line Processing Unit(LPUI-200)
            add:virent8090DEVCR5D0E2NBL70(566123),    -- for V800R010C00 CR5D0E2NBL70(SBOM),2-Port 100GBase-QSFP28 Integrated Line Processing Unit L(LPUI-200-L)
            add:virent8090DEVCR5DE1NLAX7A(566124),    -- for V800R010C00 CR5DE1NLAX7A(SBOM),1-Port 100GBase-QSFP28 + 10-Port 10GBase LAN/WAN-SFP+ Integrated Line Processing Unit L(LPUI-200-L)
            add:virent8090DEVME0D0E2NBB70(566125),    -- for V800R010C00 ME0D0E2NBB70(SBOM),2-Port 100GBase-QSFP28 Multi Service Unit Integrated(MSUI-200)
            add:virent8090DEVME0D0E4NBM70(566126),    -- for V800R010C00 ME0D0E4NBM70(SBOM),4-Port 100GBase-QSFP28 Multi Service Unit Integrated(MSUI-400)


            add:virent8090DEVCX6DSFUIM17B(565016),      -- for V800R10C00 CX6DSFUIM17B(SBOM)	480Gbps Switch Fabric Unit B(SFUI-480-B)
            add:virent8090DEVCX6DSFUIT27B(565017),      -- for V800R10C00 CX6DSFUIT27B(SBOM)	2Tbps Switch Fabric Unit B(SFUI-2T-B)
            add:virent8090DEVCX6D0SRUA872(565018),      -- for V800R10C00 CX6D0SRUA872(SBOM)	Switch and Route Processing Unit A8(16G Memory)
            add:virent8090DEVCX6DSFUIM17C(565019),      -- for V800R10C00 CX6DSFUIM17C(SBOM)	480Gbps Switch Fabric Unit C(SFUI-480-C)
            add:virent8090DEVTNRDSFUIM17B(565020),      -- for V800R10C00 TNRDSFUIM17B(SBOM)	480Gbps Switch Fabric Unit B(SFUI-480-B)
            add:virent8090DEVTNRDSFUIT27B(565021),      -- for V800R10C00 TNRDSFUIT27B(SBOM)	2Tbps Switch Fabric Unit B(SFUI-2T-B)
            add:virent8090DEVTNRD0SRUA872(565022),      -- for V800R10C00 TNRD0SRUA872(SBOM)	Switch and Route Processing Unit A8(16G Memory)
            add:virent8090DEVTNRDSFUIM17C(565023),      -- for V800R10C00 TNRDSFUIM17C(SBOM)	480Gbps Switch Fabric Unit C(SFUI-480-C)
            add:virent8090DEVCX6DSFUIM11B(565024),      -- for V800R10C00 CX6DSFUIM11B(SBOM)	480Gbps Switch Fabric Unit B(SFUI-480-B)
            add:virent8090DEVCX6DSFUIT21B(565025),      -- for V800R10C00 CX6DSFUIT21B(SBOM)	2Tbps Switch Fabric Unit B(SFUI-2T-B)
            add:virent8090DEVCX6D0SRUA812(565026),      -- for V800R10C00 CX6D0SRUA812(SBOM)	Switch and Route Processing Unit A8(16G Memory)
            add:virent8090DEVCX6DSFUIM11C(565027),      -- for V800R10C00 CX6DSFUIM11C(SBOM)	480Gbps Switch Fabric Unit C(SFUI-480-C)
            add:virent8090DEVME0DSFUIM17B(565028),      -- for V800R10C00 ME0DSFUIM17B(SBOM)	480Gbps Switch Fabric Unit B(SFUI-480-B)
            add:virent8090DEVME0D0SRUA872(565029),      -- for V800R10C00 ME0D0SRUA872(SBOM)	Switch and Route Processing Unit A8(16G Memory)
            add:virent8090DEVME0DSFUIM17C(565030),      -- for V800R10C00 ME0DSFUIM17C(SBOM)	480Gbps Switch Fabric Unit C(SFUI-480-C)

            add:virent8090DEVCR5D00EENB70(675922),      -- for V800R10C00 CR5D00EENB70(SBOM) 20-Port 100GBase-QSFP28 Integrated Line Processing Unit (LPUI-2T)
            add:virent8090DEVCR5D00EENB7B(565031),      -- for V800R10C00 CR5D00EENB7B(SBOM) 20-Port 100GBase-QSFP28 Integrated Line Processing Unit B(LPUI-2T-B)
            add:virent8090DEVCR5D00EENB7P(565032),      -- for V800R10C00 CR5D00EENB7P(SBOM) 20-Port 100GBase-QSFP28 Integrated Line Processing Unit CM(LPUI-2T-CM)
            add:virent8090DEVCX6D00EENB10(565033),      -- for V800R10C00 CX6D00EENB10(SBOM) 20-Port 100GBase-QSFP28 Integrated Line Processing Unit (ISUI-2T)

            add:virent8090DEVCX6DISUFM011(565034),      -- for V800R10C00 CX6DISUFM011(SBOM) Flexible Card Integrated Service Unit(ISUF-480)
            add:virent8090DEVME0DBSUFM071(565035),      -- for V800R10C00 ME0DBSUFM071(SBOM) Flexible Card Broadband Service Unit(BSUF-480,2 sub-slots)
            add:virent8090DEVME0DBSUFK071(565036),      -- for V800R10C00 ME0DBSUFK071(SBOM) Flexible Card Broadband Service Unit(BSUF-400,2 sub-slots)
            add:virent8090DEVME0DMSUFM071(565037),      -- for V800R10C00 ME0DMSUFM071(SBOM) Flexible Card Multi Service Unit(MSUF-480,2 sub-slots)
            add:virent8090DEVME0D0L4NCB71(565038),      -- for V800R10C00 ME0D0L4NCB71(SBOM) 4-Port 100GBase-CFP2 Broadband Service Unit Integrated(BSUI-400)
            add:virent8090DEVME0D0LKXFB71(565039),      -- for V800R10C00 ME0D0LKXFB71(SBOM) 40-Port 10GBase LAN/WAN-SFP+ Broadband Service Unit Integrated(BSUI-400)
            add:virent8090DEVME0D0E4NCM71(565040),      -- for V800R10C00 ME0D0E4NCM71(SBOM) 4-Port 100GBase-CFP2 Multi Service Unit Integrated(MSUI-400)
            add:virent8090DEVME0D0LMXFA71(565041),    -- for V800R010C00 ME0D0LMXFA71(SBOM),48-Port 10GBase LAN/WAN-SFP+ Multi Service Unit Integrated(MSUI-480)
       "

         REVISION    "201707310000Z"
         DESCRIPTION "V7.61,
          subbname8090DEVCR53C2CF0(567890),    -- 2-Port Channelized OC-3c/STM-1c POS-SFP Flexible Card
         "

        REVISION    "201707180000Z"
        DESCRIPTION "V7.60,
          add:subbname8090DEVCR5D0LEXFE72(561520),    -- 20-Port 10GBase LAN/WAN-SFP+ Flexible Card A(P480-A)
          add:subbname8090DEVCR5D0LAXFE71(561521),    -- 10-Port 10GBase LAN/WAN-SFP+ Flexible Card A(P240-A)
          add:subbname8090DEVCR5D0L6XFE70(561522),    -- 6-Port 10GBase LAN/WAN-SFP+ Flexible Card E(P120-E)
            "


        REVISION    "201707140000Z"
        DESCRIPTION "V7.59,
          add:virent8090DEVCR5DSFUIT28A(562084),  --2T Switch Fabric Unit for Single Chassis (SFU-2T-A)
          add:virent8090DEVCR5D0MPUB680(562085), --Main Processing Unit B6
          add:virent8090DEVCR5D00EDNB80(562086),  --16-Port 100GBase-QSFP28 Integrated Line Process Unit B (NE40E LPUI-2T)
          add:virent8090DEVCR5DE3NL5X60(562087),  --3-Port 100GBase-QSFP28 + 5-Port 10GBase LAN/WAN SFP+ Integrated Line Process Unit (NE5000E LPUI-1T)
            "


        REVISION    "201707120000Z"
        DESCRIPTION "V7.58,
          modify: fname8031S2720-12TP-EI(537135),            --S2720-12TP-EI           Metro Service Platform for V2R11, modify name
          modify: fname8031S2720-12TP-PWR-EI(537138),        --S2720-12TP-PWR-EI       Metro Service Platform for V2R11, modify name
          modify: fname8031S2720-52TP-EI(537140),            --S2720-52TP-EI           Metro Service Platform for V2R11, modify name
          modify: fname8031S2720-52TP-PWR-EI(537142),        --S2720-52TP-PWR-EI       Metro Service Platform for V2R11, modify name
          modify: fname8031S2720-28TP-PWR-EI-L(537144),       --S2720-28TP-PWR-EI-L      Metro Service Platform for V2R11, modify name
          modify: fname8031S2720-28TP-EI(537145),         --S2720-28TP-EI       Metro Service Platform for V2R11, modify name, modify name
          modify: fname8031S2720-28TP-PWR-EI(537148),        --S2720-28TP-PWR-EI       Metro Service Platform for V2R11, modify name

          modify: bname8031S2720-12TP-EI(537319),                --S2720-12TP-EI           Metro Service Platform for V2R11,modify name
          modify: bname8031S2720-12TP-PWR-EI(537322),            --S2720-12TP-PWR-EI       Metro Service Platform for V2R11,modify name
          modify: bname8031S2720-52TP-EI(537324),                --S2720-52TP-EI           Metro Service Platform for V2R11,modify name
          modify: bname8031S2720-52TP-PWR-EI(537326),            --S2720-52TP-PWR-EI-AC       Metro Service Platform for V2R11,modify name
          modify: bname8031S2720-28TP-PWR-EI-L(537328),           --S2720-28TP-PWR-EI-L      Metro Service Platform for V2R11,modify name
          modify: bname8031S2720-28TP-EI(537329),             --S2720-28TP-EI        Metro Service Platform for V2R11,modify name
          modify: bname8031S2720-28TP-PWR-EI(537332),            --S2720-28TP-PWR-EI       Metro Service Platform for V2R11,modify name

          add: bnameET1D2L16QX2H(700476),    --16-Port 40GE QSFP+ Interface Card(X2H,QSFP+) for 12700 v2r11
          add: bnameET1D2C08HX2H(700477),    --8-Port 100GE QSFP28 Interface Card(X2H,QSFP28) for 12700 v2r11
          add: bnameES1D2L16QX2H(663631),    --16-Port 40GE QSFP+ Interface Card(X2H,QSFP+) for 7700 v2r11
          add: bnameES1D2C08HX2H(663632),    --8-Port 100GE QSFP28 Interface Card(X2H,QSFP28) for 7700 v2r11
          add: bnameLE1D2L16QX2H(659665),    --16-Port 40GE QSFP+ Interface Card(X2H,QSFP+) for 9310 v2r11
          add: bnameLE1D2C08HX2H(659666),    --8-Port 100GE QSFP28 Interface Card(X2H,QSFP28)  for 9310 v2r11
          "

        REVISION    "201707030000Z"
        DESCRIPTION "V7.57,
                     Add: virent8090DEVCR5DE2NLFX71(564920), --CR5DE2NLFX71, 2-Port 100GBase-QSFP28 + 24-Port 10GBase LAN/WAN-SFP+ Integrated Line Processing Unit (LPUI-480)
                     Add: virent8090DEVCR5DE2NLFX72(564921), --CR5DE2NLFX72, 2-Port 100GBase-QSFP28 + 24-Port 10GBase LAN/WAN-SFP+ Integrated Line Processing Unit B(LPUI-480-B)
                     Add: virent8090DEVCR5DE2NLFX73(564922), --CR5DE2NLFX73, 2-Port 100GBase-QSFP28 + 24-Port 10GBase LAN/WAN-SFP+ Integrated Line Processing Unit L(LPUI-480-L)
                     Add: virent8090DEVCR5D00E4NB70(564923), --CR5D00E4NB70, 4-Port 100GBase-QSFP28 Integrated Line Processing Unit (LPUI-480)
                     Add: virent8090DEVCR5D00E4NB7B(564924), --CR5D00E4NB7B, 4-Port 100GBase-QSFP28 Integrated Line Processing Unit B(LPUI-480-B)
                     Add: virent8090DEVCR5D00E4NB7C(564925), --CR5D00E4NB7C, 4-Port 100GBase-QSFP28 Integrated Line Processing Unit L(LPUI-480-L)
                     Add: virentME60DEVME0DE2NLEX7C(564926), --ME0DE2NLEX7C, 2-Port 100GBase-QSFP28 + 20-Port 10GBase LAN/WAN-SFP+ Broadband Service Unit Integrated(BSUI-400)
                     Add: subbnameME0D00SP8071(159816),      --ME0D00SP8071 Versatile Service Unit Sub Card(SP80-M)
                     Add: subbnameME0D00SPD071(159815),      --ME0D00SPD071 Versatile Service Unit Sub Card(SP160-M)
                     "

        REVISION    "201706290000Z"
        DESCRIPTION "V7.56,
                     Add: fnameEF1BS7905S00(712704),              -- HUAWEI S7905 FRAME
                     Add: fnameEF1BS7908S00(712705),              -- HUAWEI S7908 FRAME
                     Add: bnameEF1D2S48TE3E(712706),        -- s7900 12-Port 100/1000BASE-X Interface Card and 36-Port 10/100/1000BASE-T(E3E,SFP/RJ45)
                     Add: bnameEF1D2G48TE3E(712707),        -- s7900 48-Port 10/100/1000BASE-T Interface Card(E3E,RJ45)
                     Add: bnameEF1D2G48TE3S(712708),        -- s7900 48-Port 10/100/1000BASE-T Interface Card(E3S,RJ45)
                     Add: bnameEF1D2G48SE3E(712709),        -- s7900 48-Port 100/1000BASE-X Interface Card(E3E,SFP)
                     Add: bnameEF1D2G48SE3S(712710),        -- s7900 48-Port 100/1000BASE-X Interface Card(E3S,SFP)
                     Add: bnameEF1D2S08SX3S(712711),        -- s7900 8-Port 10GE SFP+ Interface and 24-Port GE SFP Interface Card(X3S,SFP+)
                     Add: bnameEF1D2S16SX3S(712712),        -- s7900 16-Port 10GE SFP+ Interface and 16-Port GE SFP Interface Card(X3S,SFP+)
                     Add: bnameEF1D2X48SX3S(712713),        -- s7900 48-Port 10GE SFP+ Interface Card(X3S,SFP+)
                     Add: bnameEF1D2MCUB000(712704),        -- S7905 Main Control Unit B
                     Add: bnameEF1D2SRUF000(712705),        -- S7908 Main Control Unit F


                     "

        REVISION    "201706270000Z"
        DESCRIPTION "V7.55,
                     Add: virentANJ0002CXP00(225595),       --  System Control,Cross-connect and Multi-protocol Process Unit with 360G.
                     Add: virentANK200CXPA00(225596),       --  System Control,Cross-connect and Multi-protocol Process Unit with 360G.
                     "

        REVISION    "201706241800Z"
        DESCRIPTION "V7.54,
                     Add: bnameH80DCSPE(155960),        --  --  64-channel POTS(combo) + Vectoring board of MA5600T device, Support SuperVector board.
                     "

        REVISION    "201706220000Z"
        DESCRIPTION "V7.53,
                     Add: fnameMA5800H901BPLD(148514),     -- Backplane of the MA5800
                     Add: fnameMA5608H802Mabr(147572),     -- Backplane of the P300 broadband medium-capacity master Frame: H802MABR
                     "

	REVISION    "201706210000Z"
        DESCRIPTION "V7.52,
                     Add: subbname8090DEVCR5D0E2NFE70(561730),        --03032LCN, CR5D0E2NFE70, 2-Port 100GBase-QSFP28 Flexible Card E(P480-E)
                     Add: subbname8090DEVCR58E4KCA0(537467),           --03032MYC, CR58E4KCA0, 4-Port 400GBase CFP8 Daughter Card
                     Add: subbname8090DEVCR58D8NCB0(537470),           --03032NAC, CR58D8NCB0, 8-Port 100G CFP2 flexible Dauhtger Card
                     Add: subbname8090DEVCR57EENBE0(537471),           --03032MWM, CR57EENBE0, 20-Port 100GBase QSFP28 Integrated Line Process Unit(NE40E LPUI-2T)
                      "

        REVISION    "201706160000Z"
        DESCRIPTION "V7.51,
                 Add:   virentME60ME0D0VSE0070(564918),      -- for V800R009C10 ME0D0VSE0070(SBOM),Value-added Service Engine Unit (VSE-A) 1.3.6.1.4.1.2011.20021210.15.564918
                 Add:   virent8090DEVCR5D0SRUA872(566111),    -- for V800R010C00 CR5D0SRUA872(SBOM),Switch and Route Processing Unit A8(16G Memory) 1.3.6.1.4.1.2011.20021210.15.566111
                 Add:   virent8090DEVCR5DSFUIM17C(566112),    -- for V800R010C00 CR5DSFUIM17C(SBOM),480Gbps Switch Fabric Unit C(SFUI-480-C) 1.3.6.1.4.1.2011.20021210.15.566112
                 Add:   virent8090DEVCR5DSFUIM17B(566113),    -- for V800R010C00 CR5DSFUIM17B(SBOM),480Gbps Switch Fabric Unit B(SFUI-480-B) 1.3.6.1.4.1.2011.20021210.15.566113)

                 Add:   virent8090DEVCR5DLPUFME71(565001),      -- for V800R10C00 CR5DLPUFME71(SBOM)	Flexible Card Line Processing Unit E(LPUF-480-E)
                 Add:   virent8090DEVCR5DLPUFK071(565002),      -- for V800R10C00 CR5DLPUFK071(SBOM)	Flexible Card Line Processing Unit E(LPUF-400-E)
                 Add:   virent8090DEVCR5DLPUFM071(565003),      -- for V800R10C00 CR5DLPUFM071(SBOM)	Flexible Card Line Processing Unit(LPUF-480)
                 Add:   virent8090DEVCR5DLPUFM17B(565004),      -- for V800R10C00 CR5DLPUFM17B(SBOM)	Flexible Card Line Processing Unit B(LPUF-480-B)
                 Add:   virent8090DEVCR5D00LMXF71(565005),      -- for V800R10C00 CR5D00LMXF71(SBOM)	48-Port 10GBase LAN/WAN-SFP+ Integrated Line Processing Unit (LPUI-480)
                 Add:   virent8090DEVCR5DE2NLFX74(565006),      -- for V800R10C00 CR5DE2NLFX74(SBOM)	2-Port 100GBase-CFP2 + 24-Port 10GBase LAN/WAN-SFP+ Integrated Line Processing Unit (LPUI-480)
                 Add:   virent8090DEVCR5D00E4NC71(565007),      -- for V800R10C00 CR5D00E4NC71(SBOM)	4-Port 100GBase-CFP2 Integrated Line Processing Unit (LPUI-480)
                 Add:   virent8090DEVCR5D01LMXF7B(565008),      -- for V800R10C00 CR5D01LMXF7B(SBOM)	48-Port 10GBase LAN/WAN-SFP+ Integrated Line Processing Unit B(LPUI-480-B)
                 Add:   virent8090DEVCR5DE2NLFX75(565009),      -- for V800R10C00 CR5DE2NLFX75(SBOM)	2-Port 100GBase-CFP2 + 24-Port 10GBase LAN/WAN-SFP+ Integrated Line Processing Unit B(LPUI-480-B)
                 Add:   virent8090DEVCR5D01E4NC7B(565010),      -- for V800R10C00 CR5D01E4NC7B(SBOM)	4-Port 100GBase-CFP2 Integrated Line Processing Unit B(LPUI-480-B)
                 Add:   virent8090DEVCR5D01LMXF7C(565011),      -- for V800R10C00 CR5D01LMXF7C(SBOM)	48-Port 10GBase LAN/WAN-SFP+ Integrated Line Processing Unit L(LPUI-480-L)
                 Add:   virent8090DEVCR5DE2NLFX76(565012),      -- for V800R10C00 CR5DE2NLFX76(SBOM)	2-Port 100GBase-CFP2 + 24-Port 10GBase LAN/WAN-SFP+ Integrated Line Processing Unit L(LPUI-480-L)
                 Add:   virent8090DEVCR5D01E4NC7C(565013),      -- for V800R10C00 CR5D01E4NC7C(SBOM)	4-Port 100GBase-CFP2 Integrated Line Processing Unit L(LPUI-480-L)
                 Add:   virent8090DEVCR5D00D4NC71(565014),      -- for V800R10C00 CR5D00D4NC71(SBOM)	4-Port 100GBase-CFP2 DWDM Integrated Line Processing Unit(LPUI-480)
                 Add:   virent8090DEVCR5D00E4NC7Q(565015),      -- for V800R10C00 CR5D00E4NC7Q(SBOM)	4-Port 100G ETH/DWDM-CFP2 Integrated Line Processing Unit CM(LPUI-480-CM)

                 Add:   virent8090DEVCR9D00EKNB80(562055), -- 40-Port 100GBase QSFP28 Integrated Line Process Unit(NE9000 LPUI-4T)
                 Add:   virent8090DEVCR9D00EKNB8P(562056), -- 40-Port 100GBase QSFP28 Integrated Line Process Unit CM(NE9000 LPUI-4T-CM)
                 Add:   virent8090DEVCR9D00EKNB8L(562057)  -- 40-Port 100GBase QSFP28 Integrated Line Process Unit L(NE9000 LPUI-4T-L)
                    "

       REVISION    "201706100000Z"
        DESCRIPTION "V7.50,
                 Add:   virent8090DEVCR5D00EDNB61(562083),   -- 16-Port 100GBase-QSFP28 Integrated Line Process Unit B (NE5000E LPUI-2T-B)
                modify:virent8090DEVCR5D0MPUN080(562040)  to virent8090DEVCR9D0MPUN180(562040)
                    "


       REVISION    "201706090000Z"
        DESCRIPTION "V7.49,
                     Add: subbname8090DEVCR5D00E5MF6B(537468),    -- 5-Port 40GBase-QSFP+ Flexible Card B(CP400,Occupy 1 sub-slot)
                     Add: subbname8090DEVCR5D00LEXF6B(537469),    -- 20-Port 10GBase LAN/WAN-SFP+ Flexible Card B(CP400,Occupy 1 sub-slot)

                      "


       REVISION    "201706080000Z"
        DESCRIPTION "V7.48,
                    add:fname8031S2320-52TP-EI-DC(537206) to fname8031S5730S-68C-PWR-EI(537211)  for lsw v2r11c10
                    add:bname8031S2320-52TP-EI-DC(537390) to bname8031S5730S-68C-PWR-EI(537395)  for lsw v2r11c10
                    add:fname8031S5330-36C-HI(537216)  to fname8031S6320-30L-HI-24S(537230)   for lsw v2r11c50
                    add:bname8031S5330-36C-HI(537400) to bname8031S6320-30L-HI-24S(537414)  for lsw v2r11c50
                    add:subbnameES2D1POE4800(536784)   for lsw v2r11c50
                    add:subbnameES2D1POE2403(536785)  for lsw v2r11c50
                    add:subbnameES5D21Q06Q00(536786)  for lsw v2r11c50
                    add:subbnameES5D2CKM0000(536787)  for lsw v2r11c50

                      "

       REVISION    "201705240000Z"
        DESCRIPTION "V7.47,
                     add:bnameLE1D2G48SX1C(659664),      --48-Port 100/1000BASE-X Interface Card(X1C,SFP) for V2R11

                      "


        REVISION    "201705190914Z"
        DESCRIPTION "V7.46,
                      add wlan device
                      ADD: fnameAP1050DN-S(692298),           --WLAN new ap ENUM_

                      "

        REVISION    "201705160000Z"
        DESCRIPTION "V7.45,
                     add:fname8031S5730-52X-PWH-SI-ACF(537203),       --98010786	S5730-52X-PWH-SI-ACF add for lsw v2r11c10
                     add:fname8031S5730-56C-PWH-SI-AC(537204),        --98010785	S5730-56C-PWH-SI-AC  add for lsw v2r11c10
                     add:fname8031S5730-32C-PWH-SI-AC(537205),        --98010787	S5730-32C-PWH-SI-AC  add for lsw v2r11c10

                     add:bname8031S5730-52X-PWH-SI-ACF(537387),       --98010786	S5730-52X-PWH-SI-ACF add for lsw v2r11c10
                     add:bname8031S5730-56C-PWH-SI-AC(537388),        --98010785	S5730-56C-PWH-SI-AC  add for lsw v2r11c10
                     add:bname8031S5730-32C-PWH-SI-AC(537389),        --98010787	S5730-32C-PWH-SI-AC  add for lsw v2r11c10

                      "

        REVISION    "201705110000Z"
        DESCRIPTION "V7.44,
                     Add: subbname8090DEVCR5DE2VE1N70(537466),      --03032MVX, CR5DE2VE1N70, 2-Port 50GBase/1-Port 100GBase-QSFP28 FlexE Flexible Card (P120)
                     Add: subbname8090DEVCR5D00E25F10(561640),       --03032QNG, CR5D00E25F10, 2 Port 50G Base QSFP28 High Speed Interface Card
                     Add: subbname8090DEVCR58EENBA0(537465),           --03032MYU, CR58EENBA0,20*100GBase QSFP28 flexible Dauhtger Card
                     Add: subbnameATNANJ1EV2(564531),                              --03057706, ATNANJ1EV2, 2 Port 50GBase QSFP28 High Speed Interface Card
                     Add: subbnamePTN990TPJ1EV2(229506),                       --03057714,TPJ1EV2 , 2 Port 50G Base-Qsfp28 High-Speed Interface Card
                      "

        REVISION    "201705090000Z"
        DESCRIPTION "V7.43,
                     Add: bnameH902XSED(148623),        --  8*10G GPON board of MA5800.
                     Add: bnameH901DSHD(148624),        --  8*GE and 10GE combo board of MA5800.
                     Add: bnameH901OGHF(148625),        --  16 P2P board of MA5800.
                     Add: bnameH901OXHG(148626),        --  24*10GE board of MA5800.
                     Add: bnameH901NXLC(148627),        --  4*10GE board of MA5800.
                      "

        REVISION    "201705020000Z"
        DESCRIPTION "V7.42,
                     Add:fnamePTN7900TPD1CHASSIS(229408),   --PTN 7900E-32 Integrated Chassis Components
                     Add:bnamePTN7900TPB3CXP(229439), --TPB3CXP,System Control, Cross-Connect and Timing Unit,1*1
                     Add:bnamePTN7900TPC2CXP(229440), --TPC2CXP,System Control, Cross-Connect and Timing Unit,1*1
                     Add:bnamePTN7900TPA2SCA(229441), --TPA2SCA,System Control, Communication and Auxiliary Processing Unit,1*1
                     Add:bnamePTN7900TPD1SCA(229442), --TPD1SCA,System Control, Communication and Auxiliary Processing Unit,1*1
                     Add:bnamePTN7900TPB3XCS(229443), --TPB3XCS,Switch Fabric Unit,1*1
                     Add:bnamePTN7900TPC2XCS(229444), --TPC2XCS,Switch Fabric Unit,1*1
                     Add:bnamePTN7900TPD1XCS(229445), --TPD1XCS,Switch Fabric Unit,1*1
                     Add:bnamePTN7900TPA4EH1(229446), --TPA4EH1,1-Port 100GE Switching Processing Board
                     Add:bnamePTN7900TPA1EH4(229447), --TPA1EH4,4-Port 100GE Switching Processing Board
                     Add:bnamePTN7900TPD1EHL2(229448), --TPD1EHL2,2-Port 400GE Switching Processing Board
                     Add:bnamePTN7900TPD1PIU(229449), --TPD1PIU,Power Interface Unit
                     Add:bnamePTN7900TPD1FAN(229450), --TPD1FAN,Fan Board
                     Add:bnamePTN7900TPD1EFI(229451), --TPD1EFI,EMI Filter Interface Board
                     Add:bnamePTN7900TPA1EV2(229452), --TPA1EV2,2-Port 50GE Switching Processing Board
                     Add:virentPTN7900TPB3VXCS(229484),      --TPB3VXCS, Switch Fabric Unit Board,1*1
                     Add:virentPTN7900TPC2VXCS(229485),      --TPC2VXCS, Switch Fabric Unit Board,1*1
                    "


       REVISION    "201704220000Z"
        DESCRIPTION "V7.41,
                     --for CloudEngine 20170422
                     Add:                fnameCE688048S4Q2CQEI(688163),           -- CloudEngine CE6880-48S4Q2CQ-EI Switch(48*10G SFP+,6*40G QSFP+ or 44*10G SFP+,4*40G QSFP+,2*100G QSFP28)
                     Add:                fnameCE688024S4Q2CQEI(688164),           -- CloudEngine CE6880-24S4Q2CQ-EI Switch(24*10G SFP+,4*40G QSFP+,2*100G QSFP28)
                     Add:                fnameCE688048T4Q2CQEI(688165),           -- CloudEngine CE6880-48T4Q2CQ-EI Switch(48*10G RJ45,6*40G QSFP+ or 44*10G RJ45,4*40G QSFP+,2*100G QSFP28)
                     Add:                fnameCE12816M(688170),                   -- CE12816M DC Assembly Chassis
                     Add:                fnameCE885032CQEI(688171),               -- CloudEngine CE8850-32CQ-EI Switch(32-Port 100GE QSFP28,2-Port 10GE SFP+)
                     Add:                fnameCE12804E(688166),                   -- CE12804E Assembly Chassis
                     Add:                fnameCE12808E(688167),                   -- CE12808E Assembly Chassis
                     Add:                fnameCE12812E(688168),                   -- CE12812E Assembly Chassis
                     Add:                fnameCE12816E(688169),                   -- CE12816E Assembly Chassis
                     Add:                fnameCE687048T6CQEI(688172),             -- CloudEngine 6800,CE6870-48T6CQ-EI,CE6870-48T6CQ-EI Switch(48-Port 10GE RJ45,6-Port 100GE QSFP28)
                     Add:                bnameCE688048S4Q2CQEI(688235),           -- Manufactured Board,CloudEngine 6800,CEM48S4Q2CQP01,48-Port SFP+ Optical,4-Port 40GE QSFP+ Optical,2-Port 100GE QSFP28 Optical Switch Control Unit,1*1
                     Add:                bnameCE688024S4Q2CQEI(688236),           -- Manufactured Board,CloudEngine 6800,CEM24S4Q2CQP01,24-Port SFP+ Optical,4-Port 40GE QSFP+ Optical,2-Port 100GE QSFP28 Optical Switch Control Unit,1*1
                     Add:                bnameCE688048T4Q2CQEI(688237),           -- Manufactured Board,CloudEngine 6800,CEM48T4Q2CQP01,48-Port 10GE RJ45,4-Port 40GE QSFP+ Optical,2-Port 100GE QSFP28 Optical Switch Control Unit,1*1
                     Add:                bnameCESFU16GM(688238),                  -- Manufactured Board,CloudEngine 12800,CE-SFU16G-M,CE12816M Switch Fabric Unit G
                     Add:                bnameCEL36CQFDM(688239),                 -- Manufactured Board,CloudEngine 12800,CEL36CQFD-M,36-Port-100GE Interface Card(FD-M,QSFP28)
                     Add:                bnameCEL36LQFDM(688240),                 -- Manufactured Board,CloudEngine 12800,CEL36LQFD-M,36-Port-40GE Interface Card(FD-M,QSFP+)
                     Add:                bnameCEL24LQFDM(688241),                 -- Manufactured Board,CloudEngine 12800,CEL24LQFD-M,24-Port-40GE Interface Card(FD-M,QSFP+)
                     Add:                bnameCEL12CQFDM(688242),                 -- Manufactured Board,CloudEngine 12800,CEL12CQFD-M,12-Port-100GE Interface Card(FD-M,QSFP28)
                     Add:                bnameCEL48XSFDAM(688243),                -- Manufactured Board,CloudEngine 12800,CEL48XSFDA-M,48-Port-10GE,2-Port-40GE,2-Port-100GE Interface Card(FDA-M,SFP+,QSFP+,QSFP28)
                     Add:                bnameCEL48XSFDM(688244),                 -- Manufactured Board,CloudEngine 12800,CEL48XSFD-M,48-Port-10GE Interface Card(FD-M,SFP+)
                     Add:                bnameCE885032CQEI(688245),               -- Manufactured Board,CloudEngine 8800,CEM32CQP01,32-Port 100GE QSFP28,2-Port 10GE SFP+ Optical Switch Control Unit,1*1
                     Add:                bnameCESFU08G(688246),                   -- Manufactured Board,CloudEngine 12800,CE-SFU08G,CE12808 Switch Fabric Unit G,1*1
                     Add:                bnameCESFU04G(688247),                   -- Manufactured Board,CloudEngine 12800,CE-SFU04G,CE12804 Switch Fabric Unit G,1*1
                     Add:                bnameCESFU16CE(688248),                  -- Manufactured Board,CloudEngine 12800,CESFU16CE,CE12816E Switch Fabric Unit C,1*1
                     Add:                bnameCESFU12CE(688249),                  -- Manufactured Board,CloudEngine 12800,CESFU12CE,CE12812E Switch Fabric Unit C,1*1
                     Add:                bnameCESFU08CE(688250),                  -- Manufactured Board,CloudEngine 12800,CESFU08CE,CE12808E Switch Fabric Unit C,1*1
                     Add:                bnameCESFU04CE(688251),                  -- Manufactured Board,CloudEngine 12800,CESFU04CE,CE12804E Switch Fabric Unit C,1*1
                     Add:                bnameCEL16CQEGE(688252),                 -- Manufactured Board,CloudEngine 12800E,CEL16CQEG-E,16-Port-100GE Interface ENP Card(EG,QSFP28)
                     Add:                bnameCEL36LQEDE(688253),                 -- Manufactured Board,CloudEngine 12800E,CEL36LQED-E,36-Port-40GE Interface ENP Card(ED,QSFP+)
                     Add:                bnameCEL36LQEGE(688254),                 -- Manufactured Board,CloudEngine 12800E,CEL36LQEG-E,36-Port-40GE Interface ENP Card(EG,QSFP+)
                     Add:                bnameCEL48XSEGAE(688255),                -- Manufactured Board,CloudEngine 12800,CEL48XSEGA-E,48-Port-10GE,4-Port-100GE Interface Card(NGA,SFP+,QSFP28)
                     Add:                bnameCEL24XSEGAE(688256),                -- Manufactured Board,CloudEngine 12800E,CEL24XSEGA-E,24-Port-10GE,2-Port-100GE Interface ENP Card(EGA,SFP+,QSFP28)
                     Add:                bnameCEL48XSEDE(688257),                 -- Manufactured Board,CloudEngine 12800E,CEL48XSED-E,48-Port 10GBASE-X Interface ENP Card(ED,SFP+)
                     Add:                bnameCEL24XSEDE(688258),                 -- Manufactured Board,CloudEngine 12800E,CEL24XSED-E,24-Port 10GBASE-X Interface ENP Card(ED,SFP+)
                     Add:                bnameCEMPUAE(688259),                    -- Manufactured Board,CloudEngine 12800E,CE-MPUA-E,CE12800E Main Processing Unit A,1*1
                     Add:                bnameSIAMESEDFAN(688262),                -- CloudEngine 12800E,Siamesedfan
                     Add:                bnameVERTICALPOW(688263),                -- CloudEngine 12800E,Power Module for CE12808E,CE12812E and CE12816E
                     Add:                bnameCE687048T6CQEI(688265),             -- Manufactured Board,CloudEngine 6800,CEM48T6CQP01,48-Port 10GE RJ45,6-Port 100GE QSFP28 Optical Switch Control Unit,1*1
                     "


		REVISION    "201704110000Z"
        DESCRIPTION "V7.40,
                    Add: bnameLE1D2S04SX1C(659662) for lsw V2R11
                    Add: bnameLE1D2G48TX1C(659663) for lsw V2R11
                      "


		REVISION    "201704070930Z"
        DESCRIPTION "V7.39,
                     Add: fnameEA5821-GE(561638),	--Virtual frame H821MABC of the EA5821 GE(8/16/24) device.
                     Add: fnameEA5821-GE-POE(561639),	--Virtual Frame H821MABC of the EA5821 GE(24) POE device.
                      "

        REVISION    "201704060930Z"
        DESCRIPTION "V7.38,
                     Add: virent8090DEVCR5DNPU1TM71(675868),   -- for V800R010C00 CR5DNPU1TM71(SBOM),Network Processing Unit (NPU-1T)
                     Add: virent8090DEVCR5DNPU1TM70(675867),   -- for V800R010C00 CR5DNPU1TM70(SBOM),Network Processing Unit (NPU-1T)
                      "

	      REVISION    "201703290930Z"
        DESCRIPTION "V7.37,
                     Add: bnameH902MPLAE(148619),        --  control board of EA5800.
                     Add: bnameH901MPSCE(148620),        --  control board of EA5800-X2.
                     Add: bnameH901GPSFE(148621),        --  16*GPON board of EA5800.
                     Add: bnameH901XGHDE(148622),        --  8*10G GPON board of EA5800.
                      "

            REVISION    "201703280000Z"
        DESCRIPTION "V7.36,
                     Add: virent8090DEVCR5DLPUFE07B(564915)    -- for V800R009C10 CR5DLPUFE07B(SBOM),Flexible Card Line Processing Unit B(LPUF-200-B)

                     add wlan device
                     ADD: fnameAP8050DN(692295),           --WLAN new ap ENUM_
                     ADD: fnameAP8050DN-S(692296),         --WLAN new ap ENUM_
                     ADD: fnameAP8150DN(692297),           --WLAN new ap ENUM_7455
                     "

	    REVISION    "201703220000Z"
        DESCRIPTION "V7.35,
                     Add: bnameH901GPLF(148615),         --  16*GPON board of MA5800
                     Add: bnameH901XGLD(148616),         --  8*10G GPON board of MA5800
                     Add: bnameH901XGLF(148617),         --  16*10G GPON board of MA5800
                     Add: bnameH901XELD(148618),         --  8*10G EPON board of MA5800
                     "

	    REVISION    "201703210000Z"
        DESCRIPTION "V7.34,
                     Add: virent8090DEVCR9D00EDNB8P(562070),  --16-Port 100GBase-QSFP28 Integrated Line Process Unit(NE9000 LPUI-2T-PC)
                     Add: virent8090DEVCR9D00E8NC8P(562071),  --8-Port 100GBase-CFP2 Integrated Line Process Unit(LPUI-1T-PC)
                     Add: virent8090DEVCR9D00D8NC8P(562072),  --8-Port 100GBase-CFP DWDM Integrated Line Process Unit(LPUI-1T-PC)
                     Add: virent8090DEVCR9D00EPXF8P(562073),  --60-Port 10GBase LAN/WAN-SFP+ Integrated Line Process Unit(LPUI-1T-PC)
                     Add: virent8090DEVCR5D00LKXF6P(562074),  --40-Port 10GBase LAN/WAN-SFP+ Integrated Line Process Unit (NE5000E LPUI-400-PC)
                     Add: virent8090DEVCR5D00EDNB6P(562075),  --16-Port 100GBase-QSFP28 Integrated Line Process Unit (NE5000E LPUI-2T-PC)

                     --for v8r9c10 NE9000 20170310
                     Add: subbname8090DEVCR9D00LFXF80(537455),    -- 24-Port 1000M/10GBase LAN/WAN-SFP+ Flexible Card
                     Add: subbname8090DEVCR9D00NBXF80(537456),    -- 12-Port 10G OTN/ETH-SFP+ Flexible Card
                     Add: subbname8090DEVCR9D00N6XF80(537457),    -- 6-Port 10G OTN/ETH-SFP+ Flexible Card
                     Add: subbname8090DEVCR9D00P8UF80(537458),    -- 8-Port OC-48/12/3 STM-16/4/1 POS-SFP Flexible Card
                     Add: subbname8090DEVCR9D00P4XX80(537459),    -- 4-Port OC-192/STM-64 POS-XFP Flexible Card

                     --for v8r9c10 License 20170310
                     Add: subbname8090DEVCR57EFGFH3(537460),    -- 24-Port 1000Base-X-SFP Fixed Card E
                     Add: subbname8090DEVCR57L6XFI02(537461),   -- 6-Port 10GBase LAN/WAN-SFP+ Fixed Card E
                     Add: subbname8090DEVCR57LBXFE2(537462),    -- 12-Port 10GBase LAN/WAN-SFP+ Fixed Card E
                     Add: subbname8090DEVCR57E8NCB1(537463),    -- 8*100Gbps CFP2 Interface Board
                     "

		REVISION    "201703200000Z"
        DESCRIPTION "V7.33,
                     Add: virentANGMHSTA0311(225592),       --ATN 910C-A,ANGM13HSTA,ATN 910C-A AC+DC system, with 4*10GE(o), 8*10GE/GE/FE(o), 16*GE/FE(o)
                     Add: virentANGMHSTB0311(225593),       --ATN 910C-B,ANGM13HSTB,ATN 910C-B AC+DC system,with 4*10GE(o), 8*10GE/GE/FE(o), 8*GE/FE(o), 8*GE/FE(e)
                     Add: virentANGMHSTD0311(225594),       --ATN 910C-D,ANGM13HSTD,ATN 910C-D AC+DC system,with 4*10GE(o),8*10GE/GE/FE(o),8*GE/FE(e),16E1
                     "

        REVISION    "201703100000Z"
        DESCRIPTION "V7.32,
                     --for V8R9C10 20170310
                     Add: bnameH801XP1A(155958),                         -- 1-port XG-PON/XGS-PON interface board
                     Add: subbnameH901TPUA(148601),                   -- TPM subboard of MA5800 H902MPLA
                     "

	REVISION    "201703040000Z"
        DESCRIPTION "V7.31,
                     --for V8R9C10 20170304
                     Add: virent8090DEVCR9DLPUFK080(562054),   -- NE9000 LPUF-400 CR9DLPUFK080
                     "

        REVISION    "201702280000Z"
        DESCRIPTION "V7.30,
                     --for V8R9C10 20170228
                     Add: virent8090DEVCR5D00D4NT70(564824),  -- for V800R009C10 CR5D00D4NT70 ,4-Port 100GBase-CFP2 DWDM Integrated Line Processing Unit (LPUI-480) 1.3.6.1.4.1.2011.20021210.15.564824
                     Add: virent8090DEVCR5D0EMGFA7P(564910),   -- for V800R009C10 CR5D0EMGFA7P(SBOM),48-Port 100/1000Base-X-SFP Integrated Line Processing Unit PC(LPUI-51-PC))
                     Add: virent8090DEVCR5D00LBXF7P(564911),   -- for V800R009C10 CR5D00LBXF7P(SBOM),12-Port 10GBase LAN/WAN-SFP+ Integrated Line Processing Unit PC(LPUI-120-PC)
                     Add: virent8090DEVCR5DL6XEFG7P(564912),   -- for V800R009C10 CR5DL6XEFG7P(SBOM),6-Port 10GBase LAN/WAN-SFP+ + 24-Port 100/1000Base-X-SFP Integrated Line Processing Unit PC(LPUI-120-PC)
                     Add: virent8090DEVCR5D00LFXF7P(564913),   -- for V800R009C10 CR5D00LFXF7P(SBOM),24-Port 10GBase LAN/WAN-SFP+ Integrated Line Processing Unit PC(LPUI-240-PC)
                     Add: virent8090DEVCR5D00E8NC7P(564914)    -- for V800R009C10 CR5D00E8NC7P(SBOM),8-Port 100GBase-CFP2 Integrated Line Processing Unit PC(LPUI-1T-PC)

                     --for V8R10C00 20170228
					 Add: fname8090NE9000-8(562054),       --Quidway NE9000-8 FRAME
                     Add: virent8090DEVCR9D0MPUP180(564905),    -- V8R10C00 for CR9D0MPUP180(SBOM) NE9000-8 Main Processing Unit P1(MPUP1)
                     Add: virent8090DEVCR9D0SFUT481(564906),   -- V8R10C00 for CR9D0SFUT481(SBOM) NE9000-8 Switch Fabric Unit for Single Chassis(SFU4T-A)
                     "

        REVISION    "201702200000Z"
        DESCRIPTION "V7.29,
                     --for PTN7900 V1R8C10 20170220
                     Add:  bnamePTN7900TPA1EV4(229438), --TPA1EV4,4-port 50 Gigabit Ethernet Switching Processing Board
                     "
        REVISION    "201702141000Z"
        DESCRIPTION "V7.28,
                     Add: bnameH802X2CS(148015),         --  10GE synchronized Ethernet interface board
                     Add: bnameH801GPND(148016),         --  8GPON board of MA5600T
                     "

        REVISION    "201702100000Z"
        DESCRIPTION "V7.27,
                     Add: fnameAR505Ke-L(667881),        -- AR505Ke-L FRAME
                     Add: fnameAR2504-D-H(667882),       -- AR2504-D-H FRAME
                     Add: fnameAR502EGRb-L(667883),      -- AR502EGRb-L FRAME
                     Add: fnameAR169CVW-4B4S(667884),    -- AR169CVW-4B4S FRAME
                     Add: fnameAR169CVW(667885),         -- AR169CVW FRAME
                     Add: fnameAR169EGW-L(667886),       -- AR169EGW-L FRAME
                     Add: fnameAR169EW(667887),          -- AR169EW FRAME
                     Add: fnameAR161EW(667888),          -- AR161EW FRAME
                     Add: fnameAR161EW-M1(667889),       -- AR161EW-M1 FRAME
                     Add: fnameAR509CGW-L(667890),       -- AR509CGW-L FRAME
                     Add: fnameAR509CG-Lt-7(667891),     -- AR509CG-Lt-7 FRAME
                     Add: fnameAR-Sc-Lc(667892),         -- AR-Sc-Lc FRAME
                     Add: fnameAR-Sc-Le(667893),         -- AR-Sc-Le FRAME
                     Add: fnameAR-Sc-La(667894),         -- AR-Sc-La FRAME
                     Add: fnameAR502ER(667895),          -- AR502ER FRAME
                     Add: fnameAR169FGVW-L-8S(667896),   -- AR169FGVW-L-8S FRAME
                     Add: fnameAR502ERb(667897),         -- AR502ERb FRAME
                     Add: fnameAAR502EGRc-Lc(667898),    -- AR502EGRc-Lc FRAME

                     Add: bnameAR505Ke-L(667978),               -- AR505Ke-L Main Unit
                     Add: bnameAR2504-D-H(667979),              -- AR2504-D-H Main Unit
                     Add: bnameAR502EGRb-L(667980),             -- AR502EGRb-L Main Unit
                     Add: bnameAR169CVW-4B4S(667981),           -- AR169CVW-4B4S Main Unit
                     Add: bnameAR169CVW(667982),                -- AR169CVW Main Unit
                     Add: bnameAR169EGW-L(667983),              -- AR169EGW-L Main Unit
                     Add: bnameAR169EW(667984),                 -- AR169EW Main Unit
                     Add: bnameAR161EW(667985),                 -- AR161EW Main Unit
                     Add: bnameAR161EW-M1(667986),              -- AR161EW-M1 Main Unit
                     Add: bnameAR509CGW-L(667987),              -- AR509CGW-L Main Unit
                     Add: bnameAR509CG-Lt-7(667988),            -- AR509CG-Lt-7 Main Unit
                     Add: bnameAR-Sc-Lc(667989),                -- AR-Sc-Lc Main Unit
                     Add: bnameAR-Sc-Le(667990),                -- AR-Sc-Le Main Unit
                     Add: bnameAR-Sc-La(667991),                -- AR-Sc-La Main Unit
                     Add: bnameAR502ER(667992),                 -- AR502ER Main Unit
                     Add: bnameAR169FGVW-L-8S(667993),          -- AR169FGVW-L-8S Main Unit
                     Add: bname1LTE-Lt-7(667994),               -- 1LTE-Lt-7 Control Unit
                     Add: bnameAR502ERb(667995),                -- AR502ERb Main Control Unit
                     Add: bnameAR502EGRc-Lc(667996),            -- AR502EGRc-Lc Main Control Unit

		     add wlan device
		     ADD: fnameAP4051DN(692290),           --WLAN new ap ENUM_
                     ADD: fnameAP4050DN(692291),           --WLAN new ap ENUM_
                     ADD: fnameAP4151DN(692292),           --WLAN new ap ENUM_
                     ADD: fnameAP4051DN-S(692293),         --WLAN new ap ENUM_
                     ADD: fnameAP4050DN-S(692294),         --WLAN new ap ENUM_
                     "

        REVISION    "201701260000Z"
        DESCRIPTION "V7.26,
                     Add: fname8031S5720-28P-LI-AC-SEA(537192) to fname8031S5320-52P-PWR-LI-AC-SEA(537199) for LSW V2R10C00 support license for oversea
                     Add: bname8031S5720-28P-LI-AC-SEA(537376) to bname8031S5320-52P-PWR-LI-AC-SEA(537383) for LSW V2R10C00 support license for oversea
                     Add: bnameLE1D2S08SX2E(659661) for lsw V2R11
                     Add: fname8031S5320-12P-LI-BAT(537200),fname8031S5330-68C-SI(537201),fname8031S5730-68C-PWR-SI(537202) for lsw V2R11C10
                     Add: bname8031S5320-12P-LI-BAT(537384),bname8031S5330-68C-SI(537385),bname8031S5730-68C-PWR-SI(537386) for lsw V2R11C10
                     Add: subbnameFAN040CB(536783),              --FAN for 6720SI
                     "



        REVISION    "201701230000Z"
        DESCRIPTION "V7.25,
                     Add:  virentME60DEVME0D0L8NCA70(161606),   -- for V800R009C00 ME0D0L8NCA70(SBOM),8-Port 100GBase-CFP2 Multi Service Unit Integrated(MSUI-1T) 1.3.6.1.4.1.2011.20021210.15.161606
                     Add:  virentME60DEVME0D0L4NCB70(161607),   -- for V800R009C00 ME0D0LKXFB70(SBOM),4-Port 100GBase-CFP2 Broadband Service Unit Integrated(BSUI-400) 1.3.6.1.4.1.2011.20021210.15.161607
                     Add:  virentME60DEVME0D0L2NCB70(161608),   -- for V800R009C00 ME0DE2NLEX7B(SBOM),2-Port 100GBase-CFP2 Broadband Service Unit Integrated(BSUI-200) 1.3.6.1.4.1.2011.20021210.15.161608
                     Add:  virentME60DEVME0D0LFXFA70(161610),   -- for V800R009C00 ME0D0LEXFB70(SBOM),24-Port 10GBase LAN/WAN-SFP+ Multi Service Unit Integrated(MSUI-240) 1.3.6.1.4.1.2011.20021210.15.161610
                     Add:  virentME60DEVME0D0LMXFA70(161611),   -- for V800R009C00 ME0D0E2NCB70(SBOM),48-Port 10GBase LAN/WAN-SFP+ Multi Service Unit Integrated(MSUI-480) 1.3.6.1.4.1.2011.20021210.15.161611
                     Add:  virentME60DEVME0DVSUF8073(161612),    -- for V600R009C10 ME0DVSUF8073(SBOM),Flexible Card Versatile Service Unit 80(VSUF-80-J)
                     Add:  virent8090DEVCR5DVSUF8011(161613)     -- for V600R009C10 CR5DVSUF8011(SBOM),Flexible Card Versatile Service Unit 80(VSUF-80-J)
                     "

        REVISION    "201612270000Z"
        DESCRIPTION "V7.24,
                     Add:  fnameMA5633H821MABCT(561571),              --MA5633  new frame  H821MABCT
                     Add:  bnameH822CCKRP(156065),             --  D3.0 32*10.
                     "

       REVISION    "201612240000Z"
        DESCRIPTION "V7.23,
                    for v2r11c00&C10 add 13 box device
                     Add:fname8031S6720-48Q-SI-48S-AC(537179) to fname8031S6320-52X-PWH-SI(537191),
                     Add:bname8031S6720-48Q-SI-48S-AC(537363) to bname8031S6320-52X-PWH-SI(537375),
                     modify fname8031S5730-56C-PWH-SI-AC(537175) to fname8031S6720-56C-PWH-SI-AC(537175)
                     modify fname8031S5730-56C-PWH-SI(537176) to fname8031S6720-56C-PWH-SI(537176)
                     modify fname8031S5730-56C-PWH-SI(537176) to fname8031S6320-56C-PWH-SI-AC(537177)
                     modify fname8031S5730-56C-PWH-SI(537176) to fname8031S6320-56C-PWH-SI(537178)

                     modify bname8031S5730-56C-PWH-SI-AC(537359) to bname8031S6720-56C-PWH-SI-AC(537359)
                     modify bname8031S5730-56C-PWH-SI(537360) to bname8031S6720-56C-PWH-SI(537360)
                     modify bname8031S5330-56C-PWH-SI-AC(537361) to bname8031S6320-56C-PWH-SI-AC(537361)
                     modify bname8031S5330-56C-PWH-SI(537362) to bname8031S6320-56C-PWH-SI(537362)
                     delete bnameLE1D2S08SX2E(659661)

                    "


        REVISION    "201612220000Z"
        DESCRIPTION "V7.22,
                    Add:subbnameME0D00SP8072(159814),    --Versatile Service Daught Card(SP80-T)
                    Add:virentME60DEVME0DVSUF8072(161605),   -- for V600R009C30 ME0DVSUF8072(SBOM),Flexible Card Versatile Service Unit 80(VSUF-80-T)
                    "

        REVISION    "201612130000Z"
        DESCRIPTION "V7.21,
                    Add:subbnamePTN990TPJ1EH1(229510),        --TPJ1EH1,1 Channel 100 GE Optical Interface Board
                    Add:subbnamePTN990TPL1EM4F(229511),        --Finished Board Unit,Optix PTN 930,TPL1EM4F0,4 Channels GE/FE Electrical Interface Board
                    Add:subbnamePTN990TPL1EM4T(229512),        --Finished Board Unit,Optix PTN 930,TPL1EM4T0,4 Channels GE/FE Electrical Interface Board
                    Add:subbnamePTN990TPL1ML1A(229513),        --Finished Board Unit,OptiX PTN 930,TPL1ML1A,16 Channels E1 Interface Board(75ohm)
                    Add:subbname8090DEVCR2D00EEGF11(561636), -- 20-Port 100/1000Base-X-CSFP Physical Interface Card(PIC)
                    Add:subbname8090DEVCX6D00EEGF10(561637), -- 20-Port 100/1000Base-X-CSFP Physical Interface Card(PIC)
                    "

        REVISION    "201612060000Z"
        DESCRIPTION "V7.20,
                     for v2r10c00 tr6 add 11 box device and 4 board
                     Add:fname8031S1720-28GWR-4P-E(537116),  to  fname8031S1720-10GW-PWR-2P-E(537126),
                     Add:bname8031S1720-28GWR-4P-E(537300),  to  bname8031S1720-10GW-PWR-2P-E(537310),
                     Add:bnameLE3D2C04HX2L(659654),bnameLE3D2X48SX2L(659655),bnameLE3D2G48SX1L(659659),bnameLE3D2G48TX1L(659660),

                     for v2r11
                     Add:bnameLE1D2S08SX2E(659661),      --S9300 S9300E S9310X  8-Port 10GE SFP+ Interface and 24-Port GE SFP Interface Card(X2E,SFP+)  for V2R11
                     Add:bnameET1D2MPUDC00(700475),      --S12700,Main Processing Unit D(Optional clock)
                     Add:subbnameET1D2VQ06000(700416),   --6-Port 40GE Cluster Switching System Service Unit (QSFP+) for 12700 V2R11
                     Add:subbnameET1D2VQ02000(700417),   --2-Port 40GE Cluster Switching System Service Unit (QSFP+) for 12700 and 9700   V2R11

                     Add:fname8031S5720-12X-LI-AC(537127), to fname8031S5330-56C-PWH-SI(537178),
                     Add:bname8031S5720-12X-LI-AC(537311), to bname8031S5330-56C-PWH-SI(537362),
                     Add:subbnameES5D21X02S02(536777),to subbnameES5D21Q02Q00(536781),
                     Add:subbnamePAC930D5612(536782),

                     Add: virentME60DEVME0DVSUF8071(161603),   -- for V800R009C10 ME0DVSUF8071(SBOM),Flexible Card Versatile Service Unit 80(VSUF-80-M) 1.3.6.1.4.1.2011.20021210.15.161603
                     Add: virentME60DEVME0DVSUFD071(161604),   -- for V800R009C10 ME0DVSUFD071(SBOM),Flexible Card Versatile Service Unit 160(VSUF-160-M) 1.3.6.1.4.1.2011.20021210.15.161604
                     Add: virent8090DEVCR5D0SRUB571 (675918),  -- for V800R009C10 CR5D0SRUB571 ,Switch and Route Processing Unit B5(16G Memory) 1.3.6.1.4.1.2011.20021210.15.675918

                     Add:  bnameCSM(156063),             --  48-channel Vectoring VDSL2 + POTS COMBO service board, supports super vectoring feature.
                     Add:  bnameH832PDMSA(156064),       --  DC Power board H832PDMSA of the MA5616.
                     Add:  subbnameH833XS1A(156061),     --  SD5118V2 XG-SPON subboard.
                     Add:  subbnameVPM(156062),          --  SUPER VECTOR Subboard VPM.

                      "



        REVISION    "201612020000Z"
        DESCRIPTION "V7.19,
                     Add:  subbname8090DEVCR5D00E1NC77(561713),      -- 1-Port 100GBase-CFP2 Flexible Card A(P120-A)
                     Add:  subbname8090DEVCR5D00E1NC7A(561714),      -- 1-Port 100GBase-CFP2 Flexible CardA(P240-A)
                     Add:  subbname8090DEVME0D0E1NCB70(561715),      -- 1-Port 100GBase-CFP2 Flexible Card(BP100)
                     Add:  subbname8090DEVME0D0E1NCB71(561729),      -- 1-Port 100GBase-CFP2 Flexible Card(BP240)
                     Add:  subbname8090DEVCR57E1NCF2(561717),      -- 1-Port 100GBase-CFP2 Fixed Card
                     Add:  subbname8090DEVCX6D0E1NCA11(561718),      -- 1-Port 100GBase-CFP2 Flexible Card A(S102-A)
                     Add:  subbname8090DEVCR5CR5D00E1ND70(561719),   -- 1-Port 100GBase-QSFP28 Flexible Card A(P120-A)
                     Add:  subbname8090DEVCR5CR5D00E1ND73(561720),   -- 1-Port 100GBase-QSFP28 Flexible Card A(P240-A)
                     Add:  subbname8090DEVCR5ME0D0E1NDB70(561721),   -- 1-Port 100GBase-QSFP28 Flexible Card(BP100)
                     Add:  subbname8090DEVCR5ME0D0E1NDB71(561722),   -- 1-Port 100GBase-QSFP28 Flexible Card(BP240)
                     Add:  subbname8090DEVCR5CX6D0E1NDA10(561723),   -- 1-Port 100GBase-QSFP28 Flexible Card A(S102-A)
                     Add:  subbname8090DEVCR5D00E2NF70(561727),      -- 2-Port 100GBase-QSFP28 Flexible Card A(P480-A)
                     Add:  subbname8090DEVCR5D00MD8A70(561726),      -- 8-Channel CWDM Multiplexing & Demultiplexing (1471/1491/1511/1531/1551/1571/1591/1611nm) Flexible Card(P50)
                     Add:  subbname8090DEVCR5D00E2NB60(561728),   -- 2-Port 100GBase-QSFP28 Flexible Card(CP400,Occupy 1 sub-slot)
                     Add:  subbname8090DEVCR5D3DMR4M01(561724),      -- 4-Channel CWDM Optical Add/Drop Multiplexing (1471/1491/1511/1531nm) Physical Interface Card(PIC)
                     Add:  subbname8090DEVCR5D3DMR4M02(561725),      -- 4-Channel CWDM Optical Add/Drop Multiplexing (1551/1571/1591/1611nm) Physical Interface Card(PIC)
                     Add:  subbname8090DEVCR5D00EEGF71(561635),   -- 20-Port 100/1000Base-X-CSFP Physical Interface Card(PIC)
                     Add:  subbname8090DEVCR5D00N6GF60(561625),   -- 6-Port 10G OTN/ETH-SFP+ Flexible Card(CP400,Occupy 1 sub-slot)
                     Add:  subbname8090DEVCR5D00NBGF60(561626),   -- 12-Port 10G OTN/ETH-SFP+ Flexible Card(CP400,Occupy 1 sub-slot)
                     Add:  subbname8090DEVCR5D00E1NC79(561594), -- 1-Port 100GBase LAN/WAN-CFP2 Physical Interface Card(PIC)
                     Add:  subbname8090DEVCR5D00LAXF71(561595), -- 10-Port 10GBase LAN/WAN-SFP+ Physical Interface Card(PIC)
                     Add:  subbname8090DEVCR58E8NBA(561622), -- 8*100GBase QSFP28 Card
                     Add:  subbname8090DEVCR58D8NCA(561624), -- 8-Port 100GBase-CFP DWDM Card
                      "


        REVISION    "201611160000Z"
        DESCRIPTION "V7.14,
                     Modify: CR57LEXFE changed to CR5D0LEXFE71
                     Modify: CR57E2NCE changed to CR5D0E2NCE71
                     Modify: CR57LEXFE changed to ME0M0LEXFB71
                     Modify: CR57E2NCE changed to ME0M0E2NCB71
                     Modify: CX68EAGFEA changed to CR5D0EAGFE70
                     Modify: CX68EAGFEA changed to CR2D0EAGFE10
                     Modify: CX68L2XFEA changed to CR5D0L2XFE71
                     Modify: CX68L2XFEA changed to CR2D0EAGFE10
                     "

        REVISION    "201611100000Z"
        DESCRIPTION "V7.17,
                     Add:  fnameMA5626BH821Mabc(561634),     -- Virtual Frame H821MABC of the MA5626B device.
                     Add:  bnameH822EPUBM(156060),           -- Master board of MA5626B(SD5103) Box type device.
                     "

        REVISION    "201611090000Z"
        DESCRIPTION "V7.16,
                     Add:  fnamePTN930(229403),                          --PTN930  chassis
                     Add:  fnamePTN905G(229404),                       --PTN905G  chassis
                     Add:  fnamePTN905E(229405),                       --PTN905E  chassis
                     Add:  fnamePTN905D(229406),                       --PTN905D  chassis
                     Add:  fnamePTN905F(229407),                       --PTN905F  chassis]
                     Add:  bnameTPLD00CXP000(229431),           --TPL1CXP, System Control,Cross-connect and Multi-protocol Process Unit
                     Add:  bnameTPMD00CXPN00(229432),         --TPM1CXPN, System Control,Cross-connect and Multi-protocol Process Unit
                     Add:  bnameTPMD00CXPL00(229433),          --TPM1CXPL, System Control,Cross-connect and Multi-protocol Process Unit
                     Add:  bnameTPMD00CXPB00(229434),         --TPM1CXPB, System Control,Cross-connect and Multi-protocol Process Unit
                     Add:  bnameTPMD00CXPM00(229435),         --TPM1CXPM, System Control,Cross-connect and Multi-protocol Process Unit
                     Add:  bnameTPMD000PIU00(229436),           -- DC Power Module
                     Add:  bnameTPMD00APIU00(229437),          -- AC Power Module
                    "


        REVISION    "201611070000Z"
        DESCRIPTION "V7.15,
                     Add:subbname8090DEVCR56E4NBA1(561623), -- 4-Port 100GBase QSFP28 Flexible Card(CP1T,Occupy 1 sub-slot)
                     "


        REVISION    "201611020000Z"
        DESCRIPTION "V7.14,
                     Modify: bnameLE2D2X48SEC0(659573), LE2D2X48SED0 changed to LE2D2X48SEC0,the LE2D2X48SED0 does not support,and the 659573 was distribute to LE2D2X48SEC0 Actually
                     Delete: bnameLE2D2X48SEC0(659647), LE2D2X48SEC0 is a old board,already has id,the id is 659573,so this id Abandoned
                     Modify: fname8031S5720-10T-PWR-LI(537011) to fname8031Huawei-S5700-8P-G(537011)
                     Modify: bname8031S5720-10T-PWR-LI(537196) to bname8031Huawei-S5700-8P-G(537196)
                     "


        REVISION    "201610290000Z"
        DESCRIPTION "V7.13,
                     Modify: virent8090DEVCR5DLPUF5071(675899),      --V8R9C00 for SBOM, CR5DLPUF5071, Flexible Card Line Processing Unit(LPUF-50,four sub-slots) to virent8090DEVCR5DLPUF5071(675899),      --V8R9C00 for SBOM, CR5DLPUF5071, Flexible Card Line Processing Unit(LPUF-50,four sub-slots,4G Memory)
                     Modify: virent8090DEVCR5DLPUF507M(675900),      --V8R9C00 for SBOM, CR5DLPUF507M, Flexible Card Line Processing Unit L(LPUF-50-L,four sub-slots) to virent8090DEVCR5DLPUF507M(675900),      --V8R9C00 for SBOM, CR5DLPUF507M, Flexible Card Line Processing Unit L(LPUF-50-L,four sub-slots,4G Memory)
                     Modify: virent8090DEVCX6DISUF5011(675901),      --V8R9C00 for SBOM, CX6DISUF5011, Flexible Card Integrated Service Unit(ISUF-50,four sub-slots) to virent8090DEVCX6DISUF5011(675901),      --V8R9C00 for SBOM, CX6DISUF5011, Flexible Card Integrated Service Unit(ISUF-50,four sub-slots,4G Memory)
                     Modify: virent600DEVCX6B0BKP0373(564863),    --V8R9C00 CX600-M2H CX6B0BKP0373(SBOM), 480Gbps MNPUI NO POWER to virent600DEVCX6B0BKP0375(564863),    --V8R9C00 CX600-M2H CX6B0BKP0375(SBOM), 480Gbps MNPUI NO POWER
                     Modify: virent600DEVCR5B0BKP0377(564860),    --V8R9C00 NE40E-M2H CR5B0BKP0377(SBOM), 480Gbps MNPUI NO POWER to virent600DEVCR5B0BKP0377(564860),    --V8R9C00 NE40E-M2H CR5B0BKP0377(SBOM), 480Gbps MNPUI NO POWER
                     "

        REVISION    "201610260000Z"
        DESCRIPTION "V7.12,
                     Add: virentME60DEVME0DBSUFA071(161600),   -- for ME0DBSUFA071(SBOM),Flexible Card Broadband Service Unit(BSUF-120,2 sub-slots)
                     Add: virentME60DEVME0DBSUFF071(161599),   -- for ME0DBSUFF071(SBOM),Flexible Card Broadband Service Unit(BSUF-200,2 sub-slots)
                     Add: virentME60DEVME0DBSUFK070(161601),   -- for ME0DBSUFK070(SBOM),Flexible Card Broadband Service Unit(BSUF-400,2 sub-slots)
                     Add: virent8090DEVCR5DLPUFK070(161602),   -- for CR5DLPUFK070(SBOM),Flexible Card Line Processing Unit E(LPUF-400-E)

                     Add: fname8090NE40E-X16A(561641),        --Quidway NE40E-X16A FRAME
                     Add: fname8090NE40E-X8A(561642),        --Quidway NE40E-X8A FRAME
                     Add: fnameME60-X16A(561643),        --Quidway ME60-X16A FRAME
                     Add: fnameME60-X8A(561644),        --Quidway ME60-X8A FRAME
                     Add: fname8090CX600-X16A(561645),        --Quidway CX600-X16A FRAME
                     Add: fname8090CX600-X8A(561646),        --Quidway CX600-X8A FRAME
                     Add: fnamePTN6900-16A(561647),        --Quidway PTN6900-16A FRAME
                     Add: fnamePTN6900-8A(561648),        --Quidway PTN6900-8A FRAME
                     Add: fname8090CX600-X16A-DO(561649),        --Quidway CX600-X16A-DO FRAME
                     Add: fname8090CX600-X8A-DO(561650),        --Quidway CX600-X8A-DO FRAME

                     Modify: fname8090NE40E-X16A(561175) to fname8090NE40E-X16A-AC(561175)
                     Modify: fname8090NE40E-X8A(561177) to fname8090NE40E-X8A-AC(561177)
                     Modify: fnameME60X16A(159756) to fnameME60X16A-AC(159756)
                     Modify: fnameME60X8A(159754) to fnameME60X8A-AC(159754)
                     Modify: fname8090CX600-X16A(536865) to fname8090CX600-X16A-AC(536865)
                     Modify: fname8090CX600-X8A(536864) to fname8090CX600-X8A-AC(536864)
                     Modify: fnamePTN6900-16A(229393) to fnamePTN6900-16A-AC(229393)
                     Modify: fnamePTN6900-8A(229391) to fnamePTN6900-8A-AC(229391)
                     Modify: fname8090CX600-X16ADO(536993) to fname8090CX600-X16ADO-AC(536993)
                     Modify: fname8090CX600-X8ADO(536995) to fname8090CX600-X8ADO-AC(536995)
                     "

        REVISION    "201610250000Z"
        DESCRIPTION "V7.11,
                     Add: fnameAR129CVW(667876),         -- AR129CVW FRAME
                     Add: fnameAR1220-8GE(667877),       -- AR1220-8GE FRAME
                     Add: fnameAR2204-24GE(667878),      -- AR2204-24GE FRAME
                     Add: fnameAR2204-48GE-P(667879),    -- AR2204-48GE-P FRAME
                     Add: fnameAR505Kc-L-RM(667880),     -- AR505Kc-L-RM FRAME

                     Add: bnameAR129CVW(667973),                -- AR129CVW Main Unit
                     Add: bnameAR1220-8GE(667974),              -- AR1220-8GE Main Unit
                     Add: bnameAR2204-24GE(667975),             -- AR2204-24GE Main Unit
                     Add: bnameAR2204-48GE-P(667976),           -- AR2204-48GE-P Main Unit
                     Add: bnameAR505Kc-L-RM(667977),            -- AR505Kc-L-RM Main Unit
                     "

        REVISION    "201610190000Z"
        DESCRIPTION "V7.10,
                add: fname8090NE40E-X16B(562069),       --Quidway NE40E-X16B FRAME
                add: virent8090DEVCR5D0MPUB580(562065),   -- Main Processing Unit B5,CR57MPUB5
                add: virent8090DEVCR5DSFUIT16E(562066),   -- 1Tbps Switch Fabric Unit B(SFUI-1T-E),CR57SUF1TE
                add: virent8090DEVCR5DE2NLEX80(562067),   -- 2-Port 100GBase-CFP2 + 20-Port 10GBase-SFP+ Integrated Line Process Unit (LPUI-400), CR57LPUI400
                add: virent8090DEVCR5D00E8NC80(562068),   -- 8-Port 100GBase-CFP4- Integrated Line Process Unit(LPUI-1T),CR57LPU1TF
           "

        REVISION    "201610160000Z"
        DESCRIPTION "V7.09,
           ADD: bnameCEL24LQFD(688231),                  -- Manufactured Board,CloudEngine 12800,CE-L24LQ-FD,24-Port-40GE Interface Card(FD,QSFP+)
           ADD: bnameCEL12CQFD(688232),                  -- Manufactured Board,CloudEngine 12800,CE-L12CQ-FD,12-Port-100GE Interface Card(FD,QSFP28)
           ADD: bnameCEL48XSFD(688233),                  -- Manufactured Board,CloudEngine 12800,CE-L48XS-FD,48-Port-10GE Interface Card(FD,SFP+)
           ADD: bnameCESFUAS(688234),                    -- CloudEngine 12800S,CE-SFUA-S,CE12800S Switch Fabric Unit A
           "

        REVISION    "201610080000Z"
        DESCRIPTION "V7.08,
           ADD: bnamePTN990TPJD002CXP00(229430),           --TPJD002CXP00,System Control,Cross-connect and Multi-protocol Process Unit
           "
	REVISION    "201609290000Z"
        DESCRIPTION "V7.07,
           Add: fname8031S5720-28X-PWH-LI-AC(537114),        --LSW V2R11C00 PI1 S5720-28X-PWH-LI-AC
           Add: fname8031S5320-28X-PWH-LI-AC(537115),        --LSW V2R11C00 PI1 S5320-28X-PWH-LI-AC

           Add: bname8031S5720-28X-PWH-LI-AC(537298),        --LSW V2R11C00 PI1 S5720-28X-PWH-LI-AC
           Add: bname8031S5320-28X-PWH-LI-AC(537299),        --LSW V2R11C00 PI1 S5320-28X-PWH-LI-AC
           "


        REVISION    "201609280000Z"
        DESCRIPTION "V7.06,
                     Add: fnameAR509EG-U-A(667861),      -- AR509EG-U-A FRAME
                     Add: fnameAR169G-Lo(667862),        -- AR169G-Lo FRAME
                     Add: fnameAR161FG-Lc(667863),       -- AR161FG-Lc FRAME
                     Add: fnameAR161FGW-Lc(667864),      -- AR161FGW-Lc FRAME
                     Add: fnameAR161G-Lc(667865),        -- AR161G-Lc FRAME
                     Add: fnameAR101GW-Lc-S(667866),     -- AR101GW-Lc-S FRAME
                     Add: fnameAR201V(667867),           -- AR201V FRAME
                     Add: fnameAR503EDGW-Lc3(667868),    -- AR503EDGW-Lc3 FRAME
                     Add: fnameAR109(667869),            -- AR109 FRAME
                     Add: fnameAR109W(667870),           -- AR109W FRAME
                     Add: fnameAR109GW-L(667871),        -- AR109GW-L FRAME
                     Add: fnameAR502CG-L(667872),        -- AR502CG-L FRAME
                     Add: fnameAR2220E-S(667873),        -- AR2220E-S FRAME
                     Add: fnameAR2240C-S(667874),        -- AR2240C-S FRAME
                     Add: fnameAR3260E-S(667875),        -- AR3260E-S FRAME

                     Add: bnameAR509EG-U-A(667960),             -- AR509EG-U-A Main Unit
                     Add: bnameAR169G-Lo(667961),               -- AR169G-Lo Main Unit
                     Add: bnameAR161FG-Lc(667962),              -- AR161FG-Lc Main Unit
                     Add: bnameAR161FGW-Lc(667963),             -- AR161FGW-Lc Main Unit
                     Add: bnameAR161G-Lc(667964),               -- AR161G-Lc Main Unit
                     Add: bnameAR101GW-Lc-S(667965),            -- AR101GW-Lc-S Main Unit
                     Add: bnameAR201V(667966),                  -- AR201V Main Unit
                     Add: bnameAR503EDGW-Lc3(667967),           -- AR503EDGW-Lc3 Main Unit
                     Add: bnameAR109(667968),                   -- AR109 Main Unit
                     Add: bnameAR109W(667969),                  -- AR109W Main Unit
                     Add: bnameAR109GW-L(667970),               -- AR109GW-L Main Unit
                     Add: bnameAR502CG-L(667971),               -- AR502CG-L Main Unit
                     Add: bnameAR2220E-S(667972),               -- AR2220E-S Main Unit
                     "

        REVISION    "201609240000Z"
        DESCRIPTION "V7.05,
                     Add: bnameH901PIMA(148614),         --  DC Power board of MA5800-X7.
                     "

        REVISION    "201609230000Z"
        DESCRIPTION "V7.04, add AP5030DN-C for wlan ap "

        REVISION    "201609210000Z"
        DESCRIPTION "V7.03,
					Add: fnameNIP6860-DC (16715816),       --NIP6860 DC Basic Configuration(include X8 DC Chassis,2*SRU,1*SFU) (0x00ff1028)
					Add: fnameNIP6800-X8-CHAS-DC (16715817),       --NIP6800 Integrated Chassis Components,14U(Including 4 DC Power)  (0x00ff1029)
					Add: bnameSPU-X3-20-B-E8KE(16744461),     -- 20G X3 Firewall Service Processing Unit B(oversea)(0x00ff800d)
					Add: bnameSPUA-H(16744457),     -- X8&X16 Firewall Service Processing Unit(0x00ff8009)
					Add: bnameSPUA-M(16744458),     -- X3 Firewall Service Processing Unit(0x00ff800a)
					Add: bnameSPUA-20-O-H (16744459),     -- 20G X8&X16 Firewall Service Processing Unit (oversea)(0x00ff800b)
					Add: bnameSPUA-20-O-M(16744460),     -- 20G X3 Firewall Service Processing Unit (oversea)(0x00ff800c)
					Add: bnameSPUB-NAT-X8X16-E8KE(16744454),     -- X8&X16 NAT Service Processing Unit B(0x00ff8006)
					Add: bnamebnameNIP-SPU-B(16744462),     -- NIP6800 Service Processing Unit(Base Board)(0x00ff800e)
					Add: bnameNIP-LPUF-120 (16744463),     -- NIP6800 Flexible Card Line Processing Unit(120G,2 sub-slots)(0x00ff800f)
					Add: bnameNIP-LPUF-240 (16744464),     -- NIP6800 Flexible Card Line Processing Unit(240G,2 sub-slots)(0x00ff8010)
					Add: bnameNIP6800-X8-SRUA-200 (16744465),     -- NIP6800 X8 200Gbps Switch and Route Processing Unit A(0x00ff8011)
					Add: subbnameSPCA-H&M(16728078),    --Firewall Service Processing Card A (0x00ff400e)
					Add: subbnameSPCA-20-O-H&M(16728079),    --20 Expansion Card (oversea) (0x00ff400f)
					Add: subbnameFW-20X1G-RJ45(16728080),    --20-Port 100/1000Base-RJ45 Flexible Card (0x00ff4010)
					Add: subbnameFW-3X40G-QSFP+(16728081),    --3-Port 40GBase-QSFP+ Flexible Card (P240-A)(0x00ff4011)
					Add: subbnameSPCB-NAT-E8KE(16728068),    --X8&X16 NAT Service Processing Card B(0x00ff4004)
					Add: subbnameNIP-SAC-A(16728082),    --NIP6800 Service Processing Acceleration card-A (P240-A)(0x00ff4012)
					Add: subbnameNIP-12X10G-SFP+ (16728083),    --NIP6800 12-Port 10G Base LAN/WAN-SFP+ Flexible Card A((1/2wide,Occupy one sub-slots) (P240-A)(0x00ff4013)
					Add: subbnameNIP-6X10G-SFP+ (16728084),    --NIP6800 6-Port 10G Base LAN/WAN-SFP+ Flexible Card A(1/2wide,Occupy one sub-slots) (P240-A)(0x00ff4014)
					Add: subbnameNIP-3X40GE-QSFP+(16728085),    --NIP6800 3-Port 40GBase-QSFP+ Flexible Card(0x00ff4015)
					Add: subbnameNIP-1X100G-CFP(16728086),    --NIP6800 1-Port 100GBase-CFP Flexible Card A(0x00ff4016)
					Add: subbnameNIP-24XGE-SFP (16728087),    --NIP6800 24-Port 100/1000Base-X-SFP Flexible Card(1/2wide,Occupy one sub-slots)(0x00ff4017)
					Add: subbnameNIP-IPS-B (16728088),    --NIP6800 IPS Service Processing Card(0x00ff4018)
					"

        REVISION    "201609100000Z"
        DESCRIPTION "V7.02,
                     Add: fnameMA5898H831Mabl-DC(561633),     -- Virtual Frame H831MABL of the MA5898 DC device.
                     Add: fnameMA5821A-24GE(561578),          -- Virtual Frame H821MABS of the MA5821A-24GE device.
                     Add: bnameH825CCIA(156058),              -- Master board of MA5821A device.
                     Add: bnameH831PAIS(156059),              -- AC Power board of MA5821A device.
                     "

        REVISION    "201609020000Z"
        DESCRIPTION "V7.01,
           Add: subnameLND1EX8F(708623),                       -- 1 Channel 10GE (SFP+),8 Channels GE/FE Optical Interface Board
           "

        REVISION    "201608270000Z"
        DESCRIPTION "V6.98,
            Add: subbname8090DEVCR57L6XFI01(561476), --03031YYQ,  6-Port 10GBase LAN/WAN-SFP+ Flexible Card H(P120-H)
           Add: subbname8090DEVME03L6XFI0(561477), --03031YYV,  6-Port 10GBase LAN/WAN-SFP+ Flexible Card H(BP120-H)
           Add: subbname8090DEVCR57LBXFH1(561478), --03031YYS,  12-Port 10GBase LAN/WAN-SFP+ Flexible Card H(P240-H)
           Add: subbname8090DEVME03LBXFH0(561479), --03031YYX,  12-Port 10GBase LAN/WAN-SFP+ Flexible Card H(BP200-H)
           Add: subbname8090DEVCR57E1NCF0(561480), --03032GKY,  1-Port 100GBase-CFP2 Flexible Card A(P120-A)
           Add: subbname8090DEVCR57E1NCF1(561481), --03032GLA,  1-Port 100GBase-CFP2 Flexible CardA (P240-A)
           Add: subbname8090DEVME03E1NCF0(561482), --03032GLB,  1-Port 100GBase-CFP2 Flexible Card(BP100)
           Add: subbname8090DEVME03E1NCF1(561483), --03032GLC,  1-Port 100GBase-CFP2 Flexible Card(BP240)
           Add: subbname8090DEVCR57E1NCF2(561518), --03032GLD,  1-Port 100GBase-CFP2 Fixed Card
           Add: subbname8090DEVTNR2EF1(561484),     --03032GLE,  1 Port 100 Gigabit Ethernet Processing Flexible Card (Supporting 1588v2)
           Add: subbname8090DEVCX62E1NCF0(561485), --03032GLF,  1-Port 100GBase-CFP2 Flexible Card A(S102-A)
           Add: subbname8090DEVCR57E1NBA0(561494), --CR5D00E1ND70, 1-Port 100GBase-QSFP28 Flexible Card A(P120-A)
           Add: subbname8090DEVCR57E1NBA1(561495), --CR5D00E1ND73, 1-Port 100GBase-QSFP28 Flexible Card A(P240-A)
           Add: subbname8090DEVCX62E1NBA0(561496), --CX6D0E1NDA10, 1-Port 100GBase-QSFP28 Flexible Card A(S102-A)
           Add: subbname8090DEVME03E1NBA0(561497), --ME0D0E1NDB70, 1-Port 100GBase-QSFP28 Flexible Card(BP100)
           Add: subbname8090DEVME03E1NBA1(561498), --ME0D0E1NDB71, 1-Port 100GBase-QSFP28 Flexible Card(BP240)
           Add: subbname8090DEVCR5D0LEXFE71(561486), --20-Port 10GBase LAN/WAN-SFP+ Flexible Card H(P480-H)
           Add: subbname8090DEVCR5D0E2NCE71(561487), --2-Port 100GBase-CFP2 Flexible Card E(P480-H)
           Add: subbname8090DEVME0M0LEXFB71(561488), --20-Port 10GBase LAN/WAN-SFP+ Flexible HCardE(BP480-H)
           Add: subbname8090DEVME0M0E2NCB71(561489), --2-Port 100GBase-CFP Flexible Card H(BP480-H)
           Add: subbname8090DEVCR5D0EAGFE70(561490), --10-Port 100/1000Base-X-SFP Physical Interface Card E(PIC-E)
           Add: subbname8090DEVCR2D0EAGFE10(561491), --10-Port 100/1000Base-X-SFP Physical Interface Card E(PIC-E)
           Add: subbname8090DEVCR5D0L2XFE71(561492), --2-Port 10GBase LAN/WAN-SFP+ Physical Interface Card E(PIC-E)
           Add: subbname8090DEVCR2D0EAGFE10(561493), --2-Port 10GBase LAN/WAN-SFP+ Physical Interface Card E(PIC-E)
           Add: virent8090DEVCR57E1NCF20(675902), --03057445,  1-Port 100GBase-CFP2 Integrated Line Processing Unit (LPUI-120)
           Add: virent8090DEVCR57E1NCF21(675903), --03057446,  1-Port 100GBase-CFP2 Integrated Line Processing Unit B(LPUI-120-B)
           Add: virent8090DEVCR57E2NCF22(675904), --03057447,  2-Port 100GBase-CFP2 Integrated Line Processing Unit (LPUI-240)
           Add: virent8090DEVCR57E2NLBX24(675905), --03057448,  1-Port 100GBase-CFP2 + 12-Port 10GBase LAN/WAN-SFP+ Integrated Line Processing Unit (LPUI-240)
           Add: virent8090DEVCR57E2NCF23(675906), --03057449,  2-Port 100GBase LAN-CFP2 Integrated Line Processing Unit B(LPUI-240-B)
           Add: virent8090DEVCR57E2NLBX25(675907), --03057450,  1-Port 100GBase-CFP2 + 12-Port 10GBase LAN/WAN-SFP+ Integrated Line Processing Unit B(LPUI-240-B)
           Add: virent8090DEVCR57E1NBA20(675912), --CR5D00E1ND71, 1-Port 100GBase-QSFP28 Integrated Line Processing Unit (LPUI-120)
           Add: virent8090DEVCR57E1NBA21(675913), --CR5D00E1ND72, 1-Port 100GBase-QSFP28 Integrated Line Processing Unit B(LPUI-120-B)
           Add: virent8090DEVCR57E2NBA20(675914), --CR5D00E2ND70, 2-Port 100GBase-QSFP28 Integrated Line Processing Unit (LPUI-240)
           Add: virent8090DEVCR57E2NBA21(675915), --CR5D00E2ND71, 2-Port 100GBase LAN-QSFP28 Integrated Line Processing Unit B(LPUI-240-B)
           Add: virent8090DEVCR57E1NLBX25(675916), --CR5DE1NLBX73, 1-Port 100GBase-QSFP28 + 12-Port 10GBase LAN/WAN-SFP+ Integrated Line Processing Unit B(LPUI-240-B)
           Add: virent8090DEVCR57E1NLBX24(675917), --CR5DE1NLBX72, 1-Port 100GBase-QSFP28 + 12-Port 10GBase LAN/WAN-SFP+ Integrated Line Processing Unit (LPUI-240)
           Add: virent8090DEVCR57E2NLAX20(675908), --03057451,  1-Port 100GBase-CFP2 + 10-Port 10GBase LAN/WAN-SFP+ Integrated Line Processing Unit (LPUI-200)
           Add: virent8090DEVCR57E2NLAX21(675909), --03057452,  1-Port 100GBase-CFP2 + 10-Port 10GBase LAN/WAN-SFP+ Integrated Line Processing Unit (LPUI-200-L)
           Add: virent8090DEVCR57E2NCF24(675910), --03057453,  2-Port 100GBase-CFP2 Integrated Line Processing Unit (LPUI-200)
           Add: virent8090DEVCR57E2NCF25(675911), --03057454,  2-Port 100GBase-CFP2 Integrated Line Processing Unit (LPUI-200-L)
                   "

        REVISION    "201608160000Z"
        DESCRIPTION "V6.96,
                     Modify: virentANGMHSTA0100(225571) to virentANGMHSTA0111(225571)
                     Modify: virentANGMHSTB0100(225572) to virentANGMHSTB0111(225572)
                     Modify: virentANGMHSTA0200(225573) to virentANGMHSTA0211(225573)
                     Modify: virentANGMHSTB0200(225574) to virentANGMHSTB0211(225574)
                     Modify: virentNECMHSTA0200(704538) to virentNECMHSTA0211(704538)
                     Modify: virentNECMHSTB0200(704539) to virentNECMHSTB0211(704539)
                     Modify: bnameANGD000PIU00(229008) to bnameES5M0PSD1700(229008)
                   "

        REVISION    "201608150000Z"
        DESCRIPTION "V6.95,
                     Add: virent8090DEVCR5DLPUF5071(675899),      --V8R9C00 for SBOM, CR5DLPUF5071, Flexible Card Line Processing Unit(LPUF-50,four sub-slots)
                     Add: virent8090DEVCR5DLPUF507M(675900),      --V8R9C00 for SBOM, CR5DLPUF507M, Flexible Card Line Processing Unit L(LPUF-50-L,four sub-slots)
                     Add: virent8090DEVCX6DISUF5011(675901),       --V8R9C00 for SBOM, CX6DISUF5011, Flexible Card Integrated Service Unit(ISUF-50,four sub-slots)

                     Add: virentME60DEVME0D0E4NCM70(161595),   -- for V800R009C10 ME0D0E4NCM70(SBOM),4-Port 100GBase-CFP2 Multi Service Unit Integrated(MSUI-400)
                     Add: virentME60DEVME0D0LKXFB70(161596),   -- for V800R009C10 ME0D0LKXFB70(SBOM),40-Port 10GBase LAN/WAN-SFP+ Broadband Service Unit Integrated(BSUI-400)
                     Add: virentME60DEVME0DE2NLEX7B(161597),   -- for V800R009C10 ME0DE2NLEX7B(SBOM),2-Port 100GBase-CFP2+20-Port 10GBase LAN/WAN-SFP+ Broadband Service Unit Integrated(BSUI-400)
                     Add: virentME60DEVME0D0LEXFB71(161583),   -- for V800R009C10 ME0D0LEXFB71(SBOM),20-Port 10GBase LAN/WAN-SFP+ Multi Service Unit Integrated(MSUI-200)
                     Add: virentME60DEVME0D0LEXFB70(161584),   -- for V800R009C10 ME0D0LEXFB70(SBOM),20-Port 10GBase LAN/WAN-SFP+ Broadband Service Unit Integrated(BSUI-200)
                     Add: virentME60DEVME0D0E2NCB70(161585),   -- for V800R009C10 ME0D0E2NCB70(SBOM),2-Port 100GBase-CFP Multi Service Unit Integrated(MSUI-200)

                     Add: fname8090NE40E-X16A-HVDC(561181),        --Quidway NE40E-X16A FRAME,HVDC
                     Add: fname8090NE40E-X8A-HVDC(561182),        --Quidway NE40E-X8A FRAME,HVDC
                     Add: fnameME60-X16A-HVDC(159769),        --Quidway ME60-X16A FRAME,HVDC
                     Add: fnameME60-X8A-HVDC(159770),        --Quidway ME60-X8A FRAME,HVDC
                     Add: fname8090CX600-X16A-HVDC(561183),        --Quidway CX600-X16A FRAME,HVDC
                     Add: fname8090CX600-X8A-HVDC(561184),        --Quidway CX600-X8A FRAME,HVDC
                     Add: fnamePTN6900-16A-HVDC(561185),        --Quidway PTN6900-16A FRAME,HVDC
                     Add: fnamePTN6900-8A-HVDC(561186),        --Quidway PTN6900-8A FRAME,HVDC
                     Add: fname8090CX600-X16A-DO-HVDC(561187),        --Quidway CX600-X16A-DO FRAME,HVDC
                     Add: fname8090CX600-X8A-DO-HVDC(561188),        --Quidway CX600-X8A-DO FRAME,HVDC

                     Modify: virentME60DEVMEODBSUFMO70(161593) to virentME60DEVME0DBSUFM070(161593)
                     Modify: virentME60DEVMEODMSUFMO70(161594) to virentME60DEVME0DMSUFM070(161594)
                    "

        REVISION    "201608130000Z"
        DESCRIPTION "V6.93,
                     Add: fname8031S5720-16X-PWH-LI-AC(537113),        --S5720-16X-PWH-LI-AC        Metro Service Platform for V2R10C00
                     Add: bname8031S5720-16X-PWH-LI-AC(537297),         --S5720-16X-PWH-LI-AC      Metro Service Platform for V2R10C00
                    "

        REVISION    "201608050000Z"
        DESCRIPTION "V6.93,
                     --for PTN7900 V1R8C10 20160805
                     Add:  bnamePTN7900TPA1EHD1(229426), --TPA1EHD1,1-port 200 Gigabit Ethernet Switching Processing Board
                     Add:  bnamePTN7900TPA2EH2(229427), --TPA2EH2,2-port 100 Gigabit Ethernet Switching Processing Board
                     Add:  bnamePTN7900TPA3EH1(229428), --TPA3EH1,1-port 100 Gigabit Ethernet Switching Processing Board
                     Add:  bnamePTN7900TPA2EX8S(229429), --TPA2EX8S,8-port 10 Gigabit Ethernet Switching Processing Board
                     "

        REVISION    "201607300000Z"
        DESCRIPTION "V6.92,
                     Add: bnameH901CGID(148613),         --  8*GE and 10GE combo board of MA5800
             Add: bnameH901MPLC(148507),         --  control board of MA5800
                     Add: bnameH901MPLD(148508),         --  control board of MA5800
                     Add: bnameH902MPLC(148509),         --  control board of MA5800
                     "

        REVISION    "201607270000Z"
        DESCRIPTION "V6.91,
                     Add: fnameCE686048S18CQEI(688158),        -- CloudEngine CE6860-48S18CQ-EI Switch (48-Port 25GE SFP28 Optical,18-Port 100GE QSFP28)
                     Add: fnameCE686048S8CQEI(688159),         -- CloudEngine CE6860-48S8CQ-EI Switch (48-Port 25GE SFP28 Optical,8-Port 100GE QSFP28)
                     Add: fnameCE687048S6CQEI(688160),         -- CloudEngine CE6870-48S6CQ-EI Switch (48-Port SFP+ Optical,6-Port 100GE QSFP28)
                     Add: fnameCE687024S6CQEI(688161),         -- CloudEngine CE6870-24S6CQ-EI Switch (24-Port SFP+ Optical,6-Port 100GE QSFP28)
                     Add: fnameCE785532QEI(688162),            -- CloudEngine CE7855-32Q-EI Switch(32-Port 40GE QSFP+)
                     Add: bnameCEL36CQFD(688217),              -- Manufactured Board,CloudEngine 12800,CE-L36CQ-FD,36-Port-100GE Interface Card(FD,QSFP28)
                     Add: bnameCEL36LQFD(688218),              -- Manufactured Board,CloudEngine 12800,CE-L36LQ-FD,36-Port-40GE Interface Card(FD,QSFP+)
                     Add: bnameCEL48XSFDA(688219),             -- Manufactured Board,CE-L48XS-FDA,48-Port-10GE,2-Port-40GE,2-Port-100GE Interface Card(FDA,SFP+,QSFP+,QSFP28)
                     Add: bnameCESFU08F(688220),               -- Manufactured Board,CloudEngine 12800,CE-SFU08F,CE12808 Switch Fabric Unit F,1*1
                     Add: bnameCESFU16F(688221),               -- Manufactured Board,CloudEngine 12800,CE-SFU16F,CE12816 Switch Fabric Unit F,1*1
                     Add: bnameCESFUFS(688222),                -- Manufactured Board,CloudEngine 12800S,CE01SFUFS,CE12800S Switch Fabric Unit F,1*1
                     Add: bnameCESFU16G(688223),               -- Manufactured Board,CloudEngine 12800,CE-SFU16G,CE12816 Switch Fabric Unit G,1*1
                     Add: bnameCESFU12G(688224),               -- Manufactured Board,CloudEngine 12800,CE-SFU12G,CE12812 Switch Fabric Unit G,1*1
                     Add: bnameCEL04CFEC(688225),              -- Manufactured Board,CloudEngine 12800,CE-L04CF-EC,4-Port-100GE Interface Card(EC,CFP)
                     Add: bnameCE686048S18CQEI(688226),        -- Manufactured Board,CloudEngine 6800,CEM48S18CQP01,48-Port 25GE SFP28 Optical,18-Port 100GE QSFP28 Optical Switch Control Unit,1*1
                     Add: bnameCE686048S8CQEI(688227),         -- Manufactured Board,CloudEngine 6800,CEM48S8CQP01,48-Port 25GE SFP28 Optical,8-Port 100GE QSFP28 Optical Switch Control Unit,1*1
                     Add: bnameCE687048S6CQEI(688228),         -- Manufactured Board,CloudEngine 6800,CEM48S6CQP01,48-Port SFP+ Optical,6-Port 100GE QSFP28 Optical Switch Control Unit,1*1
                     Add: bnameCE687024S6CQEI(688229),         -- Manufactured Board,CloudEngine 6800,CEM24S6CQP01,24-Port SFP+ Optical,6-Port 100GE QSFP28 Optical Switch Control Unit,1*1
                     Add: bnameCE785532QEI(688230),            -- Manufactured Board,CloudEngine 7800,CEM32QP02,32-Port 40GE QSFP+ Optical Switch Control Unit,1*1
                     Add: portnameDCDE01CFP10G(688140),        -- The port with 10G type split from 100G CFP type
                     Add: portnameDCDE01CFP40G(688141),        -- The port with 40G type split from 100G CFP type
                     Add: portnameDCDE01CFP210G(688142),       -- The port with 10G type split from 100G CFP2 type
                     Add: portnameDCDE01CFP240G(688143),       -- The port with 40G type split from 100G CFP2 type
                     Add: portnameDCDE01CXP10G(688144),        -- The port with 10G type split from 100G CXP type
                     Add: portnameDCDE01CXP40G(688145),        -- The port with 40G type split from 100G CXP type
                     "

        REVISION    "201607180000Z"
        DESCRIPTION "V6.90,
                     Add: subbname8090DEVCR5D00E1NC79(561594),   -- 1-Port 100GBase LAN/WAN-CFP2  Physical Interface Card(PIC)
                     Add: subbname8090DEVCR5D0E2NCE70(561596), -- 2-Port 100GBase-CFP2 Flexible Card E(P480-E)
                     Add: subbname8090DEVCR5D0LEXFE70(561597), -- 20-Port 10GBase LAN/WAN-SFP+ Flexible Card E(P480-E)
                     Add: subbname8090DEVMEOM0LEXFB70(561598), -- 20-Port 10GBase LAN/WAN-SFP+ Flexible Card(BP480)
                     Add: subbname8090DEVMEOM0E2NCB70(561599), -- 2-Port 100GBase-CFP Flexible Card(BP480)
                     Add: subbname8090DEVCR5D00E4NB60(561600), -- 4-Port 100GBase QSFP28 Flexible Card(CP1T,Occupy 1 sub-slot)
                     Add: subbname8090DEVCR5DE2NLEX60(561601), -- 2-Port 100GBase QSFP28+20-Port 10GBase LAN/WAN SFP+ Flexible Card(CP1T,Occupy 1 sub-slot)
                     Add: subbname8090DEVCR5D00LFXF60(561602), -- 24-Port 10GBase LAN/WAN SFP+ Flexible Card(CP1T,Occupy 1 sub-slot)
                     Add: subbname8090DEVCR5D00N4NC60(561603), -- 4-Port 100G OTN/ETH CFP4 Flexible Card(CP1T,Occupy 1 sub-slot)
                     Add: subbname8090DEVCR5D00LMXB60(561604), -- 48-Port 10GBase LAN/WAN QSFP+  Sharp Flexible Card(CP1T,Occupy 1 sub-slot)
                     Add: subbname8090DEVCR57L5XFI3(561605), -- 5-Port 10GBase LAN/WAN-SFP+ Fixed Card E
                     Add: subbname8090DEVCR57L2XFI2(561606), -- 2-Port 10GBase LAN/WAN-SFP+ Fixed Card E
                     Add: subbname8090DEVCR2D00E1NC10(561607), --1-Port 100GBase-CFP2 Physical Interface Card(PIC)
                     Add: subbname8090DEVCR2D00LAXF10(561608), --10-Port 10GBase LAN/WAN-SFP+ Physical Interface Card
                     Add: subbname8090DEVCR57EFGFH2(561609), -- 24-Port 1000Base-X-SFP Fixed Card E
                     Add: subbname8090DEVCR5D08DMD1M01(561610),   -- Bidirectional 1-Channel CWDM Optical Add/Drop Multiplexing (1471nm) Physical Interface Card(PIC)
                     Add: subbname8090DEVCR5D08DMD1M02(561611),   -- Bidirectional 1-Channel CWDM Optical Add/Drop Multiplexing (1491nm) Physical Interface Card(PIC)
                     Add: subbname8090DEVCR5D08DMD1M03(561612),   -- Bidirectional 1-Channel CWDM Optical Add/Drop Multiplexing (1511nm) Physical Interface Card(PIC)
                     Add: subbname8090DEVCR5D08DMD1M04(561613),   -- Bidirectional 1-Channel CWDM Optical Add/Drop Multiplexing (1531nm) Physical Interface Card(PIC)
                     Add: subbname8090DEVCR5D08DMD1M05(561614),   -- Bidirectional 1-Channel CWDM Optical Add/Drop Multiplexing (1551nm) Physical Interface Card(PIC)
                     Add: subbname8090DEVCR5D08DMD1M06(561615),   -- Bidirectional 1-Channel CWDM Optical Add/Drop Multiplexing (1571nm) Physical Interface Card(PIC)
                     Add: subbname8090DEVCR5D08DMD1M07(561616),   -- Bidirectional 1-Channel CWDM Optical Add/Drop Multiplexing (1591nm) Physical Interface Card(PIC)
                     Add: subbname8090DEVCR5D08DMD1M08(561617),   -- Bidirectional 1-Channel CWDM Optical Add/Drop Multiplexing (1611nm) Physical Interface Card(PIC)
                     Add: subbname8090DEVCR5D08DMD2M01(561618),   -- Bidirectional 2-Channel CWDM Optical Add/Drop Multiplexing (1471/1491nm) Physical Interface Card(PIC)
                     Add: subbname8090DEVCR5D08DMD2M02(561619),   -- Bidirectional 2-Channel CWDM Optical Add/Drop Multiplexing (1511/1531nm) Physical Interface Card(PIC)
                     Add: subbname8090DEVCR5D08DMD2M03(561620),   -- Bidirectional 2-Channel CWDM Optical Add/Drop Multiplexing (1551/1571nm) Physical Interface Card(PIC)
                     Add: subbname8090DEVCR5D08DMD2M04(561621),   -- Bidirectional 2-Channel CWDM Optical Add/Drop Multiplexing (1591/1611nm) Physical Interface Card(PIC)
                     Add: subbname8090DEVMEOM0E2NCE70(561627),   -- 2-Port 100GBase-CFP2 Flexible Card(BP480-E)
                     Add: subbname8090DEVMEOM0LEXFE70(561628),   -- 20-Port 10GBase LAN/WAN-SFP+ Flexible Card(BP480-E)
                     Add: subbname8090DEVCR5D0L5XFH71(561629),   -- 5-Port 10GBase LAN/WAN-SFP+ Flexible Card H(P51-H, Occupy two sub-slots)
                     Add: subbname8090DEVME0D0L5XXH7F(561630),   -- 5-Port 10GBase LAN/WAN-SFP+ Flexible Card H(BP51-H,occupy 2 sub-slot)
                     Add: subbname8090DEVBGWD0L5XFH71(561631),   -- 5-Port 10GBase LAN/WAN-SFP+ Flexible Card(BP100)
                     Add: subbname8090DEVCX68LGXF0(561632),   -- 28-Port 10GBase-X-SFP+ + 16-Port 100/1000Base-X-SFP
                     "


        REVISION    "201607150000Z"
        DESCRIPTION "V6.89,
                     Add: subnameNE08ENED3MD1(704550),--32 Channels E1 Interface Board
                     Modify: subnameLND1ME8M(708621) to subnameLND1ME4F(708621)
                     Modify: subnameLND1XE2S(708622) to subnameLND1ME4T(708622)
                     "

        REVISION    "201607120000Z"
        DESCRIPTION "V6.88,
                     Add:  fnameATNDEV910C-D(225559),           --ATN910C-D  chassis
                     Add:  fnamePTN970(229402),                       --PTN970  chassis
                     Add:  virentANGMHSTD0100(225575),           --ATN 910C 2 channel DC System,with 4*10GE(o), 8*10GE /GE/FE(o),8*GE/FE(e),16E1
                     Add:  virentANGMHSTD0200(225576),           --ATN 910C 2 channel AC System,with 4*10GE(o), 8*10GE /GE/FE(o),8*GE/FE(e),16E1
                     Add:  bnameTPKD00CXPA00(229422),           --TPK1CXPA, System Control,Cross-connect and Multi-protocol Process Unit
                     Add:  bnameTPKD00CXPB00(229423),           --TPK1CXPB, System Control,Cross-connect and Multi-protocol Process Unit
                     Add:  bnameTPKD000PIU00(229424),             --TPK1PIU, Power Interface Board
                     Add:  bnameTPKM000FAN00(229425),           --TPK1FAN, Fan box
                     Add:  subbnameANKD00EX4S00(225588),       --ATN980B, 4 Channels 10GE Optical Interface Board
                     Add:  subbnameANKD00EM20F0(225589),      --ATN980B, 20 Channels GE Optical Interface Board
                     Add:  subbnameCARD1ATN910CD(225590),    --ATN910C-D virtual card,4*10GE(o), 8*10GE /GE/FE(o),8*GE/FE(e)
                     Add:  subbnameCARD2ATN910CD(225591),    --ATN910C-D virtual card,16E1
                     Add:  subbnameTPKD000SQ100(229468),       --TPK1SQ1, 4 Channels STM-1 Optical Interface Board
                     Add:  subbnameTPKD00EX2S00(229469),       --TPK1EX2S, 2 Channel 10 GE Optical Interface board(SFP+)
                     Add:  subbnameTPKD00EX1S00(229470),       --TPK1EX1S, 1 Channel 10 GE Optical Interface board(SFP+)
                     Add:  subbnameTPKD00EM8F00(229471),      --TPK1EM8F, 8 Channels GE/FE Optical Interface Board
                     Add:  subbnameTPKD00EM8T00(229472),      --TPK1EM8T, 8 Channels GE/FE Electrical Interface Board
                     Add:  subbnameTPKD00EXL100(229473),       --TPK1EXL1, 1-Port 40GBase-CFP Physical Interface Card(PIC)
                     Add:  subbnameTPKD00MD1A00(229474),      --TPK1MD1A, 32 Channels E1 Interface Board(75ohm)
                     Add:  subbnameTPKD00MD1B00(229475),      --TPK1MD1B, 32 Channels E1 Interface Board(120ohm)
                     Add:  subbnameTPKD00ML1A00(229476),       --TPK1ML1A, 16 Channels E1 Interface Board(75ohm)
                     Add:  subbnameTPKD00ML1B00(229477),       --TPK1ML1B, 16 Channels E1 Interface Board(120ohm)
                     "


        REVISION    "201607090000Z"
        DESCRIPTION "V6.87,
                     Add:  virent8090DEVCR5D00E8NB60(562064), -- V8R9C00 for CR5D00E8NB60 CR56LPUI1T(sbom)
                     "

        REVISION    "201607080000Z"
        DESCRIPTION "V6.86,
                     Add:  fname8031S5320-28X-PWR-SI(537108),           --S5320-28X-PWR-SI
                     Add:  fname8031S5320-52X-PWR-SI(537109),           --S5320-52X-PWR-SI
                     Add:  fname8031S5320-28P-SI(537110),               --S5320-28P-SI
                     Add:  fname8031S5322-52X-LI-AC(537111),            --S5322-52X-LI-AC
                     Add:  fname8031S6320-54C-EI-48S(537112),           --S6320-54C-EI-48S
                     "

       REVISION    "201607050000Z"
       DESCRIPTION "V6.85,
                     delete:
                          virent8090DEVCR5D0L5XFA7F(564865),      --for V800R009C00 CR5D0L5XFA7F(SBOM),5-Port 10GBase LAN/WAN-SFP+ Integrated Line Processing Unit E(LPUI-52-E,Enhanced HQos)
                          virent8090DEVCR5DLAXFAJ7F(564866),      --for V800R009C00 CR5DLAXFAJ7F(SBOM),10-Port 10GBase LAN/WAN-SFP+ Integrated Line Processing Unit E(LPUI-120-E)
                          virent8090DEVME0D0LAXXH71(564867),      --for V800R009C00 ME0D0LAXXH71(SBOM),10-Port 10GBase LAN/WAN-SFP+ Broadband Service Unit Integrated E(BSUI-120-E)
                     modify:
                          virent8090DEVCR5D0L5XFA8E(564841) to virent8090DEVCR5D0L5XFA7F(564841)
                          virent8090DEVCR5DLAXFAJ8E(564843) to virent8090DEVCR5DLAXFAJ7F(564843)
                          virent8090DEVME0D0LAXXE71(564846) to virent8090DEVME0D0LAXXH71(564846)
                          virent8090DEVCR5DL2XEFG8E(564842) to virent8090DEVCR5DL2XFFG7E(564842)
                          virent600DEVCR5PM2HBAS70(564858) to virent600DEVCR5PM2HBAS72(564858)
                          virent600DEVCR5PM2HBAS71(564859) to virent600DEVCR5PM2HBAS73(564859)
                          virent600DEVCX6PM2HBAS70(564861) to virent600DEVCX6PM2HBAS72(564861)
                          virent600DEVCX6PM2HBAS71(564862) to virent600DEVCX6PM2HBAS73(564862)
                     add:
                          virent8090DEVCR5DMPUX8670(564865),      --for V800R009C00 CR5DMPUX8670(SBOM),Main Processing Unit B6
                          virent8090DEVCX6DMPUX8670(564866),      --for V800R009C00 CX6DMPUX8670(SBOM),Main Processing Unit B6
                          virentME60DEVME0DMPUX8670(159767),      --for V800R009C00 ME0DMPUX8670(SBOM),Main Processing Unit B6
                     "

       REVISION    "201606301700Z"
        DESCRIPTION "V6.84,
                     Add:  subbnameAND3MD10(225566), --32 Channels E1 Interface Board
                     Add:  subnameLND2DM1(708618),   --32 Channels E1 Interface Board
                     Add:  subnameLND1QC1(708619),   --4 Channels Channelized OC-3c/STM-1c POS Optical Interface Board
                     Add:  subnameLND1QP1(708620),   --4 Channels OC-3/STM-1 POS Optical Interface Board
                     Add:  subnameLND1ME8M(708621),  --4 Channels GE/FE Optical Interface and 4 Channels GE/FE Electric Interface Board
                     Add:  subnameLND1XE2S(708622),  --2 Channels 10GE Optical Interface Board(SFP+)
                     "

        REVISION    "201606181700Z"
        DESCRIPTION "V6.83,
                    Add: fnameATNDEV910C-A(225556),        --910C-A chassis
                    Add: fnameATNDEV910C-B(225557),        --910C-B chassis
                    Add: fnameATNDEV950C(225558),          --950C chassis
                    Add: fnameNE05E-SQ(704524),            -- NE05E-SQ chassis
                    Add: fnameNE08E-S6E(704525),           -- NE08E-S6E chassis
                    Add: bnameNEDD000PIU00(704512),        --NE08E, Power
                    Add: bnameNEDD000FAN00(704513),        --NE08E, FAN
                    Add: bnameANKD000PIU00(229005),        --ATN950C, Power
                    Add: bnameANKD000FAN00(229006),        --ATN950C, FAN
                    Add: bnameANGD00APIU00(229007),        --ATN910C-A/B AC Power
                    Add: bnameANGD000PIU00(229008),        --ATN910C-A/B DC Power
                    Add: bnameANGD000FAN00(229009),        --ATN910C-A/B FAN
                    Add: subbnameANDD00EM4F00(225575),     --ATN950C, 4 Channels GE/FE Optical Interface Board
                    Add: subbnameANDD00EM4T00(225576),     --ATN950C, 4 Channels GE/FE Electrical Interface Board
                    Add: subbnameANDD00EM8F00(225577),     --ATN950C, 8 Channels GE/FE Optical Interface Board
                    Add: subbnameANDD00EM8T00(225578),     --ATN950C, 8 Channels GE/FE Electrical Interface Board
                    Add: subbnameANDD00EX1S00(225579),     --ATN950C, 1 Channel 10 GE Optical Interface board(SFP+)
                    Add: subbnameANKD00EX2S00(225580),     --ATN950C, 2 Channel 10 GE Optical Interface board(SFP+)
                    Add: subbnameANDD16E17500(225581),     --ATN950C, 16 Channels E1 Interface Board(75ohm)
                    Add: subbnameANDD16E11200(225582),     --ATN950C, 16 Channels E1 Interface Board(120ohm)
                    Add: subbnameANDD32E17500(225583),     --ATN950C, 32 Channels E1 Interface Board(75ohm)
                    Add: subbnameANDD32E11200(225584),     --ATN950C, 32 Channels E1 Interface Board(120ohm)
                    Add: subnameNEDD00EM4F00(704560),      --NE08E, 4 Channels GE/FE Optical Interface Board
                    Add: subnameNEDD00EM4T00(704561),      --NE08E, 4 Channels GE/FE Electrical Interface Board
                    Add: subnameNEDD00EM8F00(704562),      --NE08E, 8 Channels GE/FE Optical Interface Board
                    Add: subnameNEDD00EM8T00(704563),      --NE08E, 8 Channels GE/FE Electrical Interface Board
                    Add: subnameNEDD00EX1S00(704564),      --NE08E, 1 Channel 10 GE Optical Interface board(SFP+)
                    Add: subnameNEDD00EX2S00(704565),      --NE08E, 2 Channel 10 GE Optical Interface board(SFP+)
                    Add: subnameNEDD16E17500(704566),      --NE08E, 16 Channels E1 Interface Board(75ohm)
                    Add: subnameNEDD16E11200(704567),      --NE08E, 16 Channels E1 Interface Board(120ohm)
                    Add: subnameNEDD32E17500(704568),      --NE08E, 32 Channels E1 Interface Board(75ohm)
                    Add: subnameNEDD32E11200(704569),      --NE08E, 32 Channels E1 Interface Board(120ohm)
                    Add: subnameCARDNE05ESQ(704570),       --NE05E virtual card
                    Add: subbnameLNDD01XE8F00(225585),     --ATN980B, 1 Channel 10GE Optical(SFP+)+8 Channels GE/FE Optical Interface Board
                    Add: subnameCARDATN910CA(225586),      --ATN910C-A virtual card
                    Add: subnameCARDATN910CB(225587)       --ATN910C-B virtual card
                    Add: virentANKD00CXPB00(225569),       --ATN950C, system Control,Cross-connect and Multi-protocol Process Unit,80G
                    Add: virentANKD00CXPA00(225570),       --ATN950C, system Control,Cross-connect and Multi-protocol Process Unit
                    Add: virentANGMHSTA0100(225571),       --ATN 910C 2 channel DC System,with 4*10GE(o), 8*10GE /GE/FE(o),16*GE/FE(o)
                    Add: virentANGMHSTB0100(225572),       --ATN 910C 2 channel AC System,with 4*10GE(o), 8*10GE /GE/FE(o),16*GE/FE(o)
                    Add: virentANGMHSTA0200(225573),       --ATN 910C 2 channel DC System,with 4*10GE(o), 8*10GE /GE/FE(o),8*GE/FE(o),8*GE/FE(e)
                    Add: virentANGMHSTB0200(225574),       --ATN 910C 2 channel AC System,with 4*10GE(o), 8*10GE /GE/FE(o),8*GE/FE(o),8*GE/FE(e)
                    Add: virentNEDD00CXPA00(704535),       --NE08E, system Control,Cross-connect and Multi-protocol Process Unit
                    Add: virentNECMHSTA0100(704536),       --NE05E-SQ 2 channel DC System,with 4*10GE(o), 8*10GE /GE/FE(o),16*GE/FE(o)
                    Add: virentNECMHSTB0100(704537),       --NE05E-SQ 2 channel AC System,with 4*10GE(o), 8*10GE /GE/FE(o),16*GE/FE(o)
                    Add: virentNECMHSTA0200(704538),       --NE05E-SQ 2 channel DC System,with 4*10GE(o), 8*10GE /GE/FE(o),8*GE/FE(o),8*GE/FE(e)
                    Add: virentNECMHSTB0200(704539),       --NE05E-SQ 2 channel AC System,with 4*10GE(o), 8*10GE /GE/FE(o),8*GE/FE(o),8*GE/FE(e)
                           "

        REVISION    "201606171700Z"
        DESCRIPTION "V6.82,
                      --for PTN7900 V1R7C10 20160617
                      Add:   bnamePTN7900TPA2EH1(229412), --TPA2EH1,1-port 100 Gigabit Ethernet Switching Processing Board
                      Add:   bnamePTN7900TPA1EH2(229413), --TPA1EH2,2-port 100 Gigabit Ethernet Switching Processing Board
                      Add:   bnamePTN7900TPA2EXL2(229414), --TPA2EXL2,2-port 40 Gigabit Ethernet Switching Processing Board
                      Add:   bnamePTN7900TPA1EX16S(229415), --TPA1EX16S,16-port 10 Gigabit Ethernet Switching Processing Board
                      Add:   bnamePTN7900TPA2EX12(229416), --TPA2EX12,12-port 10 Gigabit Ethernet Switching Processing Board
                      Add:   bnamePTN7900TPA1EX8S(229417), --TPA1EX8S,8-port 10 Gigabit Ethernet Switching Processing Board
                      --for PTN7900/990 V1R8C00 20160617
                      Mod:   bnamePTN7900TPA1MQ1(229418),   --TPA1MQ1,63 Channels E1 Interface Processing Board
                      Mod:   bnamePTN7900TPA2EG24(229419),  --TPA2EG24,24-port Gigabit Ethernet Switching Processing Board
                      Mod:   bnamePTN7900TPA1MPA(229420),   --TPA1MPA,Multi-port GE/STM-1/E1 Processing Board
                      Mod:   bnamePTN990TPJA000PIU00(229421),   --TPJA000PIU00,AC Power Interface Board
                           "
        REVISION    "201606080000Z"
        DESCRIPTION "V6.81,
                     ADD: bnameH901CVEC(148539),          --  Video board of MA5800 device.
                           "

        REVISION    "201606070000Z"
        DESCRIPTION "V6.80,
                     Add: bnameES1D2MCUAC00(663628),      --S7703,Main Control Unit A(Optional Clock)
                     Add: bnameES1D2SRUAC00(663629),      --S7706/S7712,Main Control Unit A(Optional clock)
                     "

        REVISION    "201606060000Z"
        DESCRIPTION "V6.79,
                     Add: AP6150DN,AP6050DN,AP4030TN,AP4050DN-E,AP4050DN-HD,AP7050DE,AP1010SN, AP2050DN,AP2050DN-S,AP2050DN-E,AP4050DE for WLAN ap
                     Update: AP4030DN-E,AP7050DN-E,AD9430DN-24,AD9430DN-12  for WLAN ap
                     "
        REVISION    "201606030000Z"
        DESCRIPTION "V6.78,
                     Add: virentME60DEVMEODBSUFMO70(161593),     -- for V800R009C00 MEODBSUFMO70(SBOM),Flexible Card Broadband Service Unit(BSUF-480,2 sub-slots)
                     Add: virentME60DEVMEODMSUFMO70(161594),     -- for V800R009C00 MEODMSUFMO70(SBOM),Flexible Card Broadband Service Unit(MSUF-480,2 sub-slots)
                     Add: virent8090DEVCR5DLPUFME70(564864),     -- for V800R009C00 CR5DLPUFME70(SBOM),Flexible Card Line Processing Unit E(LPUF-480-E)
                     Add: virent8090DEVCR5D0L5XFA7F(564865),      --for V800R009C00 CR5D0L5XFA7F(SBOM),5-Port 10GBase LAN/WAN-SFP+ Integrated Line Processing Unit E(LPUI-52-E,Enhanced HQos)
                     Add: virent8090DEVCR5DLAXFAJ7F(564866),      --for V800R009C00 CR5DLAXFAJ7F(SBOM),10-Port 10GBase LAN/WAN-SFP+ Integrated Line Processing Unit E(LPUI-120-E)
                     Add: virent8090DEVME0D0LAXXH71(564867),      --for V800R009C00 ME0D0LAXXH71(SBOM),10-Port 10GBase LAN/WAN-SFP+ Broadband Service Unit Integrated E(BSUI-120-E)
                     "

        REVISION    "201605310000Z"
        DESCRIPTION "V6.77,
                     Add: subbname8090DEVME0D0EAGFE70(561588), -- 10-Port 100/1000Base-X-SFP  Physical Interface Card E(PIC-E)
                     Add: subbname8090DEVME0D0L2XFE71(561589), -- 2-Port 10GBase LAN/WAN-SFP+  Physical Interface Card(PIC-E)
                     Add: subbname8090DEVCR5D0EFGFE71(561578), -- 24-Port 1000Base-X-SFP Flexible Card  E(P52-E)
                     Add: subbname8090DEVCR5D0L5XFE74(561579), -- 5-Port 10GBase LAN/WAN-SFP+ Flexible Card E(P52-E, Occupy two sub-slots)
                     Add: subbname8090DEVCR5D0L2XFE75(561580), -- 2-Port 10GBase LAN/WAN-SFP+ Flexible Card E(P52-E)
                     Add: subbname8090DEVCR5D0L5XFE76(561581), -- 5-Port 10GBase LAN/WAN-SFP+ Flexible Card E(P120-E)
                     Add: subbname8090DEVME0D0EFGFE7E(561582), -- 24-Port 1000Base-X-SFP Flexible Card E(BP52-E)
                     Add: subbname8090DEVME0D0L5XXE7E(561583), -- 5-Port 10GBase LAN/WAN-SFP+ Flexible Card E(BP52-E,occupy 2 sub-slot)
                     Add: subbname8090DEVME0D0L5XXE8E(561584), -- 5-Port 10GBase LAN/WAN-SFP+ Flexible Card E(BP120-E)
                     Add: subbname8090DEVME0D0L2XXE7E(561585), -- 2-Port 10GBase LAN/WAN-SFP+ Flexible Card E(BP5E-E)
                     Add: subbname8090DEVCR5D0LAXFH70(561586), -- 10-Port 10GBase LAN/WAN-SFP+ Flexible Card H(P240-H)
                     Add: subbname8090DEVCX6D0LAXFH10(561587),   -- 10-Port 10GBase LAN/WAN-SFP+ Flexible Card H(S200-H)
                     Add: subbname8090DEVCR5D0L2XFH72(561592),   -- 2-Port 10GBase LAN/WAN-SFP+  Physical Interface Card H (PIC-H)
                     Add: subbname8090DEVCR2D0L2XFH11(561590),   -- 8-Port 100/1000Base-X-SFP  Physical Interface Card H
                     Add: subbname8090DEVCR5D0E8GFH70(561593),   -- 2-Port 10GBase LAN/WAN-SFP+  Physical Interface Card H (PIC-H)
                     Add: subbname8090DEVCR2D0E8GFH10(561591),   -- 8-Port 100/1000Base-X-SFP  Physical Interface Card H

                     "

        REVISION    "201605270000Z"
        DESCRIPTION "V6.76,
                     Add: fnameMA5821-24GE-POE(561574),     --Virtual Frame H821MABC of the MA5821 24GE poe device.
                     Add: fnameMA5611SAE08PD8VDSL(561575),        --Virtual Frame MA5611S-AE08 of the MA5611S-AE08 8VDSL pd device.
                     Add: fnameMA5611SAE16PD16VDSL(561576),       --Virtual Frame MA5611S-AE16 of the MA5611S-AE16 16VDSL pd device.
                     Add: fnameMA5811SMA5811SAE08PD(561577),      --Virtual Frame MA5811S-AE08 of the MA5811S-AE08 G.fast pd device.
                     Add: bnameH825XCWA(156050),      --Master board of  of MA5821 POE.
                     Add: bnameHS22EPGP(156051),      --24 GE board of MA5821 POE.
                     Add: bnameH82BBVJM(156052),      --Master board of  of PH MA5611S-AE08 PD.
                     Add: bnameH82BBVUM(156053),      --Master board of  of PH MA5611S-AE16 PD.
                     Add: bnameH835BGUDR(156054),     --Master board of  of MA5811S-AE08 PD.
                     Add: bnameHS2BBVJM(156055),      --8 VDSL board of PH MA5611S-AE08 PD.
                     Add: bnameHS2BBVUM(156056),      --16 VDSL board of PH MA5611S-AE16 PD.
                     Add: subbnameH831CKMA(156057),   --  Clock subboard of MA5818
                     "

        REVISION    "201605170000Z"
        DESCRIPTION "V6.02,
                     Add: bnameH80XVPS(148014),          --  support vector board of MA5600T.
                     Add: bnameH901MPSC(148505),         --  control board of MA5800-X2
                     Add: bnameH901MPSD(148506),         --  control board of MA5800-X2
                     Add: bnameH901CGCD(148608),         --  8*GE and 10GE combo board of MA5800
                     Add: bnameH901XGSF(148609),         --  16*10GE board of MA5800
                     Add: bnameH901PISA(148610),         --  DC Power board of MA5800-X2
                     Add: bnameH901PISB(148611),         --  AC Power board of MA5800-X2
                     Add: bnameH901PISC(148612),         --  DC Power board of MA5800-X2
                     Add: subbnameH901CPCB(148513),      --  Clock subboard of MA5800-X2 H901MPSC
                     Add: subbnameH901CPCC(148514),      --  Clock subboard of MA5800-X2 H901MPSD
                     "

        REVISION    "201605130000Z"
        DESCRIPTION "V6.74,
                     Add: fnameAR161-S(667853),          -- AR161-S FRAME
                     Add: fnameAR161W-S(667854),         -- AR161W-S FRAME
                     Add: fnameAR161GW-Lc-S(667855),     -- AR161GW-Lc-S FRAME
                     Add: fnameAR509GW-L-D-H(667856),    -- AR509GW-L-D-H FRAME
                     Add: fnameSRG2340E(667857),         -- SRG2340E FRAME
                     Add: fnameSRG2320EI(667858),        -- SRG2320EI FRAME
                     Add: fnameSRG1320E(667859),         -- SRG1320E FRAME
                     Add: fnameAR1200EW-T1(667860),      -- AR1200EW-T1 FRAME

                     Add: bnameAR161-S(667951),                 -- AR161-S Main Control Unit
                     Add: bnameAR161W-S(667952),                -- AR161W-S Main Control Unit
                     Add: bnameAR161GW-Lc-S(667953),            -- AR161GW-Lc-S Main Control Unit
                     Add: bnameAR509GW-L-D-H(667954),           -- AR509GW-L-D-H Main Control Unit
                     Add: bnameSRG2340E(667955),                -- SRG2340E Main Control Unit
                     Add: bnameSRG2320EI(667956),               -- SRG2320EI Main Control Unit
                     Add: bnameSRG1320E(667957),                -- SRG1320E Main Control Unit
                     Add: bnameAR1200EW-T1(667958),             -- AR1200EW-T1 Main Control Unit
                     Add: bname1LTE-L-H(667959),                -- 1LTE-L-H Control Unit

             Modify: fnameAR1000v(667827) to fnameAR1000V(667827)
             Modify: bnameAR1000v(667917) to bnameAR1000V(667917)
             "

        REVISION    "201605111400Z"
        DESCRIPTION "V6.73,
                     Modify:  virent8090DEVCR5DSFUIT06A(562047),   -- NE5000E 1T Switch Fabric Unit for Single Chassis,
                     "

       REVISION    "201605110000Z"
        DESCRIPTION "V6.72,
                     Add: fnameATNDEV910B-DDC(225547),
                     Add: fnameATNDEV910B-DAC(225548),
                     Add: fnameATNDEV910B-FDC(225554),
                     Add: fnameATNDEV910B-FAC(225555),
                     "

        REVISION    "201605040000Z"
        DESCRIPTION "V6.71,
                     Modify:  fname8031E628-PWR-V2(537081),
                     Modify:  fname8031E628-V2(537083),
                     Modify:  bname8031E628-PWR-V2(537266),
                     Modify:  bname8031E628-V2(537268),
                     "

        REVISION    "201604220000Z"
        DESCRIPTION "V6.70,
                     Add:  fnameNGFW1UL0(16715814),  -- USG6300 L0 Frame Unit.
                     Add:  bnameSUF1MPUA-8GE-WL(16744453),  -- USG6300 1U Main Processing Unit Board.
                     Add:  bnameSUF1MPUA-8GE-W(16744452),  -- USG6300 1U Main Processing Unit Board.
                     Add:  bnameSUF1MPUA-8GE(16744451),  -- USG6300 1U Main Processing Unit Board.
                     Add:  bnameSUF1MPUA-4GE-W(16744450),  -- USG6300 1U Main Processing Unit Board.
                     Add:  bnameSUF1MPUA-4GE(16744449),  -- USG6300 1U Main Processing Unit Board.
                     "


        REVISION    "201604210000Z"
        DESCRIPTION "V6.69,
                     Add:subbname8090DEVCR2D00E1NC10(561574), --1-Port 100GBase-CFP2 Physical Interface Card(PIC)
                     Add:subbname8090DEVCR2D00LAXF10(561575), --10-Port 10GBase LAN/WAN-SFP+ Physical Interface Card
                     "




        REVISION    "201604190000Z"
        DESCRIPTION "V6.68,
                           Add: virent8090DEVCR5D0MPUB571(564850),    -- V8R8C10 season 4 for CR5D0MPUB571(SBOM), Main Processing Unit B5(16G Memory)
               Add: virent8090DEVCX6D0MPUB571(564851),    -- V8R8C10 season 4 for CX6D0MPUB571(SBOM), Main Processing Unit B5(16G Memory)
               Add: virentPTN6900DEVTNRD0MPUB571(229479), -- V8R8C10 season 4 for TNRD0MPUB571(SBOM), Main Processing Unit B5(16G Memory)
                   Add: virentME60DEVME0D0MPUB571(159764),    -- V8R8C10 season 4 for ME0D0MPUB571(SBOM), Main Processing Unit B5(16G Memory)

                   Add: virent8090DEVCR5D0MPUD471(564852),    --V8R8C10 season 4 for CR5D0MPUD471(SBOM),Main Processing Unit D4(16G Memory)
                   Add: virent8090DEVCX6D0MPUD471(564853),    --V8R8C10 season 4 for CX6D0MPUD471(SBOM),Main Processing Unit D4(16G Memory)
                   Add: virentPTN6900DEVTNRD0MPUD471(229480), --V8R8C10 season 4 for TNRD0MPUD471(SBOM),Main Processing Unit D4(16G Memory)

                   Add: virent8090DEVCR5D0SRUA871(564854),    -- V8R8C10 season 4 for CR5D0SRUA871(SBOM), Switch and Route Processing Unit A8(16G Memory)
                   Add: virent8090DEVCX6D0SRUA871(564855),    -- V8R8C10 season 4 for CX6D0SRUA871(SBOM), Switch and Route Processing Unit A8(16G Memory)
                   Add: virentPTN6900DEVTNRD0SRUA871(229482), -- V8R8C10 season 4 for TNRD0SRUA871(SBOM), Switch and Route Processing Unit A8(16G Memory)
                   Add: virentME60DEVME0D0SRUA871(159765),    -- V8R8C10 season 4 for ME0D0SRUA871(SBOM), Switch and Route Processing Unit A8(16G Memory)

                   Add: virent8090DEVCR5D0SRUA971(564856),    -- V8R8C10 season 4 for CR5D0SRUA971(SBOM), Switch and Route Processing Unit A9(16G Memory)
                   Add: virent8090DEVCX6D0SRUA971(564857),    -- V8R8C10 season 4 for CX6D0SRUA971(SBOM), Switch and Route Processing Unit A9(16G Memory)
                   Add: virentPTN6900DEVTNRD0SRUA971(229483), -- V8R8C10 season 4 for TNRD0SRUA971(SBOM), Switch and Route Processing Unit A9(16G Memory)
                   Add: virentME60DEVME0D0SRUA971(159766),    -- V8R8C10 season 4 for ME0D0SRUA971(SBOM), Switch and Route Processing Unit A9(16G Memory)
                 "

        REVISION    "201604161000Z"
        DESCRIPTION "V6.67,
                     Add:virent8090DEVCR9D00D8NC80(562063),   --NE9000 V8R9C00 for CR9D00D8NC80 (sbom)                     "



        REVISION    "201604151000Z"
        DESCRIPTION "V6.66,
                     Add:bname8031S5320-28P-SI-DC(537287), bname8031S5320-52P-SI-DC(537288), bname8031S5320-56C-PWR-EI-ACF(537289)
                     "


        REVISION    "201604150000Z"
        DESCRIPTION "V6.65,
                     Add: fname8031CX600-M2H(537102),       --Quidway CX600-M2H FRAME
                     Add: fname8090NE40E-M2H(562039),       --Quidway NE40E-M2H FRAME
                     Add: virent8090DEVCR9DEDNEIXB80(562053),   -- NE9000 LPUI-2T CR9DEDNEIXB80
                     Add: virent600DEVCR5PM2HBAS70(564858),    --V8R9C00 NE40E-M2H CR5PM2HBAS70(SBOM), 480Gbps MNPUI DC
                     Add: virent600DEVCR5PM2HBAS71(564859),    --V8R9C00 NE40E-M2H CR5PM2HBAS71(SBOM), 480Gbps MNPUI AC
                     Add: virent600DEVCR5B0BKP0373(564860),    --V8R9C00 NE40E-M2H CR5B0BKP0373(SBOM), 480Gbps MNPUI NO POWER
                     Add: virent600DEVCX6PM2HBAS70(564861),    --V8R9C00 CX600-M2H CX6PM2HBAS70(SBOM), 480Gbps MNPUI DC
                     Add: virent600DEVCX6PM2HBAS71(564862),    --V8R9C00 CX600-M2H CX6PM2HBAS71(SBOM), 480Gbps MNPUI AC
                     Add: virent600DEVCX6B0BKP0373(564863),    --V8R9C00 CX600-M2H CX6B0BKP0373(SBOM), 480Gbps MNPUI NO POWER
                     Add: virent8090DEVCR5DNPU48070(675865),     -- V8R9C00 for SBOM ,CR5DNPU48070, Network Processing Unit (NPU-480)
                     Add: virent8090DEVCR2DNSPC0010(675866)     -- V8R9C00 for SBOM ,CR2DNSPC0010, Network Service Processor (NSP-C)
                     "
        REVISION    "201604140000Z"
        DESCRIPTION "V6.64,
                     Add: bnameSPUB-X8X16-E8KE(16748627),     -- X8&X16 Firewall Service Processing Unit B.(0x00ff9053)
                     Add: bnameSPUA-X8X16-E8KE(16748628),     -- X8&X16 Firewall Service Processing Unit A. (0x00ff9054)
                     Add: bnameSPUB-X3-E8KE(16748629),     -- X3 Firewall Service Processing Unit B.(0x00ff9055)
                     Add: bnameSPUA-X3-E8KE(16748630),     -- X3 Firewall Service Processing Unit A.(0x00ff9056)
                     Add: subbnameSPCB-D-E8KE(16748631),     -- Firewall Processing card B.(0x00ff9057)
                     Add: subbnameSPCA-S-E8KE(16748632),     -- Firewall Processing card A.(0x00ff9058)
                     Add: bnameSPU-X3-B2(16748633),     -- X3 Service Processing Unit 2(Base Board). (0x00ff9059)
                     Add: bnameSPU-X8X16-20-B-E8KE(16748634),     -- 20G X8&X16 Firewall Service Processing Unit B(oversea).(0x00ff905a)
                     Add: bnameSPU-X8X16-20-A-E8KE(16748635),     -- 20G X8&X16 Firewall Service Processing Unit A(oversea).(0x00ff905b)
                     Add: bnameSPU-X3-20-A-E8KE(16748636),     -- 20G X3 Firewall Service Processing Unit A(oversea).(0x00ff905c)
                     Add: subbnameSPC-20-B-E8KE(16748637),     -- 20G Firewall Performance Expansion Card B(oversea).(0x00ff905d)
                     Add: subbnameSPC-20-A-E8KE(16748638),     -- 20G Firewall Performance Expansion Card A(oversea).(0x00ff905e)
                     Add: subbnameE8KE-X-20X1G-RJ45(16728066),     -- Finished Board Unit,Eudemon8000E-X,E8KE-X-20X1G-RJ45,20-Port 10/100/1000Base-RJ45 Flexible Card.(0x00ff4002)
                     Add: subbnameE8KE-X-3X40GE-QSFP(16728067),     -- Finished Board Unit,Eudemon8000E-X,E8KE-X-3X40GE-QSFP+,3-Port 40GBase-QSFP+ Flexible Card(P240-A).(0x00ff4003)
                     Add: bnameE8KE-X-LPUF-120(16748606),     -- Finished Board Unit,Eudemon8000E-X,E8KE-X-LPUF-120,Flexible Card Line Processing Unit(LPUF-120,2 sub-slots).(0x00ff903e)
                     Add: bnameE8KE-X-LPUF-240(16748607),     -- Finished Board Unit,Eudemon8000E-X,E8KE-X-LPUF-240,Flexible Card Line Processing Unit(LPUF-240,2 sub-slots).(0x00ff903f)
                     "
        REVISION    "201604110000Z"
        DESCRIPTION "V6.63,
                     Add: fnameEDFABP21(737285),     -- Virtual frame EDFABP21 of EDFA3220D device.
                     Add: bnameEDFAHFA1(746001),     -- HFA board of EDFA3220D.
                     Add: bnameEDFAFAN1(746002),     -- FAN board of EDFA3220D.
                     Add: bnameEDFAPWR1(746003),     -- PWR board of EDFA3220D.
                     Add: bnameEDFAEMU1(746004),     -- Master board of EDFA3220D.
                     "
        REVISION    "201604070000Z"
        DESCRIPTION "V6.62,
                   Add: virent8090DEVCR5D0MPUB571(564850),    -- V8R8C10 season 4 for CR5D0MPUB571(SBOM), Main Processing Unit B5(16G Memory)
                   Add: virent8090DEVCX6D0MPUB571(564851),    -- V8R8C10 season 4 for CX6D0MPUB571(SBOM), Main Processing Unit B5(16G Memory)
                   Add: virentPTN6900DEVTNRD0MPUB571(229479), -- V8R8C10 season 4 for TNRD0MPUB571(SBOM), Main Processing Unit B5(16G Memory)
                   Add: virentME60DEVME0D0MPUB571(159764),    -- V8R8C10 season 4 for ME0D0MPUB571(SBOM), Main Processing Unit B5(16G Memory)

                   Add: virent8090DEVCR5D0MPUD471(564852),    --V8R8C10 season 4 for CR5D0MPUD471(SBOM),Main Processing Unit D4(16G Memory)
                   Add: virent8090DEVCX6D0MPUD471(564853),    --V8R8C10 season 4 for CX6D0MPUD471(SBOM),Main Processing Unit D4(16G Memory)
                   Add: virentPTN6900DEVTNRD0MPUD471(229480), --V8R8C10 season 4 for TNRD0MPUD471(SBOM),Main Processing Unit D4(16G Memory)

                   Add: virent8090DEVCR5D0SRUA871(564854),    -- V8R8C10 season 4 for CR5D0SRUA871(SBOM), Switch and Route Processing Unit A8(16G Memory)
                   Add: virent8090DEVCX6D0SRUA871(564855),    -- V8R8C10 season 4 for CX6D0SRUA871(SBOM), Switch and Route Processing Unit A8(16G Memory)
                   Add: virentPTN6900DEVTNRD0SRUA871(229482), -- V8R8C10 season 4 for TNRD0SRUA871(SBOM), Switch and Route Processing Unit A8(16G Memory)
                   Add: virentME60DEVME0D0SRUA871(159765),    -- V8R8C10 season 4 for ME0D0SRUA871(SBOM), Switch and Route Processing Unit A8(16G Memory)

                   Add: virent8090DEVCR5D0SRUA971(564856),    -- V8R8C10 season 4 for CR5D0SRUA971(SBOM), Switch and Route Processing Unit A9(16G Memory)
                   Add: virent8090DEVCX6D0SRUA971(564857),    -- V8R8C10 season 4 for CX6D0SRUA971(SBOM), Switch and Route Processing Unit A9(16G Memory)
                   Add: virentPTN6900DEVTNRD0SRUA971(229483), -- V8R8C10 season 4 for TNRD0SRUA971(SBOM), Switch and Route Processing Unit A9(16G Memory)
                   Add: virentME60DEVME0D0SRUA971(159766),    -- V8R8C10 season 4 for ME0D0SRUA971(SBOM), Switch and Route Processing Unit A9(16G Memory)
                 "


        REVISION    "201604011100Z"
        DESCRIPTION "V6.61,
                     Modify:
                     virent8090DEVCR5D00E8NC61(562045),   -- 8-Port 100GBase-CFP2- Integrated Line Process Unit(NE5000E LPUI-1T)
                     virent8090DEVCR5D00EFMB61(562046),   -- 24-Port 40GBase-QSFP+ Integrated Line Process Unit (NE5000E LPUI-1T)
                     virent8090DEVCR5D00EDNC60(562050),   -- 16-Port 100GBase-CFP4 Integrated Line Process Unit (NE5000E LPUI-2T)
                     DEL:
                     virent8090DEVCR5DEDNEIXB60(562051),  -- 16-Port 100GBase-QSFP28 + 32-Port 10GBase-QSFP+ Integrated Line Process Unit (NE5000E LPUI-2T)
                 "

        REVISION    "201603291700Z"
        DESCRIPTION "V6.60,
                     The object identifier of switch V2R10 is added
                     "

        REVISION    "201603290000Z"
        DESCRIPTION "V6.59,
                     ADD:
                     fnameCE685548T6QHI(688156),          -- CloudEngine CE6855-48T6Q-HI Switch (48-Port 10GE RJ45, 6-Port 40GE QSFP+)
                     fnameCE685548S6QHI(688157),          -- CloudEngine CE6855-48S6Q-HI Switch (48-Port SFP+ Optical,6-Port 40GE QSFP+)
                     bnameCE685548T6QHI(688215),              -- Manufactured Board,CloudEngine 6800,CEM48T6QP02,48 Port 10GE RJ45, 6 Port 40GE QSFP+ Optical Switch Control Unit,1*1
                     bnameCE685548S6QHI(688216),              -- Manufactured Board,CloudEngine 6800,CEM48S6QP05,48-Port SFP+ Optical,6-Port 40GE QSFP+ Optical Switch Control Unit,1*1
                     portnameDCDE01QSFP28(688138),           -- The port with 100G QSFP type
                     portnameDCDE01SFP25G(688139),           -- The port with 25G SFP type
                     Modify:
                     portnameDCDE01CFP2(688135),             -- The port with 100G CFP2 type
                     portnameDCDE01CXP(688136),              -- The port with 100G CXP type
                 "
        REVISION    "201603251000Z"
        DESCRIPTION "V6.58,
                     Modify:
                     fname8090NE9000X20(562038),       --Quidway NE9000-X20 FRAME to   fname8090NE9000-20(562038),       --Quidway NE9000-20 FRAME
                 "


        REVISION    "201603211701Z"
        DESCRIPTION "V6.57,
                     ADD:
                     bnameH901TWED(148607),           --  8*10G GPON board of MA5800.
                 "

        REVISION    "201603211635Z"
        DESCRIPTION "V6.56,
                     ADD:
                     bnamePTN990TPJA000PIU00(229415),           --TPJA000PIU00,AC Power Interface Board
                     "

        REVISION    "201603211500Z"
        DESCRIPTION "V6.56,
                     Add:subbname8090DEVCR57EFGFH0(561458),       --03031YYN, CR5D0EFGFH70, 24-Port 1000Base-X-SFP Flexible Card H(P51-H)
                     Add:subbname8090DEVME03EFGFH0(561459),       --03031YYT, ME0D0EFGFH7H, 24-Port 1000Base-X-SFP Flexible Card H(BP51-H)
                     Add:subbname8090DEVCR57L5XFI0(561460),       --03031XPT, CR5D0L5XFE70, 5-Port 10GBase LAN/WAN-SFP+ Flexible Card E(P51-E, Occupy two sub-slots)
                     Add:subbname8090DEVCR57L5XFI2(561461),      --03031XPU, CR5D0L5XFH71, 5-Port 10GBase LAN/WAN-SFP+ Flexible Card H(P51-H, Occupy two sub-slots)
                     Add:subbname8090DEVCR57L5XFI01(561462),      --03031XPV, CR5D0L5XFE71, 5-Port 10GBase LAN/WAN-SFP+ Flexible Card E(P101-E)
                     Add:subbname8090DEVCR57L5XFI02(561463),      --03031XPW, CR5D0L5XFH70, 5-Port 10GBase LAN/WAN-SFP+ Flexible Card H(P120-H)
                     Add:subbname8090DEVME03L5XFI1(561464) ,      --03031XPX, ME0D0L5XXE7F, 5-Port 10GBase LAN/WAN-SFP+ Flexible Card E(BP51-E,occupy 2 sub-slot)
                     Add:subbname8090DEVME03L5XFI2(561465) ,      --03031XPY, ME0D0L5XXH7F, 5-Port 10GBase LAN/WAN-SFP+ Flexible Card H(BP51-H,occupy 2 sub-slot)
                     Add:subbname8090DEVME03L5XFI0(561466),       --03031XQA, ME0D0L5XXE7H, 5-Port 10GBase LAN/WAN-SFP+ Flexible Card E(BP100-E)
                     Add:subbname8090DEVME03L5XFI3(561467) ,      --03031XQB, ME0D0L5XFH7H, 5-Port 10GBase LAN/WAN-SFP+ Flexible Card H(BP100-H)
                     Add:subbname8090DEVCR57L2XFI1(561468),       --03031YYP, CR5D0L2XFH70, 2-Port 10GBase LAN/WAN-SFP+ Flexible Card H(P51-H)
                     Add:subbname8090DEVCR57L2XFI0(561469),       --03031XQD, CR5D0L2XFE70, 2-Port 10GBase LAN/WAN-SFP+ Flexible Card E(P51-E)
                     Add:subbname8090DEVME03L2XFI0(561470),       --03031XQF, ME0D0L2XXE7H, 2-Port 10GBase LAN/WAN-SFP+ Flexible Card E(BP51-E)
                     Add:subbname8090DEVME03L2XFI1(561471),       --03031XQG, ME0D0L2XXE8H, 2-Port 10GBase LAN/WAN-SFP+ Flexible Card H(BP51-H)
                     Add:subbname8090DEVCR57EFGFH1(561472),       --03031XQJ, CR5D0EFGFE70, 24-Port 1000Base-X-SFP Flexible Card E(P51-E)
                     Add:subbname8090DEVME03EFGFH1(561473),       --03031XQM, ME0D0EFGFE7H, 24-Port 1000Base-X-SFP Flexible Card H(BP51-H)
                     Add:subbname8090DEVCX62L5XFH0(561474) ,      --03032AWL, CX6D0L5XFH10, 5-Port 10GBase LAN/WAN-SFP+ Flexible Card H(S102-H)
                     Add:subbname8090DEVBGW01L5XFH0(561475) ,     --03032AWM, BGWD0L5XFH71, 5-Port 10GBase LAN/WAN-SFP+ Flexible Card(BP100)
                     Add:subbname600DEVCR57EFGFH2(561515),       -- V6R9C20,03031XQL,24-Port 1000Base-X-SFP Fixed Card E
                     Add:subbname600DEVCR57L5XFI3(561516),       -- V6R9C20,03031XQC,5-Port 10GBase LAN/WAN-SFP+ Fixed Card E
                     Add:subbname600DEVCR57L2XFI2(561517),       -- V6R9C20,03031XQH,2-Port 10GBase LAN/WAN-SFP+ Fixed Card E
                     Add:virent8090DEVCR5D0L5XFA8E(564841),      --CR5D0L5XFA8E,5-Port 10GBase LAN/WAN-SFP+ Integrated Line Processing Unit E(LPUI-52-E,Enhanced HQos)
                     Add:virent8090DEVCR5DL2XEFG8E(564842),      --CR5DL2XEFG8E,2-Port 10GBase LAN/WAN-SFP+ + 24-Port 1000Base-X-SFP Integrated Line Processing Unit E(LPUI-52-E,Enhanced HQos)
                     Add:virent8090DEVCR5DLAXFAJ8E(564843),      --CR5DLAXFAJ8E,10-Port 10GBase LAN/WAN-SFP+ Integrated Line Processing Unit E(LPUI-103-E)
                     Add:virent8090DEVME0DL2XEFG8E(564844),      --ME0DL2XEFG8E,2-Port 10GBase LAN/WAN-SFP++24-Port 1000Base-SFP Broadband Service Unit Integrated E(BSUI-52-E)
                     Add:virent8090DEVME0D0L5XXE71(564845),      --ME0D0L5XXE71,5-Port 10GBase LAN/WAN-SFP+ Broadband Service Unit Integrated E(BSUI-52-E)
                     Add:virent8090DEVME0D0LAXXE71(564846),      --ME0D0LAXXE71,10-Port 10GBase LAN/WAN-SFP+ Broadband Service Unit Integrated E(BSUI-101-E)
                     Add:virent8090DEVCR5DLPUFE07E(564847),      --CR5DLPUFE07E,Flexible Card Line Processing Unit(LPUF-200-E)
                     Add:virent8090DEVME0DBSUFB070(564848),      --ME0DBSUFB070,Flexible Card Broadband Service Unit(BSUF-120,2 sub-slots)
                     Add:virent8090DEVME0DBSUFC870(564849),      --ME0DBSUFC870,Flexible Card Broadband Service Unit(BSUF-200,2 sub-slots)
                     Add:subbname8090DEVCR57LAXFH0(561441) ,     --03031EAS, CX6D0LAXFH10, 10-Port 10GBase LAN/WAN-SFP+ Flexible Card H(S200-H)
                    "

        REVISION    "201603181700Z"        DESCRIPTION "V6.54,
                     Add: virent8090DEVCR5DSFUFT050(562058),   -- NE5000E V8R9C00 for CR5DSFUFT050(sbom)
                     Add: virent8090DEVCR5DSFUIT06H(562059),    -- NE5000E V8R9C00 for CR5DSFUIT06H(sbom)
                     Add: virent8090DEVCR5D0MPUA750(562060),   -- NE5000E V8R9C00 for CR5D0MPUA750(sbom)
                     Add: virent8090DEVCR5D0MPUB660(562061),   -- NE5000E V8R9C00 for CR5D0MPUB660(sbom)
                     Add: virent8090DEVCR5DLPUFT060(562062),   -- NE5000E V8R9C00 for CR5DLPUFT060(sbom)
                     Add: virent8090DEVCR5D0OFCT050(561716),   -- NE5000E V8R9C00 for CR5D0OFCT050(sbom).
                     "


        REVISION    "201603171700Z"
        DESCRIPTION "V6.53,
                     Add: subbnameH831GE4A(155688),     -- 4 GE upstream subboard.
                     "

        REVISION    "201603111700Z"
        DESCRIPTION "V6.52,
                     Add: fnameMA5621-FE-DC(561572),        --Frame MA5621-FE-DC of the MA5621(sd5130) device(DC).
                     Add: fnameMA5621H831MABC-DC(561573),   --Backplane of MA5621(SD5103) Spec master Frame:H831MABC(DC).
                     Add: bnameHS22EPFFMA5621(156049),      --4 FE board of MA5621.
                     "

        REVISION    "201602291700Z"
        DESCRIPTION "V6.51,
                     Modify: bnameHS35BGUDM(155999) to bnameHS35BGUD(155999).
                     Add: bnameHS35BGUDM(156048),        --8 G.FAST board of MA5811S-AE08  device(AC).
                     Del: fnameMA5811S-AE08-AC(561571),  --Virtual frame MA5811S-AE08 of MA5811S_AE08 device(AC).
                     "


        REVISION    "201602220900Z"
        DESCRIPTION "V6.50,
                     Add: fnameAR2204E-D(667830),        -- AR2204E-D FRAME
                     Add: fnameAR2504E-H(667831),        -- AR2504E-H FRAME
                     Add: fnameAR509G-Lc(667832),        -- AR509G-Lc FRAME
                     Add: fnameAR129CGVW-L(667833),      -- AR129CGVW-L FRAME
                     Add: fnameAR101-S(667834),          -- AR101-S FRAME
                     Add: fnameAR101W-S(667835),         -- AR101W-S FRAME
                     Add: fnameAR550C-4GE(667836),       -- AR550C-4GE FRAME
                     Add: fnameAR550C-2C6GE(667837),     -- AR550C-2C6GE FRAME
                     Add: fnameAR509CG-Lt(667838),       -- AR509CG-Lt FRAME
                     Add: fnameAR509CG-Lt-N(667839),     -- AR509CG-Lt-N FRAME
                     Add: fnameAR503EQGW-L(667840),      -- AR503EQGW-L FRAME
                     Add: fnameAR503EW(667841),          -- AR503EW FRAME
                     Add: fnameAR503EDGW-Lc(667842),     -- AR503EDGW-Lc FRAME
                     Add: fnameAR509CG-L(667843),        -- AR509CG-L FRAME
                     Add: fnameAR168FVW(667844),         -- AR168FVW FRAME
                     Add: fnameAR532(667845),            -- AR532 FRAME
                     Add: fnameAR502ERc(667846),         -- AR502ERc FRAME
                     Add: fnameAR502EGR-L(667847),       -- AR502EGR-L FRAME
                     Add: fnameAR502EG-L(667848),        -- AR502EG-L FRAME
                     Add: fnameAR502EGW-L(667849),       -- AR502EGW-L FRAME
                     Add: fnameAR550E(667850),           -- AR550E FRAME
                     Add: fnameAR509CG-Lc(667851),       -- AR509CG-Lc FRAME
                     Add: fnameAR2204-51GE-R(667852),    -- AR2204-51GE-R FRAME

                     Add: bnameAR2204E-D(667920),               -- AR2204E-D Main Control Unit
                     Add: bname2VDSL2(667921),                  -- 2VDSL2 Control Unit
                     Add: bnameAR2504E-H(667922),               -- AR2504E-H Main Control Unit
                     Add: bnameAR509G-Lc(667923),               -- AR509G-Lc Main Control Unit
                     Add: bnameAR129CGVW-L(667924),             -- AR129CGVW-L Main Control Unit
                     Add: bnameAR101-S(667925),                 -- AR101-S Main Control Unit
                     Add: bnameAR101W-S(667926),                -- AR101W-S Main Control Unit
                     Add: bnameAR550C-4GE(667927),              -- AR550C-4GE Main Control Unit
                     Add: bnameAR550C-2C6GE(667928),            -- AR550C-2C6GE Main Control Unit
                     Add: bnameAR509CG-Lt(667929),              -- AR509CG-Lt Main Control Unit
                     Add: bnameAR509CG-Lt-N(667930),            -- AR509CG-Lt-N Main Control Unit
                     Add: bnameAR503EQGW-L(667931),             -- AR503EQGW-L Main Control Unit
                     Add: bnameAR503EW(667932),                 -- AR503EW Main Control Unit
                     Add: bnameAR503EDGW-Lc(667933),            -- AR503EDGW-Lc Main Control Unit
                     Add: bnameAR509CG-L(667934),               -- AR509CG-L Main Control Unit
                     Add: bnameAR168FVW(667935),                -- AR168FVW Main Control Unit
                     Add: bnameAR532(667936),                   -- AR532 Main Control Unit
                     Add: bnameAR502ERc(667937),                -- AR502ERc Main Control Unit
                     Add: bnameAR502EGR-L(667938),              -- AR502EGR-L Main Control Unit
                     Add: bnameAR502EG-L(667939),               -- AR502EG-L Main Control Unit
                     Add: bnameAR502EGW-L(667940),              -- AR502EGW-L Main Control Unit
                     Add: bnameAR550E(667941),                  -- AR550E Main Control Unit
                     Add: bname1LTE-L(667942),                  -- 1LTE-L Control Unit
                     Add: bname1LTE-Lt(667943),                 -- 1LTE-Lt Control Unit
                     Add: bname1LTE-Lo(667944),                 -- 1LTE-Lo Control Unit
                     Add: bnameHDDSATA(667945),                 -- HDDSATA Control Unit
                     Add: bname3G-HSPA7-H(667946),              -- 3G-HSPA+7-H Control Unit
                     Add: bnameARPAC-60WC(667947),              -- PAC-60WC Power Card Unit
                     Add: bnameAR509CG-Lc(667948),              -- AR509CG-Lc Main Control Unit
                     Add: bnameAR2204-51GE-R(667949),           -- AR2204-51GE-R Main Control Unit
                     Add: bname1LTE-Lc(667950),                 -- 1LTE-Lc Control Unit

                     Modify: fnameAR2504(667810) to fnameAR2504-H(667810)
                     Modify: bnameAR2504(667895) to bnameAR2504-H(667895)
                     Modify: bnameAR8ES3GS(667896) to bnameAR8ES2GS(667896)
                     Modify: bnameAR8ES3G(667897) to bnameAR8ES2G(667897)
                     "

        REVISION    "201602170900Z"
        DESCRIPTION "V6.49,
                     Add: bnameH901XSED(148604),           --  8*10G GPON board of MA5800.
             Add: bnameH901GPHD(148605),           --  8*GPON board of MA5800.
                     Add: bnameH901GPSD(148606),           --  8*GPON board of MA5800.
                     "


        REVISION    "201602030900Z"
        DESCRIPTION "V6.48,
                     Add: bnameH835BGUDM(156044),        --Master board of MA5811S-AE08 device(AC).
                     Add: fnameMA5811S-AE08-AC(561571),  --Virtual frame MA5811S-AE08 of MA5811S_AE08 device(AC).
                     Modify: bnameHS35BGUD(155999) to bnameHS35BGUDM(155999).
                     "


        REVISION    "201602020900Z"
        DESCRIPTION "V6.47,
                     Add: fnamePTN990-AC(229401),     -- PTN990 Chassis with AC power.
                     Add: bnamePTN7900TPA1MQ1(229412),         --TPA1MQ1,63 Channels E1 Interface Processing Board
                     Add: bnamePTN7900TPA2EG24(229413),        --TPA2EG24,24-port Gigabit Ethernet Switching Processing Board
                     Add: bnamePTN7900TPA1MPA(229414),         --TPA1MPA,Multi-port GE/STM-1/E1 Processing Board
                     "


        REVISION    "201601281500Z"
        DESCRIPTION "V6.46,
                     Add: bnameLE1D2X48SEC1(659614)
                     Add: bnameES1D2X48SEC0(663611)
                     "

        REVISION    "201601280000Z"
        DESCRIPTION "V6.45,
                     Add: fnameCE88604CEI(688155),             -- CloudEngine CE8860-4C-EI Switch(with 4 interface slots)
                     Add: bnameCEL36LQEG(688207),              -- Manufactured Board,CloudEngine 12800-CE-L36LQ-EG,36-Port 40GE Interface Card(EG,QSFP+)-1*1
                     Add: bnameCE88604CEI(688208),             -- CloudEngine CE8860-4C-EI Switch(with 4 interface slots)
                     Add: bnameCEL02LQEC(688209),              -- Manufactured Board,CloudEngine 12800,CE-L02LQ-EC,2-Port-40G Interface Card(EC,QSFP+)
                     Add: bnameCEL04CFMD(688210),              -- Manufactured Board,CloudEngine 12800,CE-L04CF-MD,4-Port-100GE Interface Card(MD,CFP),1*1
                     Add: bnameCEL24LQMC1(688211),             -- Manufactured Board,CloudEngine 12800,CE-L24LQ-EC1,24-Port-40G Interface Card(MC1,QSFP+),1*1
                     Add: bnameCEL12LQMD(688212),              -- Manufactured Board,CloudEngine 12800,CE-L12LQ-MD,12-Port-40G Interface Card(MD,QSFP+),1*1
                     Add: bnameCEL48XSMD(688213),              -- Manufactured Board,CloudEngine 12800,CE-L48XS-MD,48-Port-10GE Interface Card(MD,QSFP+),1*1
                     Add: bnameCEL48XSMC(688214),              -- Manufactured Board,CloudEngine 12800,CE-L48XS-MC,48-Port-10GE Interface Card(MC,QSFP+),1*1
                     Add: subbnameCED24S2CQ(688137),           -- Manufactured Board,CloudEngine 8800,CE88-D24S2CQ,CE8860:24-Port-10G(SFP+),2-Port-100G(QSFP28) Interface Card,1*1
                     Add: subbnameCED24T2CQ(688138),           -- Manufactured Board,CloudEngine 8800,CE88-D24T2CQ,CE8860:24-Port 10GBASE-T(RJ45),2-Port-100G(QSFP28) Interface Card,1*1
                     Add: subbnameCED16Q(688139),              -- Manufactured Board,CloudEngine 8800,CE88-D16Q,CE8860:16-Port-40G Interface Card(QSFP+),1*1
                     Add: subbnameCED8CQ(688140),              -- Manufactured Board,CloudEngine 8800,CE88-D8CQ,CE8860:8-Port-100G Interface Card(QSFP28),1*1
                     "

          REVISION    "201601221600Z"
          DESCRIPTION "V6.44,
                      Add:     virent8090DEVCX6DISUFM010(564820),     -- V8R8C10,LPUF480,Flexible Card Line Processing Unit(LPUF-480)
                      Add:     virent8090DEVCX6DISUFE012(564821),     -- V8R8C10,LPUF-200,Flexible Card Integrated Service Unit(ISUF-201)
                      Add:     virent8090DEVCR5D00E8NC7C(564822),      -- for V800R008C10 CR5D00E8NC7C(SBOM), 8-Port 100GBase-CFP2 Integrated Line Processing Unit B(LPUI-1T-L)
                      Add:     virent8090DEVCR5D00LMXF7C(564823),      -- for V800R008C10 CR5D00LMXF7C(SBOM), 48-Port 10GBase LAN/WAN-SFP+ Integrated Line Processing Unit (LPUI-480-L)
                      Add:     virent8090DEVCR5DE2NLFX7C(564825),      -- for V800R008C10 CR5DE2NLFX7C(SBOM), 2-Port 100GBase-CFP2 + 24-Port 10GBase LAN/WAN-SFP+ Integrated Line Processing Unit (LPUI-480-L)
                      Add:     virent8090DEVCX6DSFUIM01B(564826),     --CX6DSFUIM01B,480Gbps Switch Fabric Unit B(SFUI-480-B)
                      Add:     virent8090DEVCR5D00E4NC7C(564827),      -- for V800R008C10 CR5D00E4NC7C(SBOM), 4-Port 100GBase-CFP2 Integrated Line Processing Unit (LPUI-480-L)
                      Add:     virent8090DEVCX6DSFUIM01C(564828),     --CX6DSFUIM01C 480Gbps Switch Fabric Unit(SFUI-480-B)
                      Add:     virent8090DEVCX6D0MPUB510(564829),     --CX6D0MPUB510 Main Processing Unit B5
                      Add:     virent8090DEVCX6D0SRUA810(564830),     --CX6D0SRUA810 Switch and Route Processing Unit A8
                      Add:     virent8090DEVCX6D0MPUD410(564832),     --CX6D0MPUD410,Main Processing Unit D4
                      Add:     virent8090DEVCX6D0SRUA771(564834),     --CX6D0SRUA771,Enhanced Switch and Route Processing Unit A5
                      Add:     virent8090DEVCR5DLPUFM07B(564836),      -- CR5DLPUFM07B,Flexible Card Line Processing Unit(LPUF-480-B)
                      Add:     virent8090DEVCR5D00LMXF7B(564837),      -- CR5D00LMXF7B,48-Port 10GBase LAN/WAN-SFP+ Integrated Line Processing Unit (LPUI-480-B)
                      Add:     virent8090DEVCR5DE2NLFX7B(564838),      -- CR5DE2NLFX7B,2-Port 100GBase-CFP2 + 24-Port 10GBase LAN/WAN-SFP+ Integrated Line Processing Unit (LPUI-480-B)
                      Add:     virent8090DEVCR5D00E4NC7B(564839),      -- CR5D00E4NC7B,4-Port 100GBase-CFP2 Integrated Line Processing Unit (LPUI-480-B)
                      Add:     virent8090DEVCX6D0LEXFA11(564840),      --CX6D0LEXFA11,20-Port 10GBase LAN/WAN-SFP+ Integrated  Integrated Service Unit (ISUI-201)

                      Add:     virentME60DEVME0D0SRUB570(161589),     --ME0D0SRUB570 Switch and Route Processing Unit A10
                      Add:     virentME60DEVME0DSFUIM07B(161590),   -- for V800R008C10 ME0DSFUIM07B(SBOM),480Gbps Switch Fabric Unit B(SFUI-480-B)
                      Add:     virentME60DEVME0DSFUIM07C(161591),   -- for V800R008C10 ME0DSFUIM07C(SBOM),480Gbps Switch Fabric Unit C(SFUI-480-C)
                      Add:     virentPTN6900DEVTNRD0SRUB570(229481),  --TNRD0SRUB570,Enhanced Switch and Route Processing Unit A5
              "
        REVISION    "201601191600Z"
        DESCRIPTION "V6.43,
              ADD: subbname8090DEVCR56E8NCE(561455),   -- NE5000E,CR56E8NCE , 8-Port 100GBase-CFP4
              ADD: subbname8090DEVCR56E8NLDXA(561456), --NE5000E,CR56E8NLDXA, 8-Port 100GBase-CFP4 + 16-Port 10GBase-QSFP+
              ADD: subbname8090DEVCR56EDNLIXV(561457), --NE5000E,CR56EDNLIXV, 16-Port 100GBase-QSFP28 + 32-Port 10GBase-QSFP+
              "

        REVISION    "201601181600Z"
        DESCRIPTION "V6.42,
              ADD: subbname8090DEVME0D0LAXFE7H(561420), -- 10-Port 10GBase LAN/WAN-SFP+ Flexible Card E(BP240-E)
              ADD: subbname8090DEVCX6D0E2NCA10(561667),   --2-Port 100GBase-CFP2 Flexible Card A(S480-A)
              ADD: subbname8090DEVCX6D0LFXFA11(561668),   --24-Port 10GBase LAN/WAN-SFP+ Flexible Card A(S480-A)
                    "

        REVISION    "201601141600Z"
        DESCRIPTION "V6.41,
                     Add: fnameLX1BS9303S00(659471)
                     Add: fnameLX1BS9306S00(659472)
                     Add: fnameLX1BS9312S00(659473)
                     "

        REVISION    "201601111600Z"
        DESCRIPTION "V6.40,
                     Add: subbnameH836ASDB(156048),     -- VOIP DSP Subboard H836ASDB.
                     "

        REVISION    "201512281600Z"
        DESCRIPTION "V6.39,
                     Add: fnameMA5800H901BPSB(148513),     -- Backplane of the MA5800-X2.
                     Add: bnameH901MPSA(148503),           -- control board of MA5800-X2
                     Add: bnameH902MPLA(148504),           -- control board of MA5800
                     Add: subbnameH901CPCA(148512),        -- Clock subboard of MA5800-X2 H901MPSA
                     Add: bnameH901MPWD(148601),           -- AC Power board of MA5800-X2
                     Add: bnameH901MPWE(148602),           -- DC Power board of MA5800-X2
                     Add: bnameH901MPWC(148603),           -- DC Power board of MA5800-X2
                     "

        REVISION    "201512260000Z"
        DESCRIPTION "V6.38,
                  ADD:
                   NE0508E HWPCBType: 0x000AC000~0x000ACFFF(704512~708607)
                   ETN HWPCBType: 0x000AD000~0x000ADFFF(708608~712703)
                   bnameLNDD01FAN(708608),               --Fan board, etn550-A
                   "

        REVISION    "201512230000Z"
        DESCRIPTION "V6.37,
                   ADD: bnameHS22EPGDMA5878(156047),   --8GE board of MA5878 device.
                   "

        REVISION    "201512220000Z"
        DESCRIPTION "V6.36,
                     Add: fnameH821MABCMA5821(561570),   --Virtual frame H821MABC of MA5821(sd5568) device.
                     Add: bnameH823TCIAT(156045),         --Master board of MA5821(sd5568) device.
                     Add: bnameHS23TCIAT(156046),         --24GE and 1*10GE board of MA5821(sd5568) device.
                     "

        REVISION    "201512180000Z"
        DESCRIPTION "V6.35,
                     Add: fnameMA56948VD-DC(145958),       -- Virtual frame MA5694-VD of the MA5694(8VD) DC device.
                     Add: fnameMA56944VD-DC(145972),       -- Virtual frame MA5694-VD of the MA5694(4VD) DC device.
                     "

        REVISION    "201512150000Z"
        DESCRIPTION "V6.34,
                     Add: fnameH831MABMMA5818(561568),   --Frame H831MABM of the MA5818 device.
                     Add: fnameMA5621-FE(561569),        --Frame MA5621-FE of the MA5621(sd5130) device(AC).
                     Add: bnameH831CCMAMA5818(156036),   --Master board of MA5818 device.
                     Add: bnameVPJ(156037),               --G.FAST vectoring serial control engine board of the MA5818 device.
                     Add: bnameINT(156038),               --Serial board(without VP chip) of the MA5818 device.
                     Add: bnameH831PAMA(156039),         --550W AC power board of the MA5818 device.
                     Add: bnameH831PAMB(156040),         --550W AC power board(support standby power) of the MA5818 device.
                     Add: bnameH831PDMA(156041),         --550W DC power board of the MA5818 device.
                     Add: bnameFDS(156042),              --24 line G.FAST serial board of the MA5818 device.
                     Add: bnameH823E2IQ(156043),         --Master board of the MA5621(sd5130) device.
                     Add: subbnameH832XS1C(156044),      --XG-SPON subboard of the MA5878 device.
                     "

        REVISION    "201512100000Z"
        DESCRIPTION "V6.33,
                     Add: fnameMA5800H901BPIB(148512),     -- 19inch, 200G backplane for MA5800-X15.
                     "

        REVISION    "201512090000Z"
        DESCRIPTION "V6.32,
                      Add:     virent8090DEVCX6DISUFM010(564820),     -- V8R8C10,LPUF480,Flexible Card Line Processing Unit(LPUF-480)
                      Add:     virent8090DEVCX6DISUFE011(564821),     -- V8R8C10,LPUF-200,Flexible Card Integrated Service Unit(ISUF-201)
                      Add:     virent8090DEVCR5D00E8NC7C(564822),      -- for V800R008C10 CR5D00E8NC7C(SBOM), 8-Port 100GBase-CFP2 Integrated Line Processing Unit B(LPUI-1T-L)
                      Add:     virent8090DEVCR5D00LMXF7C(564823),      -- for V800R008C10 CR5D00LMXF7C(SBOM), 48-Port 10GBase LAN/WAN-SFP+ Integrated Line Processing Unit (LPUI-480-L)
                      Add:     virent8090DEVCR5DE2NLFX7C(564825),      -- for V800R008C10 CR5DE2NLFX7C(SBOM), 2-Port 100GBase-CFP2 + 24-Port 10GBase LAN/WAN-SFP+ Integrated Line Processing Unit (LPUI-480-L)
                      Add:     virent8090DEVCX6DSFUIM01B(564826),     --CX6DSFUIM01B,480Gbps Switch Fabric Unit B(SFUI-480-B)
                      Add:     virent8090DEVCR5D00E4NC7C(564827),      -- for V800R008C10 CR5D00E4NC7C(SBOM), 4-Port 100GBase-CFP2 Integrated Line Processing Unit (LPUI-480-L)
                      Add:     virent8090DEVCX6DSFUIM01C(564828),     --CX6DSFUIM01C 480Gbps Switch Fabric Unit(SFUI-480-B)
                      Add:     virent8090DEVCX6D0MPUB510(564829),     --CX6D0MPUB510 Main Processing Unit B5
                      Add:     virent8090DEVCX6D0SRUA810(564830),     --CX6D0SRUA810 Switch and Route Processing Unit A8
                      Add:     virent8090DEVCX6D0MPUD410(564832),     --CX6D0MPUD410,Main Processing Unit D4
                      Add:     virent8090DEVCX6D0SRUA771(564834),     --CX6D0SRUA771,Enhanced Switch and Route Processing Unit A5
                      Add:     virent8090DEVCR5DLPUFM07B(564836),      -- CR5DLPUFM07B,Flexible Card Line Processing Unit(LPUF-480-B)
                      Add:     virent8090DEVCR5D00LMXF7B(564837),      -- CR5D00LMXF7B,48-Port 10GBase LAN/WAN-SFP+ Integrated Line Processing Unit (LPUI-480-B)
                      Add:     virent8090DEVCR5DE2NLFX7B(564838),      -- CR5DE2NLFX7B,2-Port 100GBase-CFP2 + 24-Port 10GBase LAN/WAN-SFP+ Integrated Line Processing Unit (LPUI-480-B)
                      Add:     virent8090DEVCR5D00E4NC7B(564839),      -- CR5D00E4NC7B,4-Port 100GBase-CFP2 Integrated Line Processing Unit (LPUI-480-B)
                      Add:     virent8090DEVCX6D0LEXFA11(564840),      --CX6D0LEXFA11,20-Port 10GBase LAN/WAN-SFP+ Integrated  Integrated Service Unit (ISUI-201)
                      Add:     virentME60DEVME0DSFUIU07B(161585),     -- V8R8C10,SFU1TB,1Tbps Switch Fabric Unit B(SFUI-1T-B)
                      Add:     virentME60DEVME0DSFUIU07C(161586),     --ME0DSFUIU07C 1Tbps Switch Fabric Unit C(SFUI-1T-C)
                      Add:     virentME60DEVME0D0MPUB570(161587),     --ME0D0MPUB570 Main Processing Unit B5
                      Add:     virentME60DEVME0D0SRUA970(161588),     --ME0D0SRUA970 Switch and Route Processing Unit A9
                      Add:     virentME60DEVME0D0SRUAE70(161589),     --ME0D0SRUAE70 Switch and Route Processing Unit A10
                      Add:     virentME60DEVME0DSFUIM07B(161590),   -- for V800R008C10 ME0DSFUIM07B(SBOM),480Gbps Switch Fabric Unit B(SFUI-480-B)
                      Add:     virentME60DEVME0DSFUIM07C(161591),   -- for V800R008C10 ME0DSFUIM07C(SBOM),480Gbps Switch Fabric Unit C(SFUI-480-C)
                      Add:     virentME60DEVME0D0SRUA870(161592),   -- for V800R008C10 ME0D0SRUA870(SBOM),Switch and Route Processing Unit A8
                      Add:     virentPTN6900DEVTNRD0SRUA571(229481),  --TNRD0SRUA571,Enhanced Switch and Route Processing Unit A5
                         "



        REVISION    "201512072126Z"
        DESCRIPTION "V6.31,
                      ADD:virent8090DEVCR58CMUB(562052),   -- NE9000 Centralized Monitoring Board
                      "

                    REVISION    "201512041000Z"
        DESCRIPTION "V6.30,
             Add: subbname8090DEVCR2D00A2CF10(570048),   -- CR2D00A2CF10, 2-Port OC-3c/STM-1c ATM-SFP Physical Interface Card"


        REVISION    "201511270000Z"
        DESCRIPTION "V6.29,
                     Add: bnameH901OXEG(148600),           --  24*10GE board of MA5800.
                     Add: fnameMA5800H901BPLE(148511),     -- Backplane of the MA5800.
                     "

        REVISION    "201511240000Z"
        DESCRIPTION "V6.18,
                     ADD: fnameAD9430DN-24-FAT(692268)----WLAN new AP.
                     ADD: fnameAD9430DN-12-FAT(692269)----WLAN new AP.
                      "

        REVISION    "201511191700Z"
        DESCRIPTION "V6.27,
                   ADD: bnameH82DEFMG(156034),   --Master board of MA5811S-AE48/DE48 device.
                   ADD: bnameHS2DEFMG(156035),   --48 G.FAST board of MA5811S-AE48/DE48 service board.
                   ADD: fnameMA5811S-AE48(561566),  --Virtual frame MA5811S-AE48 of MA5811S_AE48 device.
                   ADD: fnameMA5811S-DE48(561567),  --Virtual frame MA5811S-DE48 of MA5811S_DE48 device.
                   "


        REVISION    "201511171000Z"
        DESCRIPTION "V6.26,
              ADD: subbname8090DEVCR56EDNCV(561453),   -- NE5000E,CR56EDNCV,16-Port 100GBase-CFP4
              ADD: subbname8090DEVCR56EDNBV(561454),   -- NE5000E,CR56EDNBV,16-Port 100GBase-QSFP28
                    "

        REVISION    "201511161953Z"
        DESCRIPTION "V6.25,
              ADD: bnameLE1D2X08SSC0(659584),      --S9300, 8-Port 10GBASE-X Interface Card(SC,SFP+)                    "

        REVISION    "201511051953Z"
        DESCRIPTION "V6.24,
              ADD: fname8090NE9000X20(562038),       --Quidway NE9000-X20 FRAME
              ADD: virent8090DEVCR5D0MPUN080(562040),   -- NE9000 Main Processing Unit N(NE9000 MPUN)
              ADD: virent8090DEVCR9D00E8NC80(562041),   -- 8-Port 100GBase-CFP2- Integrated Line Process Unit(NE9000 LPUI-1T)
              ADD: virent8090DEVCR9D00EFMB80(562042),   -- 24-Port 40GBase-QSFP+ Integrated Line Process Unit (NE9000 LPUI-1T)
              ADD: virent8090DEVCR5D0SFUT080(562043),   -- NE9000 1T Switch Fabric Unit for Single Chassis (NE9000 SFUI-1T)
              ADD: virent8090DEVCR9D00EPXF80(562044),   -- 60-Port 10GBase LAN/WAN-SFP+ Integrated Line Process Unit (NE9000 LPUI-1T)
              ADD: virent8090DEVCR5D00E8NC61(562045),   -- 8-Port 100GBase-CFP4- Integrated Line Process Unit(NE5000E LPUI-1T)
              ADD: virent8090DEVCR5DE8NEDX61(562046),   -- 8-Port 100GBase-CFP4 + 16-Port 10GBase-QSFP+ Integrated Line Process Unit (NE5000E LPUI-1T)
              ADD: virent8090DEVCR5DSFUIT06A(562047),   -- NE5000E 1T Switch Fabric Unit for Single Chassis
              ADD: virent8090DEVCR5DSFUIT26A(562048),   -- NE5000E-X16B 2T CLC Switch Fabric Unit for Single Chassis (SFU-2T-A)
              ADD: virent8090DEVCR5D00EDNB60(562049),   -- 16-Port 100GBase-QSFP28 Integrated Line Process Unit (NE5000E LPUI-2T)
              ADD: virent8090DEVCR5DEDNEIXB60(562050),   -- 16-Port 100GBase-QSFP28 + 32-Port 10GBase-QSFP+ Integrated Line Process Unit (NE5000E LPUI-2T)
                    "
        REVISION    "201511051000Z"
        DESCRIPTION "V6.23,
              ADD: fnameAR111-S(667824),          -- AR111-S FRAME
              ADD: fnameAR503GW-LcM7(667825),     -- AR503GW-LcM7 FRAME
              ADD: fnameAR511GW-LcAV2M3(667826),  -- AR511GW-LcAV2M3 FRAME
              ADD: fnameAR1000v(667827),          -- AR1000v FRAME
              ADD: fnameAR511DcGW-LcAV2(667828),  -- AR511DcGW-LcAV2 FRAME
              ADD: fnameAR2204-51GE(667829),      -- AR2204-51GE FRAME

              ADD: bnameAR111-S(667914),                 -- AR111-S Main Control Unit
              ADD: bnameAR503GW-LcM7(667915),            -- AR503GW-LcM7 Main Control Unit
              ADD: bnameAR511GW-LcAV2M3(667916),         -- AR511GW-LcAV2M3 Main Control Unit
              ADD: bnameAR1000v(667917),                 -- AR1000v Main Control Unit
              ADD: bnameAR511DcGW-LcAV2(667918),         -- AR511DcGW-LcAV2 Main Control Unit
              ADD: bnameAR2204-51GE(667919),             -- AR2204-51GE Main Control Unit
                    "

        REVISION    "201510311700Z"
        DESCRIPTION "V6.22,
                   Add: subnameSUBCMC(148511),              -- SUBCMC subboard.
                   "

        REVISION    "201510301000Z"
        DESCRIPTION "V6.21,
                     Add: fnameH832MABL(561563),             --Virtual frame H832MABL of the MA5878(SD5568) device.
                     Add: fnameH821MABCMA5821GE(561564),     --Virtual frame H821MABC of the MA5821(GE) device.
                     Add: fnameH821MABCMA5822GE(561565),     --Virtual frame H821MABC of the MA5822(GE) device.
                     Add: bnameH836CCLD(156032),             -- Master board of MA5878(SD5568).
                     Add: bnameH831EGUC(156033),             -- 8GE board of MA5878 device.
                    "

        REVISION    "201510271000Z"
        DESCRIPTION "V6.20,
                     delete: fnameATNDEV910B-DAC(225547),         --910B-D AC chassis.
                             fnameATNDEV910B-EAC(225548),         --910B-E chassis
                             fnameNE05E-SN(704523),             -- NE05E-SN chassis
                 fnameETN500-B(708609),              --ETN500-B chassis
                             fnameETN500-C(708610),              --ETN500-C chassis
                     add: subbnameAND2EX8F(225565),          -- 1 Channel 10GE (SFP+),8 Channels GE/FE Optical Interface Board
                          subnameLND1ME8F(708612),                       -- 8 Channels Fast Ethernet Optical Interface Board
                          subnameLND1ME8T(708613),                       -- 8x GE service interface board electric
                          subnameLND1XE1S(708614),                       --1 Channel 10GE Optical Interface Board
                          subnameLND1XE8F(708615),                       -- 1 Channel 10GE (SFP+),8 Channels GE/FE Optical Interface Board
                          subnameLND1DM1A(708616),                       --32x E1 service interface board (75 ohms)
                          subnameLND1DM1B(708617),                       --32x E1 service interface board (120 ohms)
                          subnameNE08ENED1MPAA(704546),          --4-Channel FXS/FXO+2-Channel E&M+2-Channel RS232+2-Channel RS485 Board
                          subnameNE08ENED1SA8(704547),           --8-Channel V.35/X.21/V.24 Board
                          subnameNE08EPWRPIC(704548),            --the pic of TNF1APIU
                          subnameNE08ENED1MP8A(704549),          --4-Channel C37.94,4-Channel CoDir64K
                          subnameNE08ENED3MD1(704550),--32 Channels E1 Interface Board
                          virentATN910BANG1CXPD-DC(225560),   --ATN 910B 2 channel DC System,with 8*GE/FE(e),16*GE/FE(o),4*10GE(o)
                          virentATN910BANG1CXPD-AC(225561),   --ATN 910B 2 channel AC System,with 8*GE/FE(e),16*GE/FE(o),4*10GE(o)
                          virentLND1MXUA(708611),                 --Cross-connect and Multi-protocol Process Unit
                          bnameNE08ETNF1APIU(704527),          --AC Power Interface Board
                  fnameETN550-A(708609),                        --ETN550-A chassis
             modify:  virentNE05E-SN(704524)  to virentNE05E-SN(704526)  "


        REVISION    "201510231000Z"
        DESCRIPTION "V6.19,
                     Add: bnameH835CCFE(156009),      -- Master board of MA5612 Box type device.
                     Add: bnameCAL(156030),           -- 32 ADSL+32 POTS serial combo board.
                     Add: bnameH832PDVSB(156031),     -- DC Power board H832PDVSB of the MA5616.
                    "

        REVISION    "201510221000Z"
        DESCRIPTION "V6.18,
                     Add: fnameAP7050DN-E-FAT(692267)----WLAN new AP"

        REVISION    "201510201000Z"
        DESCRIPTION "V6.17,
                     Add: fnameAP4030DN-E(692266)----WLAN new AP"

        REVISION    "201510131000Z"
        DESCRIPTION "V6.16,
              ADD: fname8031S5720-14X-PWH-SI-AC(536960),
              ADD: fname8031S6720S-26Q-EI-24S-AC(536961),
              ADD: fname8031S6720S-26Q-EI-24S-DC(536962),
              ADD: fname8031S6320-26Q-EI-24S-AC(536963),
              ADD: fname8031S6320-26Q-EI-24S-DC(536964),
              ADD: fname8031S5300-28TP-PWR-LI-AC(536965),
              ADD: fname8031S5300-10P-PWR-LI-AC-NEW(536966),
              ADD: fname8031S5320-28X-SI-DC(536967),
              ADD: fname8031S5320-52X-SI-DC(536968),
              ADD: fname8031S5720-28X-PWR-SI-DC(536969),
                   fname8031S5720-52X-PWR-SI-DC(536970),
              ADD: fname8031S5320-52X-PWR-SI-ACF(536971),
              ADD: fname8031S5720-28X-SI-DC(536972),
              ADD: fname8031S5720-52X-SI-DC(536973),
              ADD: fname8031S5720S-28X-SI-DC(536974),
              ADD: fname8031S5720S-52X-SI-DC(536975),
              ADD: fname8031S5720-32X-EI-DC(536976),
              ADD: fname8031S5720-50X-EI-DC(536977),
              ADD: fname8031S5720-32X-EI-24S-DC(536978),
              ADD: fname8031S5720-50X-EI-46S-DC(536979),
              ADD: fname8031S5720-36C-EI-DC(536980),
                    "


        REVISION    "201510101000Z"
        DESCRIPTION "V6.15,
                     Add: subbname8090DEVCR5D00A2CF70(570047),  -- CR5D00A2CF70, 2-Port OC-3c/STM-1c ATM-SFP Physical Interface Card"

        REVISION    "201509301000Z"
        DESCRIPTION "V6.13,
                     Add: fnameME60X2-M8A(161583),              -- Quidway ME60M-X2-M8A FRAME
                     Add: fnameME60X2-M8A-DC(161584),           -- Quidway ME60M-X2-M8A-DC FRAME
                     Add: fnameME60X2-M16A(161585),             -- Quidway ME60M-X2-M16A FRAME

                     Add: fnameME60S8A(161586),                 -- Quidway ME60S-X2-S8A FRAME
                     Add: fnameME60S8A-DC(161587),              -- Quidway ME60S-X2-S8A-DC FRAME
                     Add: fnameME60S16A(161588),                -- Quidway ME60S-X2-S16A FRAME

                     ADD: virent8090DEVCR5DSRUA5E71(564819),      -- for V800R008C00 CR5DSRUA5E71(SBOM), Switch and Route Processing Unit A5E

                     Add: fname8031CX600-X3ADO(536921),           -- Quidway CX600-3ADO Carrier Switch.

                Add: fname8090CX600-X16ADO(536960),               --Quidway CX600-X16ADO-AC Carrier Switch
                Add: fname8090CX600-X16ADO-DC(536961),            --Quidway CX600-X16ADO-DC Carrier Switch
                Add: fname8090CX600-X8ADO(536962),                --Quidway CX600-X8ADO-AC Carrier Switch
                Add: fname8090CX600-X8ADO-DC(536963),             --Quidway CX600-X8ADO-DC Carrier Switch
                Add: fname8031CX600-X3ADO(536964),                  -- Quidway CX600-3ADO Carrier Switch

                Add: fname8031CX600-M8A(536965),                  --Quidwy CX600-M8A-AC FRAME
                Add: fname8031CX600-M8A-DC(536966),               --Quidwy CX600-M8A-DC FRAME
                Add: fname8031CX600-M8ADO(536967),                --Quidwy CX600-M8ADO-AC FRAME
                Add: fname8031CX600-M8ADO-DC(536968),             --Quidwy CX600-M8ADO-DC FRAME
                Add: fname8031CX600-M16A(536969),                 --Quidwy CX600-M16AFRAME
                Add: fname8031CX600-M16ADO(536970),               --Quidwy CX600-M16ADO-AC FRAME

                Add: fname8090NE40E-X2-M8A(562035),          -- Quidwy CX600-X2-M8A FRAME, ne40e
                Add: fname8090NE40E-X2-M8A-DC(562036),       -- Quidwy CX600-X2-M8A-DC  FRAME, ne40e
                Add: fname8090NE40E-X2-M16A(562037),         -- Quidwy CX600-X2-M16A FRAME, ne40e

                Add: fnameME60X2-M8A(161583),           -- Quidway ME60M-X2-M8A FRAME
                Add: fnameME60X2-M8A-DC(161584),            -- Quidway ME60M-X2-M8A-DC FRAME
                Add: fnameME60X2-M16A(161585),          -- Quidway ME60M-X2-M16A FRAME
                Add: fnameME60S8A(161586),              -- Quidway ME60S-X2-S8A FRAME
                Add: fnameME60S8A-DC(161587),           -- Quidway ME60S-X2-S8A-DC FRAME
                Add: fnameME60S16A(161588),             -- Quidway ME60S-X2-S16A FRAME

                Add: fnamePTN6900-M8A(229398),      --PTN 6900-2-M8A Integrated DC Chassis Components
                Add: fnamePTN6900-M8A-DC(229399),   --PTN 6900-2-M8A Integrated AC Chassis Components
                Add: fnamePTN6900-M16A(229400),     --PTN 6900-2-M16A Integrated Chassis Components

                Add: fnameNE20E-X2-M8A(675848),      --Quidway CX600-X2-M8A-AC FRAME,ne20e
                Add: fnameNE20E-X2-M8A-DC(675849),   --Quidway CX600-X2-M8A-DC FRAME,ne20e
                Add: fnameNE20E-X2-M16A(675850),     --Quidway CX600-X2-M16A FRAME,ne20e

                Add: virent8090DEVCR5DSRUA5E71(564819),      -- for V800R008C00 CR5DSRUA5E71(SBOM), Switch and Route Processing Unit A5E

 "


        REVISION    "201509291000Z"
        DESCRIPTION "V6.13,
                     Add: subbname8090DEVCR5D00EEGF70(561562),       -- CX68EEGFAE, 20-Port 100/1000Base-X-SFP  Physical Interface Card(PIC)
                     Add: subbname8090DEVCR2D00EEGF10(675896),       -- CX68EEGFAE, 20-Port 100/1000Base-X-SFP Physical Interface Card
                    "

        REVISION    "201509171000Z"
        DESCRIPTION "V6.12,
                     Add: bnameHS22EPGB(156006),      -- 16GE board of MA582x device.
                     Add: bnameH826XPUB(156007),      -- Master board of MA582x 16GE device.
                     Add: bnameHS22EPGD(156008),      -- 8GE board of MA582x device.
                    "
        REVISION    "201509161000Z"
        DESCRIPTION "V6.11,
                     Add: fnameMA56948VD(145959),       -- Virtual frame MA5694-VD of the MA5694(8VD) device.
                     Add: fnameMA5621A4(145960),        -- Virtual frame MA5621A-4 of the MA5621A(4 serial port) device.
                    "

        REVISION    "201509151000Z"
        DESCRIPTION "V6.10,
              ADD: subbname8090DEVCR53CFE1(564527),   --24-Port Channelized E1/T1-DB100 Flexible Card
              ADD: subbname8090DEVCX6D0LAXFA12(561442),   --10-Port 10GBase LAN/WAN-SFP+ Flexible Card A(S200-A) V5 561415
              ADD: subbname8090DEVCX6D0E3MFA10(561443),   --3-Port 40GBase-QSFP+ Flexible Card(S200-A)
              ADD: subbname8090DEVCX6D0E1NCA10(561444),   --1-Port 100GBase-CFP Flexible Card A(S102-A)
              ADD: subbname8090DEVCX6D0E1MCA10(561445),   --1-Port 40GBase LAN-CFP Flexible Card A(S102-A)
              ADD: subbname8090DEVME0D0LAXFB7H(561446),   --10-Port 10GBase LAN/WAN-SFP+ Flexible Card(BP240) V5 561419
              ADD: subbname8090DEVCR57L3XFA2(561447),   --3-Port 10GBase LAN/WAN-SFP+ Fixed Card
              ADD: subbname8090DEVCR56E8NCB(561448),   -- NE5000E,CR56E8NCB,8*100Gbps CFP2 Interface Board
              ADD: subbname8090DEVCR56EFMBB(561449),   -- NE5000E,CR56EFMBB,24*40Gbps QSFP+ Interface Board
              ADD: subbname8090DEVCR58E8NCD(561450),   -- NE9000,CR58E8NCD,8-Port 100GBase-CFP2
              ADD: subbname8090DEVCR58EFMBD(561451),   -- NE9000,CR58EFMBD,24-Port 40GBase-QSFP+
              ADD: subbname8090DEVCR58EPXFB(561452),   -- NE9000,CR58EPXFB,60-Port 10GBase LAN/WAN-SFP+
              ADD: subbname8090DEVCR5DP4C2HF7020(561547),   -- CX68P2HFC, 4-Port OC-3c/STM-1c (or 2-Port OC12c/STM-4c)  POS-SFP Physical Interface Card(PIC)
              ADD: subbnameCR5DP2C1HF70(675895),        -- CX68P2CFC, 2-Port OC-3c/STM-1c (or 1-Port OC12c/STM-4C) POS-SFP  Physical Interface Card(PIC)
              ADD: subbnameCR2DP4C2HF1120(675894),      -- CX68P2HFC, 4-Port OC-3c/STM-1c (or 2-Port OC12c/STM-4c)  POS-SFP  Physical Interface Card
              ADD: subbnameCR2DP2C1HF1120(675893),      -- CX68P1HFC, 2-Port OC-3c/STM-1c (or 1-Port OC12c/STM-4C) POS-SFP  Physical Interface Card
              ADD: subbnameCR5DP2C1HF7020(675892),      -- CX68P2CFC, 2-Port OC-3c/STM-1c (or 1-Port OC12c/STM-4C) POS-SFP  Physical Interface Card(PIC)
                    "


        REVISION    "201509110900Z"
        DESCRIPTION "V6.09,
              ADD: bnameH80XATR(146150),          --  ATR series voice board of MA5600T device,
              ADD: bnameH901CRED(148538),         --  IP backhaul board of MA5800."

        REVISION    "201509101400Z"
        DESCRIPTION "V6.08,
                    Add: fnameATNDEV980B-DC(225552),                --980B DC chassis
                    Add: fnameATNDEV980B-AC(225553),                --980B AC chassis
                    Add: fnameNE05E-SN(704523),                            -- NE05E-SN chassis
                    Add: bnameATNANJ1FAN(225341),                     --Fan board, 980B
                    Add: bnameATNTNF5PIU(225342),                        --DC Power board, 980B
                    Add: bnameATNTNF5APIU(225343),                     --AC Power board, 980B
                    Add: subbnameANJ1EXL1(225563),                     --Channel 40GE Optical Interface Board
                    Add: virentANJ1CXP01(225556),                          --ATN 980B,ANJ1CXP01,System Control,Cross-connect and Multi-protocol Process Unit
                    Add: virentNE05E-SN(704524),                             --12G AC System with 16 Channels E1,support Temperature Harden,natural heat dissipation  "

          REVISION    "201508241000Z"
          DESCRIPTION "V6.07,
         Modify:virent8090DEVCR5DL2NLEX60(562039),   -- NE5000E,CR56E2NLEXF0,2 port 100GBase CFP2 & 20 port 10GBase LAN/WAN-SFP+ Line Processing Unit(NE5000E LPUI-400)

  "


        REVISION    "201508131000Z"
        DESCRIPTION "V6.06,
              ADD: fnameAR531GZ-U-D(667814),      -- AR531GZ-U-D FRAME
              ADD: fnameAR161FGW-LA(667815),      -- AR161FGW-LA FRAME
              ADD: fnameAR515GW-LM9-D(667816),    -- AR515GW-LM9-D FRAME
              ADD: fnameAR161G-U(667817),         -- AR161G-U FRAME
              ADD: fnameAR121GW-L(667818),        -- AR121GW-L FRAME
              ADD: fnameAR129GW-L(667819),        -- AR129GW-L FRAME
              ADD: fnameAR502G-L-D-H(667820),     -- AR502G-L-D-H FRAME
              ADD: fnameAR502GR-L-D-H(667821),    -- AR502GR-L-D-H FRAME
              ADD: fnameAR531G-F(667822),         -- AR531G-F FRAME
              ADD: fnameAR511CGW-LAV2M3(667823),  -- AR511CGW-LAV2M3 FRAME

              ADD: bnameAR531GZ-U-D(667904),             --  AR531GZ-U-D Main Control Unit
              ADD: bnameAR161FGW-LA(667905),             --  AR161FGW-LA Main Control Unit
              ADD: bnameAR515GW-LM9-D(667906),           --  AR515GW-LM9-D Main Control Unit
              ADD: bnameAR161G-U(667907),                --  AR161G-U Main Control Unit
              ADD: bnameAR121GW-L(667908),               --  AR121GW-L Main Control Unit
              ADD: bnameAR129GW-L(667909),               --  AR129GW-L Main Control Unit
              ADD: bnameAR502G-L-D-H(667910),            --  AR502G-L-D-H Main Control Unit
              ADD: bnameAR502GR-L-D-H(667911),           --  AR502GR-L-D-H Main Control Unit
              ADD: bnameAR531G-F(667912),                --  AR531G-F Main Control Unit
              ADD: bnameAR511CGW-LAV2M3(667913),         --  AR511CGW-LAV2M3 Main Control Unit
                    "

        REVISION    "201508071900Z"
        DESCRIPTION "V6.05,
                     Add: bnameH901PILB(148537),         --  Power board of MA5800
                    "

        REVISION    "201508071800Z"
        DESCRIPTION "V6.04,
                     Add:subbname8090DEVCR57E8NCB0(561561),   --8*100Gbps CFP2 Interface Board
                     Add:subbnamePTN990J1EM16DP1(229464),        --J1EM16D-P1,16 Channel 1 GE Optical Interface board
                     Add:subbnamePTN990J1EM16DP2(229465),        --J1EM16D-P2,16 Channel 1 GE Optical Interface board
                     Add:subbnamePTN990TPJ1EF8F(229466),        --TPJ1EF8F,8 Channel 1 GE Optical Interface board
                     Add:subbnamePTN990TPJ1EX4S(229467),        --TPJ1EX4S,4 Channel 10 GE Optical Interface board(SFP+)
                    "


        REVISION    "201507220800Z"
        DESCRIPTION "V6.03,
                     Add: fnameME60S4(159759),                  -- Quidway ME60S-X1-S4 FRAME
                     Add: fnameME60S4-DC(159760),               -- Quidway ME60S-X1-S4-DC FRAME
                     Add: fnameME60S8(159761),                  -- Quidway ME60S-X2-S8 FRAME
                     Add: fnameME60S8-DC(159762),               -- Quidway ME60S-X2-S8-DC FRAME
                     Add: fnameME60S16(159763),                 -- Quidway ME60S-X2-S16 FRAME
                     Add: fnameME60X1M4(159764),                -- Quidway ME60M-X1-M4 FRAME
                     Add: fnameME60X1M4-DC(159765),             -- Quidway ME60M-X1-M4-DC FRAME
                     Add: fnameME60X2-M8(159766),               -- Quidway ME60M-X2-M8 FRAME
                     Add: fnameME60X2-M8-DC(159767),            -- Quidway ME60M-X2-M8-DC FRAME
                     Add: fnameME60X2-M16(159768),              -- Quidway ME60M-X2-M16 FRAME

                     Add: virent8090DEVCR5D00E8NC7B(564741),    -- V8R8C00 for CR5D00E8NC7B(SBOM)
                     Add: virentME60DEVME2D00MPUE10(159762),    --for Main Processing Unit E  ME60-S
                     Add: virentME60DEVME0D00MPUK70(159763),    --for Main Processing Unit K  ME60-M

                     Add: virentME60DEVME2DSPUA0010(161581),    --for ME2DSPUA0010 Service Processor Unit(SPU-A)
                     Add: virentME60DEVME2DSPUB0010(161582),    --for ME2DSPUB0010 Service Processor Unit(SPU-B)
                     Add: virentME60DEVME0DBSU24071(161580),    --for ME0DBSU24071 Broadband Service Unit(BSU-240-A)
                     Add: fnameME60X2-M8A(161583),              -- Quidway ME60M-X2-M8A FRAME
                     Add: fnameME60X2-M8A-DC(161584),           -- Quidway ME60M-X2-M8A-DC FRAME
                     Add: fnameME60X2-M16A(161585),             -- Quidway ME60M-X2-M16A FRAME
                     Add: fnameME60S8A(161586),                 -- Quidway ME60S-X2-S8A FRAME
                     Add: fnameME60S8A-DC(161587),              -- Quidway ME60S-X2-S8A-DC FRAME
                     Add: fnameME60S16A(161588),                -- Quidway ME60S-X2-S16A FRAME
                    "

        REVISION    "201507160800Z"
        DESCRIPTION "V6.02,  recover for 5.97
                    "

        REVISION    "201507011800Z"
        DESCRIPTION "V6.01,
                     Add: fnameH831MABL-H833CCFE(561555),    --MA5878  new frame  H831MABL.
                     Add: bnameH833CCFE(156001),       -- Master board of MA5878.
                     Add: bnameHS31EIUC(156002),       -- 8 FE vitual board of MA5878.
                     Add: bnameHS31GE2A(156003),       -- 2 GE vitual board of MA5878.
                     Add: bnameHS31ASNB(156004),       -- 16-channel VoIP POTS service board of MA5878.
                     Add: bnameHS31ASLB(156005),       -- 8-channel VoIP POTS service board of MA5878.
                    "

    REVISION    "201506241800Z"
        DESCRIPTION "V6.00,
              Add: subbnameH901CKUB(148502),          -- Clock subboard of MA5800 H901MPLB
              Add: bnameH80XSDM(148012),              -- Support SuperVector board.
              Add: bnameH80XSDP(148013),              -- Support SuperVector board.
                   "

        REVISION    "201506231200Z"
        DESCRIPTION "V5.99,
                     Add: Reserve HWFrameType(147530 ~ 147539, 148511 ~ 148540) for MA5800.
                     Add: Reserve HWPCBType(148503 ~ 148510, 148600 ~ 148699, 156010 ~ 156029) for MA5800.
                     Add: Reserve HWSubPCBType(148511 ~ 148525) type for MA5800.
                    "

    --  Revision history MxUV8R16C10 add new mib
        REVISION    "201506181600Z"
        DESCRIPTION "V5.98,
          ADD: fnameAP5030DN-S(692254),           --WLAN new ap
              ADD: fnameAP9132DN(692255),             --WLAN new ap
              ADD: fnameAP3010DN-V2(692259),          --WLAN new ap
          ADD: fnameAC6005-8-RU(692260),          --WLAN new ac for russia
          ADD: fnameAC6005-8-PWR-RU(692261),      --WLAN new ac for russia
          ADD: fnameAC6605-26-PWR-RU(692262),     --WLAN new ac for russia
          ADD: fnameACU2-RU(692263),              --WLAN new ac for russia
          ADD: fnameAC6003-8(692264),             --WLAN new ac
          ADD: fnameAC6003-8-PWR(692265),         --WLAN new ac
                   "

    REVISION    "201506171600Z"
        DESCRIPTION "V5.97,
              ADD: virentPTN6900DEVTNRDSFUIU07C(229475),   -- for V800R007C00 TNRDSFUIU07C(SBOM),1Tbps Switch Fabric Unit C(SFUI-1T-C)
              ADD: virentPTN6900DEVTNRD0MPUB570(229476),   -- for V800R007C00 TNRD0MPUB570(SBOM),Main Processing Unit B5
              ADD: virentPTN6900DEVTNRDSFUIM07B(229477),   -- for V800R007C00 TNRDSFUIM07B(SBOM),480Gbps Switch Fabric Unit B(SFUI-480-B)
              ADD: virentPTN6900DEVTNRDSFUIU07B(229478),   -- for V800R007C00 TNRDSFUIU07B(SBOM),1Tbps Switch Fabric Unit B(SFUI-1T-B)
              ADD: virent8090DEVCR5D0MPUD470(561175),      -- for V800R007C00 CR5D0MPUD470(SBOM), Main Processing Unit D4
              ADD: virent600DEVCR5DLPUF507L(564804),       -- for V800R007C00 CR5DLPUF507L(SBOM),Flexible Card Line Processing Unit L(LPUF-50-L,four sub-slots)
              ADD: virent600DEVCR5D00LBXF7L(564805),       -- for V800R007C00 CR5D00LBXF7L(SBOM),12-Port 10GBase LAN/WAN-SFP+ Integrated Line Processing Unit L(LPUI-120-L)
              ADD: virent600DEVCR5D00LFXF7L(564806),       -- for V800R007C00 CR5D00LFXF7L(SBOM),24-Port 10GBase LAN/WAN-SFP+ Integrated Line Processing Unit L(LPUI-240-L)
              ADD: virent600DEVCR5D00D2NT70(564807),       -- for V800R007C00 CR5D00D2NT70(SBOM),2-Port 100GE Tunable DWDM Integrated Line Processing Unit (LPUI-200)
              ADD: virent600DEVCR5DLPUFE070(564808),       -- for V800R007C00 CR5DLPUFE070(SBOM),Flexible Card Line Processing Unit(LPUF-200)
              ADD: virent600DEVCX6D0MPUD470(564809),       -- for V800R007C00 CX6D0MPUD470(SBOM),Main Processing Unit D4
              ADD: virentME60DEVME0P0MPUD470(159758),      -- for V800R007C00 ME0P0MPUD470(SBOM), Main Processing Unit D4
              ADD: virentME60DEVME0D0SRUA970(159759),      -- for V800R007C00 ME0D0SRUA970(SBOM),Switch and Route Processing Unit A9
              ADD: virentME60DEVME0D0MPUB570(159760),      -- for V800R007C00 ME0D0MPUB570(SBOM),Main Processing Unit B5
              ADD: virentME60DEVME0D0SRUA870(159761),      -- for V800R007C00 ME0D0SRUA870(SBOM),Switch and Route Processing Unit A8
              ADD: virentME60DEVME0DSFUIU07C(160512),      -- for V800R007C00 ME0DSFUIU07C(SBOM),1Tbps Switch Fabric Unit C(SFUI-1T-C)
              ADD: virentME60DEVME0DSFUIK07B(160513),      -- for V800R007C00 ME0DSFUIK07B(SBOM),480Gbps Switch Fabric Unit(SFUI-480-B)
              ADD: virentME60DEVME0DSFUIU07B(160514),      -- for V800R007C00 ME0DSFUIU07B(SBOM),1Tbps Switch Fabric Unit B(SFUI-1T-B)
              ADD: virentME60DEVME0DSFUIK07A(160515),      -- for V800R007C00 ME0DSFUIK07A(SBOM),480Gbps Switch Fabric Unit(SFUI-480-A)
              ADD: virentPTN6900DEVTNRD0MPUD370(229405),   -- for V800R007C00 TNRD0MPUD370(SBOM),Main Processing Unit D3
              ADD: virentPTN6900DEVTNRD0MPUD470(229406),   -- for V800R007C00 TNRD0MPUD470(SBOM),Main Processing Unit D4
              ADD: virent8090DEVCR5D00EMGF74(564811),      -- for V800R007C00 CR5D00EMGF74(SBOM), 48-Port 100/1000Base-X-SFP Integrated Line Processing Unit S(LPUI-51-S)
              ADD: virent8090DEVCR5DL2XEFG73(564812),      -- for V800R007C00 CR5DL2XEFG73(SBOM), 2-Port 10GBase LAN/WAN-SFP+ + 24-Port 100/1000Base-X-SFP Integrated Line Processing Unit S(LPUI-51-S)
              ADD: virent8090DEVCX6D0MPUK170(561176),      -- for V800R007C00 CX6D0MPUK170(SBOM), Main Processing Unit K1
              ADD: virent8090DEVCR5D0MPUK170(561177),      -- for V800R007C00 CR5D0MPUK170(SBOM), Main Processing Unit K1
              ADD: virent8090DEVCR2D0MPUE110(561178),      -- for V800R007C00 CR2D0MPUE110(SBOM), Main Processing Unit K1
              ADD: virentPTN6900DEVTNUD00MPUK71(229407),   -- for V800R007C00 TNUD00MPUK71(SBOM), Main Processing Unit K1
              ADD: virent8090DEVCR2B0BKP0210(561179),      -- for V800R007C00 CR2B0BKP0210(SBOM), Integration Processing Unit
              ADD: virent8090DEVCR5B0BKP0371(561180),      -- for V800R007C00 CR5B0BKP0371(SBOM), Integration Processing Unit
              ADD: virent8090DEVCX6B0BKP0371(561181),      -- for V800R007C00 CX6B0BKP0371(SBOM), Integration Processing Unit
              ADD: virentPTN6900DEVTNRB0BKP0371(229408),   -- for V800R007C00 TNUD00MPUK71(SBOM), Integration Processing Unit
              ADD: virent8090DEVCR2B0BKP0211(561182),      -- for V800R007C00 CR2B0BKP0211(SBOM), Integration Processing Unit
              ADD: virent8090DEVCR5B0BKP0372(561183),      -- for V800R007C00 CR5B0BKP0372(SBOM), Integration Processing Unit
              ADD: virent8090DEVCX6B0BKP0372(561184),      -- for V800R007C00 CX6B0BKP0372(SBOM), Integration Processing Unit
              ADD: virentPTN6900DEVTNRB0BKP0372(229409),   -- for V800R007C00 TNRB0BKP0372(SBOM), Integration Processing Unit
              ADD: virent8090DEVCR5D00E2NC76(564813),      -- for V800R008C00 CR5D00E2NC76(SBOM), 2-Port 100GBase-CFP Integrated Line Processing Unit(LPUI-200)
              ADD: virent8090DEVCR5D00LEXF76(564814),      -- for V800R008C00 CR5D00LEXF76(SBOM), 20-Port 10GBase LAN/WAN-SFP+ Integrated Line Processing Unit(LPUI-200)
              ADD: virent8090DEVCR5DE1NLAX76(564815),      -- for V800R008C00 CR5DE1NLAX76(SBOM), 1-Port 100GBase-CFP + 10-Port 10GBase LAN/WAN-SFP+ Integrated Line Processing Unit(LPUI-200)
              ADD: virent8090DEVCR5D00E2NC75(564816),      -- for V800R008C00 CR5D00E2NC75(SBOM), 2-Port 100GBase-CFP Integrated Line Processing Unit L(LPUI-200-L)
              ADD: virent8090DEVCR5D00LEXF75(564817),      -- for V800R008C00 CR5D00LEXF75(SBOM), 20-Port 10GBase LAN/WAN-SFP+ Integrated Line Processing Unit L(LPUI-200-L)
              ADD: virent8090DEVCR5DE1NLAX75(564818),      -- for V800R008C00 CR5DE1NLAX75(SBOM), 1-Port 100GBase-CFP + 10-Port 10GBase LAN/WAN-SFP+ Integrated Line Processing Unit L(LPUI-200-L)
              ADD: virent8090DEVCR5DSRUA5E71(564819),      -- for V800R008C00 CR5DSRUA5E71(SBOM), Switch and Route Processing Unit A5E
                   "


              REVISION    "201506151600Z"
        DESCRIPTION "V5.96,
              ADD: fnameH821MABCR(561554),            --MA5633   new frame  H821MABCR
              ADD: bnameH822CCKRD(155996) ,           --MA5633   mainboard   H822CCKRD
              ADD: bnameHS33CDAF(155997) ,            --MA5633   board      HS33CDAF
              ADD: bnameHS33CDAG(155601) ,            --MA5633   board      HS33CDAG
              ADD: subbnameH822UX1A(155956) ,         --10GXPON subboard    H822UX1A
                   "


        REVISION    "201505271600Z"
        DESCRIPTION "V5.95,
              ADD: fnameAR2204-27GE(667804),      -- Quidway AR2204-27GE FRAME
              ADD: fnameAR2204-27GE-P(667805),    -- Quidway AR2204-27GE-P FRAME
              ADD: fnameAR2204-51GE-P(667806),    -- Quidway AR2204-51GE-P FRAME
              ADD: fnameAR1220C(667807),          -- Quidway AR1220C FRAME
              ADD: fnameAR1220-S2(667808),        -- Quidway AR1220-S2 FRAME
              ADD: fnameAR2240C(667809),          -- Quidway AR2240C FRAME
              ADD: fnameAR2504(667810),           -- Quidway AR2504 FRAME
              ADD: fnameAR161FV-1P(667811),       -- Quidway AR161FV-1P FRAME
              ADD: fnameAR169W-P-M9(667812),      -- Quidway AR169W-P-M9 FRAME
              ADD: fnameAR169RW-P-M9(667813),     -- Quidway AR169RW-P-M9 FRAME
              ADD: bnameAR2204-27GE(667886),             --  AR2204-27GE Main Control Unit
              ADD: bnameAR2204-27GE-P(667887),           --  AR2204-27GE-P Main Control Unit
              ADD: bnameAR2204-51GE-P(667888),           --  AR2204-51GE-P Main Control Unit
              ADD: bnameAR1220C(667889),                 --  AR1220C Main Control Unit
              ADD: bnameAR1220-S2(667890),               --  AR1220-S2 Main Control Unit
              ADD: bnameSRU40C(667891),                  --  SRU40C Main Control Unit
              ADD: bnameSRU100E(667893),                 --  SRU100E Main Control Unit
              ADD: bnameSRU200E(667894),                 --  SRU200E Main Control Unit
              ADD: bnameAR2504(667895),                  --  AR2504 Main Control Unit
              ADD: bnameAR8ES3GS(667896),                --  8ES3GS Control Unit
              ADD: bnameAR8ES3G(667897),                 --  8ES3G Control Unit
              ADD: bnameAR1LTE-LV(667898),               --  1LTE-LV Control Unit
              ADD: bnameAR24ES2GP(667899),               --  24ES2GP Control Unit
              ADD: bnameAR2X10GL(667900),                --  2X10GL Control Unit
              ADD: bnameAR161FV-1P(667901),              --  AR161FV-1P Main Control Unit
              ADD: bnameAR169W-P-M9(667902),             --  AR169W-P-M9 Main Control Unit
              ADD: bnameAR169RW-P-M9(667903),            --  AR169RW-P-M9 Main Control Unit
                    "

        REVISION    "201505211200Z"
        DESCRIPTION "V5.94,
              ADD: fnameCE6850U48S6QHI(688146),         -- CloudEngine CE6850U-48S6Q-HI Switch (24-Port 10GE SFP+,support 2/4/8G FC,2-Port 40GE QSFP+)
              ADD: fnameCE685048T6QHI(688147),          -- CloudEngine CE6850-48T6Q-HI Switch (48-Port 10GE RJ45,6-Port 40GE QSFP+)
              ADD: fnameCE681032T16S4QLI(688148),       -- CloudEngine CE6810-32T16S4Q-LI Switch (32-Port 10GE RJ45,16-Port 10GE SFP+,4-Port 40GE QSFP+ Optical)
              ADD: fnameCE585548T4S2QEI(688150),        -- CloudEngine CE5855-48T4S2Q-EI Switch (48-Port GE RJ45,4-Port SFP+,2-Port 40GE QSFP+)
              ADD: fnameCE585524T4S2QEI(688151),        -- CloudEngine CE5855-24T4S2Q-EI Switch (24-Port GE RJ45,4-Port SFP+,2-Port 40GE QSFP+)
              ADD: fnameCE6850U24S2QHI(688152),         -- CloudEngine CE6850U-24S2Q-HI Switch (24-Port 10GE SFP+,support 2/4/8G FC,2-Port 40GE QSFP+)
              ADD: fnameCE681024S2QLI(688153),          -- CloudEngine CE6810-24S2Q-LI Switch (24-Port 10GE SFP+,2-Port 40GE QSFP+)
              ADD: fnameCE685148S6QHI(688154),          -- CloudEngine CE6851-48S6Q-HI Switch (48-Port 10GE SFP+,6-Port 40GE QSFP+)
              ADD: bnameCE6850U48S6QHI(688198),             -- CloudEngine 6800-CEM48S6QP02,48-Port 10GE SFP+,support 2/4/8G FC,6-Port 40GE QSFP+ Optical Switch Control Unit,1*1
              ADD: bnameCE685048T6QHI(688199),              -- CloudEngine 6800-CEM48T6QP01,48-Port 10GE RJ45,6-Port 40GE QSFP+ Optical Switch Control Unit,1*1
              ADD: bnameCE681032T16S4QLI(688200),           -- CloudEngine 6800-CEM32T16S4QP01,32-Port 10GE RJ45,16-Port 10GE SFP+ Optical,4-Port 40GE QSFP+ Optical Switch Control Unit,1*1
              ADD: bnameCE585548T4S2QEI(688202),            -- CloudEngine 5800-CEM48T4S2QP03,48-Port GE RJ45,4-Port SFP+ Optical,2-Port 40GE QSFP+ Optical Switch Control Unit,1*1
              ADD: bnameCE585524T4S2QEI(688203),            -- CloudEngine 5800-CEM24T4S2QP03,24-Port GE RJ45,4-Port SFP+ Optical,2-Port 40GE QSFP+ Optical Switch Control Unit,1*1
              ADD: bnameCE6850U24S2QHI(688204),             -- CloudEngine 6800-CEM24S2QP02,24-Port 10GE SFP+,support 2/4/8G FC,2-Port 40GE QSFP+ Optical Switch Control Unit,1*1
              ADD: bnameCE681024S2QLI(688205),              -- CloudEngine 6800-CEM24S2QP01,24-Port 10GE SFP+,2-Port 40GE QSFP+ Optical Switch Control Unit,1*1
              ADD: bnameCE685148S6QHI(688206),              -- CloudEngine 6800-CEM48S6QP04,48-Port 10GE SFP+,6-Port 40GE QSFP+ Optical Switch Control Unit,1*1
                    "

        REVISION    "201505210000Z"
        DESCRIPTION "V5.93,
                ADD: bnameH832PDSA(155992),   --DC Power board H832PDSA of  the  MA5616.
                ADD: bnameH832PDVSA(155993),  --DC Power board H832PDVSA of  the  MA5616.
                ADD: bnameH832PDNSA(155994),  --DC Power board H832PDNSA of  the  MA5616.
                ADD: bnameH83DSDMM(155995),   --48-channel super vectoring vdsl2+ service board
                ADD: bnameH835BGUD(155998),   --Master board of MA5811S-AE08 device.
                ADD: bnameHS35BGUD(155999),   --8 G.FAST board of MA5811S-AE08  device (AC).
                ADD: bnameHS35BGUDR(156000),   --8 G.FAST board of MA5811S-AE08  device (RPOE).
                ADD: subbnameASDF(155669),    -- VOIP DSP Subboard H836ASDF
                ADD: subbnameVPS(155670),     -- SUPER VECTOR Subboard VPS
                ADD: fnameMA5811S-AE08(561553),  --Virtual frame MA5811S-AE08 of MA5811S-AE08 device
                    "

        REVISION    "201505120000Z"
        DESCRIPTION "V5.92,
                ADD: fname8031E628(536956),
                ADD: fname8031E628-X(536957),
                ADD: fname8031E652(536958),
                ADD: fname8031E652-X(536959),
                ADD: bname8031E628(537152),
                ADD: bname8031E628-X(537153),
                ADD: bname8031E652(537154),
                ADD: bname8031E652-X(537155),
                    "


        REVISION    "201504211134Z"
        DESCRIPTION "V5.91,
              ADD: fnamePTN990(229397),                       --PTN 990 Integrated DC Chassis Components
              ADD: bnamePTN990TPJD000CXP00(229408),           --TPJD000CXP00,System Control,Cross-connect and Multi-protocol Process Unit
              ADD: bnamePTN990TPJD000PIU00(229409),           --TPJD000PIU00,Power Interface Board
              ADD: bnamePTN990TPJM000FAN00(229410),           --TPJM000FAN00,Fan box
              ADD: bnamePTN990TPJD000CXP01(229411),           --TPJD000CXP01,System Control,Cross-connect and Multi-protocol Process Unit
              ADD: subbnamePTN990TPJD00EXL100(229451),        --TPJD00EXL100,1-Port 40GBase-CFP Physical Interface Card(PIC)
              ADD: subbnamePTN990TNDD00EX1S00(229452),        --TNDD00EX1S00,1 Channel 10 GE Optical Interface board(SFP+)
              ADD: subbnamePTN990TNDD00EX2S00(229453),        --TNDD00EX2S00,2 Channel 10 GE Optical Interface board(SFP+)
              ADD: subbnamePTN990TNDD00EM4T01(229454),        --TNDD00EM4T01,4 Channels GE/FE Electrical Interface Board
              ADD: subbnamePTN990TNDD00EM8T01(229455),        --TNDD00EM8T01,8 Channels GE/FE Electrical Interface Board
              ADD: subbnamePTN990TNDD00EM4F02(229456),        --TNDD00EM4F02,4 Channels GE/FE Optical Interface Board
              ADD: subbnamePTN990TNDD00EM8F02(229457),        --TNDD00EM8F02,8 Channels GE/FE Optical Interface Board
              ADD: subbnamePTN990TPJD000AUX00(229458),        --TPJD000AUX00,Auxiliary  Flexible Interface Card
              ADD: subbnamePTN990TNDD000SQ100(229459),        --TNDD000SQ100,4 Channels STM-1 Optical Interface Board
              ADD: subbnamePTN990TNDD00MD1A00(229460),        --TNDD00MD1A00,32 Channels E1 Interface Board(75ohm)
              ADD: subbnamePTN990TNDD00MD1B00(229461),        --TNDD00MD1B00,32 Channels E1 Interface Board(120ohm)
              ADD: subbnamePTN990TNDD00ML1A00(229462),        --TNDD00ML1A00,16 Channels E1 Interface Board(75ohm)
              ADD: subbnamePTN990TNDD00ML1B00(229463),        --TNDD00ML1B00,16 Channels E1 Interface Board(120ohm)  "

        REVISION    "201504171200Z"
        DESCRIPTION "V5.90,
                     ADD: subbname8090DEVCR5D00P2XX72(570030),     --2-Port OC-192c/STM-64c POS-XFP Flexible Card(P51-A)
                     ADD: subbname8090DEVCR57L4XEBGFB(570031),     --4-Port 10GBase LAN/WAN-SFP++12-Port 100/1000Base-X-SFP Integrated Integrated Service Unit B(ISUI-51-B,Supporting 1588v2)
                     ADD: subbname8090DEVCR57TBXF00(570032),         --12-Port OTU2-SFP+ Fixed Card
                     ADD: subbname8090DEVCR57T6XF00(570033),         --6-Port OTU2-SFP+ Fixed Card(P120)
                     ADD: subbname8090DEVCX6D0EFGFA12(570034),       -- CX6D0EFGFA12,24-Port 100/1000Base-X-SFP Integrated Integrated Service Unit (ISUI-21,Supporting 1588v2)
                     ADD: subbname8090DEVCX6DL1XEDG1A(570038),       -- CX6DL1XEDG1A,1-Port 10GBase LAN/WAN-SFP++16-Port 100/1000Base-X-SFP Integrated Integrated Service Unit (ISUI-21,Supporting 1588v2)
                     ADD: subbname8090DEVCR5D0EFGFA73(570039),       -- CR5D0EFGFA73,24-Port 100/1000Base-X-SFP Integrated Integrated Service Unit (ISUI-21,Supporting 1588v2)
                     ADD: subbname8090DEVCR5DL1XEDG70(570040),       -- CR5DL1XEDG70,1-Port 10GBase LAN/WAN-SFP++16-Port 100/1000Base-X-SFP Integrated Integrated Service Unit (ISUI-21,Supporting 1588v2)
                     ADD: subbname8090DEVCR53P4UF0(570043),           -- CR53P4UF0,4-Port OC-48c/STM-16c POS-SFP Flexible Card
                     ADD: subbname8090DEVCR53P2UF0(570044),           -- CR53P2UF0,2-Port OC-48c/STM-16c POS-SFP Flexible Card
                     ADD: subbname8090DEVCR53P8HF0(570045),           -- CR53P8HF0,8-Port OC-12c/STM-4c POS-SFP Flexible Card
                     ADD: subbname8090DEVCR53P1XX0(570046),           -- CR53P1XX0,1-Port OC-192c/STM-64c POS-XFP Flexible Card(Occupy two slots)
                     ADD: subbname8090DEVCR5D00L2NC63(561418),   -- Finished Board,NE5000E,CR56E2NCC2,2-Port 100GBase-CFP2 Flexible Card(CP400,Occupy 1 sub-slot)
                     ADD: subbname8090DEVCR5D00LEXF63(561419),   -- Finished Board,NE5000E,CR56LEXF2,20-Port 10GBase LAN/WAN-SFP+ Flexible Card(CP400,Occupy 1 sub-slot)
                     Modify: subbnameCR53P2CF(659455) to subbnameCR5D00P2CF70(659455), -- --2-Port OC-3c/STM-1C POS SFP Flexible Card
                     Modify: subbnameCR53P4CF(659465) to subbnameCR53P4CF0(659465),  --4-Port OC-3c/STM-1C POS SFP Flexible Card
                     Modify: subbnameCR53P8CF(659454) to subbnameCR53P8CF0(659454),  --8-Port OC-3c/STM-1c POS-SFP Flexible Card
                     Modify: subbname8090DEVCR5D00D2NT70(561549) to subbname8090DEVCR57D2NT00(561549), -- 2-Port 100GE Tunable DWDM Integrated Line Processing Unit (LPUI-200)
                     "


        REVISION    "201504111200Z"
        DESCRIPTION "V5.89,
                     Delete ifAdminStatus and ifOperStatus
                     "

        REVISION    "201504091200Z"
        DESCRIPTION "V5.88,
                     ADD: bnameH901EDSH(148536),         --  TDM service board of MA5800.
                     "

        REVISION    "201504081200Z"
        DESCRIPTION "V5.87,
                 Add: fnameMA5600H803Mabc(147529),         -- Backplane of the P300 broadband master Frame: H803MABC.
                 Add: fnameMA5600H802Mabh(147571),         -- Backplane(19 Inch) of the P300 new broadband master Frame: H802MABH
                     "

        REVISION    "201504011200Z"
        DESCRIPTION "V5.86,
       ADD fname and bname of ar121w, ar121w-s, ar161w and ar129w
                     "

        REVISION    "201503311200Z"
        DESCRIPTION "V5.85,
       ADD virent8090DEVCR5D00TBXF71(564903),    -- V8R7C10 for 12-Port OTU2-SFP+ Integrated Line Processing Unit (LPUI-120)
       ADD: virent8090DEVCR5D00TFXF71(564904),    -- V8R7C10 for 24-Port OTU2-SFP+ Integrated Line Processing Unit (LPUI-240)
                     "


    --  Revision history SwitchV2R8C00 add new mib
        REVISION    "201503301200Z"
        DESCRIPTION "V5.84,
                     ADD: fname8031S5700S-28X-LI-AC(536953),           --S5700S-28X-LI-AC           Metro Service Platform for V2R8C00
                     ADD: fname8031S5700S-52X-LI-AC(536954),           --S5700S-52X-LI-AC           Metro Service Platform for V2R8C00
                     ADD: fname8031S5700S-28P-PWR-LI-AC(536955),       --S5700S-28P-PWR-LI-AC       Metro Service Platform for V2R8C00
                     ADD: bname8031S5700S-28X-LI-AC(537149),          --S5700S-28X-LI-AC           Metro Service Platform for V2R8C00
                     ADD: bname8031S5700S-52X-LI-AC(537150),          --S5700S-52X-LI-AC           Metro Service Platform for V2R8C00
                     ADD: bname8031S5700S-28P-PWR-LI-AC(537151),      --S5700S-28P-PWR-LI-AC       Metro Service Platform for V2R8C00
                     ADD: bnameLE1D2G48VEA2(659583),      --S9300, 48-Port 10/100/1000BASE-T POE Interface Card(EA,RJ45,POE,EEE)
                     "


    --  Revision history MxUV8R16C00 add new mib
        REVISION    "201503241200Z"
        DESCRIPTION "V5.83,
                     ADD: bnameHS35BVUP(155989),               -- 16G.FAST+VECTOR board of MA5811S_BT  device.
                     ADD: bnameH835BVUP(155991),               -- Master board of MA5811S_BT device.
                     ADD: fnameMA5811S_BT_H821MABC(145957),    -- Virtual frame H821MABC of MA5811S_BT device .
                     "
    --  Revision history SwitchV2R8C00 add new mib
        REVISION    "201503231200Z"
        DESCRIPTION "V5.82,
    ADD:virent8090DEVCR5DLPUFK062(562033),   -- 400G Flexible Card Line Processing Unit B(NE5000E LPUF-400-B,2 sub-slots)
    ADD:virent8090DEVCR5D0MPUA451(562034),   -- NetEngine5000E Cluster-CR55MPUA5
    ADD:virent8090DEVCCR5D00ICUA51(562035),   -- NetEngine5000E Cluster-CR55ICUA1
    ADD:virent8090DEVCR5DSFUFK051(562036),   -- NetEngine5000E Cluster-CR55SFUF400D
    ADD:virent8090DEVCR5D00L4NC60(562037),   -- NE5000E,CR56E4NCC0,4-Port 100GBase-CFP2 Integrated Line Processing Unit (LPUI-400)
    ADD:virent8090DEVCR5D00LKXF60(562038),   -- NE5000E,CR56LKXFA0,40-Port 10GBase LAN/WAN-SFP+ Integrated Line Process Unit(NE5000E LPUI-400)
    ADD: virent8090DEVCR5DL2NLEX60(562039),   -- NE5000E,CR56E2NLEXF0,2 port 100GBase CFP2 & 20 port 10GBase LAN/WAN-SFP+ Line Processing Unit(NE5000E LPUI-400)
    ADD:virent8090DEVCCR5D0OFCK051(561415),   -- NetEngine5000E Cluster-CR55OFC400D-400G
  "


    --  Revision history SwitchV2R8C00 add new mib
        REVISION    "201503111200Z"
        DESCRIPTION "V5.81,
                     ADD: fname8031S5720S-28P-SI-AC(536922),           --S5720S-28P-SI-AC           Metro Service Platform for V2R8C00
                     ADD: fname8031S5321-28P-SI-AC(536923),            --S5321-28P-SI-AC            Metro Service Platform for V2R8C00
                     ADD: fname8031S5720S-28X-SI-AC(536924),           --S5720S-28X-SI-AC           Metro Service Platform for V2R8C00
                     ADD: fname8031S5321-28X-SI-AC(536925),            --S5321-28X-SI-AC            Metro Service Platform for V2R8C00
                     ADD: fname8031S5321-28X-SI-DC(536926),            --S5321-28X-SI-DC            Metro Service Platform for V2R8C00
                     ADD: fname8031S5720S-52P-SI-AC(536927),           --S5720S-52P-SI-AC           Metro Service Platform for V2R8C00
                     ADD: fname8031S5321-52P-SI-AC(536928),            --S5321-52P-SI-AC            Metro Service Platform for V2R8C00
                     ADD: fname8031S5720S-52X-SI-AC(536929),           --S5720S-52X-SI-AC           Metro Service Platform for V2R8C00
                     ADD: fname8031S5321-52X-SI-AC(536930),            --S5321-52X-SI-AC            Metro Service Platform for V2R8C00
                     ADD: fname8031S5321-52X-SI-DC(536931),            --S5321-52X-SI-DC            Metro Service Platform for V2R8C00
                     ADD: fname8031S5720-28P-SI-AC(536932),            --S5720-28P-SI-AC            Metro Service Platform for V2R8C00
                     ADD: fname8031S5320-28P-SI-AC(536933),            --S5320-28P-SI-AC            Metro Service Platform for V2R8C00
                     ADD: fname8031S5720-28X-SI-AC(536934),            --S5720-28X-SI-AC            Metro Service Platform for V2R8C00
                     ADD: fname8031S5320-28X-SI-AC(536935),            --S5320-28X-SI-AC            Metro Service Platform for V2R8C00
                     ADD: fname8031S5720-52P-SI-AC(536936),            --S5720-52P-SI-AC            Metro Service Platform for V2R8C00
                     ADD: fname8031S5320-52P-SI-AC(536937),            --S5320-52P-SI-AC            Metro Service Platform for V2R8C00
                     ADD: fname8031S5720-52X-SI-AC(536938),            --S5720-52X-SI-AC            Metro Service Platform for V2R8C00
                     ADD: fname8031S5320-52X-SI-AC(536939),            --S5320-52X-SI-AC            Metro Service Platform for V2R8C00
                     ADD: fname8031S5720-28X-PWR-SI-AC(536940),        --S5720-28X-PWR-SI-AC        Metro Service Platform for V2R8C00
                     ADD: fname8031S5320-28X-PWR-SI-AC(536941),        --S5320-28X-PWR-SI-AC        Metro Service Platform for V2R8C00
                     ADD: fname8031S5720-52X-PWR-SI-AC(536942),        --S5720-52X-PWR-SI-AC        Metro Service Platform for V2R8C00
                     ADD: fname8031S5720-52X-PWR-SI-ACF(536943),       --S5720-52X-PWR-SI-ACF       Metro Service Platform for V2R8C00
                     ADD: fname8031S5320-52X-PWR-SI-AC(536944),        --S5320-52X-PWR-SI-AC        Metro Service Platform for V2R8C00
                     ADD: fname8031S5710-28X-LI-AC(536945),            --S5710-28X-LI-AC            Metro Service Platform for V2R8C00
                     ADD: fname8031S5710-52X-LI-AC(536946),            --S5710-52X-LI-AC            Metro Service Platform for V2R8C00
                     ADD: fname8031S6720-30C-EI-24S-AC(536947),        --S6720-30C-EI-24S-AC        Metro Service Platform for V2R8C00
                     ADD: fname8031S6320-30C-EI-24S-AC(536948),        --S6320-30C-EI-24S-AC        Metro Service Platform for V2R8C00
                     ADD: fname8031S6320-30C-EI-24S-DC(536949),        --S6320-30C-EI-24S-DC        Metro Service Platform for V2R8C00
                     ADD: fname8031S6720-54C-EI-48S-AC(536950),        --S6720-54C-EI-48S-AC        Metro Service Platform for V2R8C00
                     ADD: fname8031S6320-54C-EI-48S-AC(536951),        --S6320-54C-EI-48S-AC        Metro Service Platform for V2R8C00
                     ADD: fname8031S6320-54C-EI-48S-DC(536952),        --S6320-54C-EI-48S-DC        Metro Service Platform for V2R8C00

                     "

    --  Revision history WLANV2R5C30 add new mib
        REVISION    "201503091200Z"
        DESCRIPTION "V5.80,
                     ADD: bnameAP9131DN(692253),               -- WLAN FATAP board.
                     DEL: bnameAP7110SN(692236),               -- WLAN not supported finally.
                     "

    --  Revision history MxUV8R16C00 add new mib
        REVISION    "201502091200Z"
        DESCRIPTION "V5.79,
                     ADD: bnameHS21GE4B(148535),               -- 4GE baoard for MA5694_4VD device.
                     ADD: bnameH821AVIC(148534),               -- Master board of MA5694_4VD device.
                     ADD: fnameMA5694-4VD-H821MABC(145956),    -- Virtual frame H821MABC of MA5694_4VD device .
                     "

    --  Revision history MxUV8R16C00 add new mib
        REVISION    "201502031200Z"
        DESCRIPTION "V5.78,
                     ADD: bnameMA5612ASL(155990),         -- 8-channel VoIP POTS service board of MA5612.
                     ADD: fnameMA5694SDCH821MABC(561552),  -- Virtual frame H821MABC of MA5694S  PON DOCK  DC device.
                    "
    --  Revision history 8090V8R7C10 8090V600R009C00 add new mib
        REVISION    "201502021200Z"
        DESCRIPTION "V5.77,
                Modify: subbname8090DEVCR5D00L4XF71(561545) to subbname8090DEVCR5D00L4XF72(561545), -- CX68L4XFD, 4-Port 10GBase LAN/WAN-SFP+ Physical Interface Card(PIC)
                Delete: subbname8090DEVCR5DL1XE8G70(561503), -- CX68L1XE8GF, 1-Port 10GBase LAN/WAN-SFP+  8-Port 100/1000Base-X-SFP Physical Interface Card(PIC)
                    "
        --  Revision history FW V5R1C00 modify confilict mib
        REVISION    "201501311708Z"
        DESCRIPTION "V5.76,
         [bnameLE1D2FW00S01(659577), bnameLE1D2FW00S01(16719992)],
         [bnameET1D2IPS0S00(700449), bnameET1D2IPS0S00(16719988)],
         [bnameET1D2FW00S02(700452), bnameET1D2FW00S02(16719991)],
         [bnameET1D2FW00S00(700450), bnameET1D2FW00S00(16719989)],
         [bnameET1D2FW00S01(700451), bnameET1D2FW00S01(16719990)],
         delete
                bnameUSG9100SU61SPUA(16748552),     -- Service Processing Board,with HS General Security Platform Software
                bnameUSG9100SU61E8GF(16748553),     -- 8-port GE Optical Interface Card(SFP),with HS General Security Platform Software
                bnameUSG9100SU61P4UF(16748554),     -- 4-port 2.5G POS Optical Interface Card (SFP),with HS General Security Platform Software
                bnameUSG9100SU61E1XX(16748555),     -- 1-port 10G LAN XFP Optical Interface Board,with HS General Security Platform Software
                bnameUSG9100SU61W1XX(16748556),     -- 1-port 10G WAN XFP Optical Interface Board,with HS General Security Platform Software
                bnameUSG9100SU61P1XX(16748557),     -- 1-port 10G POS XFP Optical Interface Board,with HS General Security Platform Software
                bnameUSG9100SU61MSU01(16748558),    -- ATCA Main Processing & Switching Unit,with HS General Security Platform Software
                bnameUSG9100SU61SMMD02(16748559),   -- Shelf Management Module,with HS General Security Platform Software
                bnameUSG9100SU6Z1ATCA(16748560),    -- Integrated Chassis Components-5U
                bnameUSG9100SU6Z2ATCA(16748561),    -- Integrated Chassis Components-14U
                bnameUSG9100CN6E01FFB(16748562),    -- CGA Integrated Frame Fan Box
                bnameUSG9100CN6E02FFB(16748563),    -- 5U Integrated Frame Fan Box
         "
         --  Revision history 8090V8R7C10 8090V600R009C00 add new mib
        REVISION    "201501291200Z"
        DESCRIPTION "V5.75,
                     ADD: subbname8090DEVDVSU2(561425),     -- For V6R9C00 16G DVSU Card(VSUF160)
                     ADD: virent8090DEVVSUI160(564810),     -- for V600R009C00 CR5DVSUID010(SBOM), Integrated Versatile Service Unit(VSUI-160-E)
                     ADD: virentME60DEVVSUI160(161579),     -- for V600R009C00 ME0DVSUID070(SBOM),Integrated Versatile Service Unit(VSUI-160-E)
                     Add: subbname8090DEVME2D00E8GE12(570001),    -- ME2D00E8GE12, 8-Port 100/1000Base-RJ45 Physical Interface Card
                     Add: subbname8090DEVME2D00EAGF10(570002),    -- ME2D00EAGF10, 10-Port 100/1000Base-X-SFP Physical Interface Card
                     Add: subbname8090DEVME2D00L4XF11(570003),    -- ME2D00L4XF11, 4-Port 10GBase LAN/WAN-SFP+ Physical Interface Card
                     Add: subbname8090DEVME2DL1XE8G11(570004),    -- ME2DL1XE8G11, 1-Port 10GBase LAN/WAN-SFP+ + 8-Port 100/1000Base-X-SFP Physical Interface Card
                     Add: subbname8090DEVME2D00L2XF12(570005),    -- ME2D00L2XF12, 2-Port 10GBase LAN/WAN-SFP+ Physical Interface Card
                     Add: subbname8090DEVCR2D00C1CF11(570006),    -- CR2D00C1CF11, 1-Port Channelized STM-1c POS-SFP Physical Interface Card
                     Add: subbname8090DEVME0D00E8GE71(570007),    -- 8-Port 100/1000Base-RJ45 Physical Interface Card(PIC)
                     Add: subbname8090DEVME0D00EAGF70(570008),    -- 10-Port 100/1000Base-X-SFP  Physical Interface Card(PIC)
                     Add: subbname8090DEVME0D00L4XF72(570009),    -- 4-Port 10GBase LAN/WAN-SFP+  Physical Interface Card(PIC)
                     Add: subbname8090DEVME0DL1XE8G71(570010),    -- 1-Port 10GBase LAN/WAN-SFP+ + 8-Port 100/1000Base-X-SFP Physical Interface Card(PIC)
                     Add: subbname8090DEVME0D00L2XF71(570011),    -- 2-Port 10GBase LAN/WAN-SFP+  Physical Interface Card(PIC)
                     Add: subbname8090DEVME0D00L4XF70(570012),    -- 4-Port 10GBase LAN-SFP+  Physical Interface Card(PIC)
                     Add: subbname8090DEVME0DL1XE8G70(570013),    -- 1-Port 10GBase LAN/WAN-SFP+ + 8-Port 100/1000Base-X-SFP Physical Interface Card(PIC)
                     Add: subbname8090DEVME0D00L2XF70(570014),    -- 2-Port 10GBase LAN/WAN-SFP+  Physical Interface Card(PIC)
                     Add: subbname8090DEVME0D00E8GF71(570015),    -- 8-Port 100/1000Base-X-SFP  Physical Interface Card(PIC)
                     Add: subbname8090DEVME0D00E8GE70(570016),    -- 8-Port 100/1000Base-RJ45 Physical Interface Card(PIC)
                     Add: subbname8090DEVME0D00C4CF71(570017),    -- 4-Port Channelized STM-1c POS-SFP  Physical Interface Card(PIC)
                     Add: subbname8090DEVME0D000IE170(570018),    -- 32-Port E1 Physical Interface Card(PIC,75ohm)
                     Add: subbname8090DEVME0D000IE171(570019),    -- 32-Port E1 Physical Interface Card(PIC,120ohm)
                     Add: subbname8090DEVME0D000DE170(570020),    -- 16-Port E1 Physical Interface Card(PIC,75ohm)
                     Add: subbname8090DEVME0D000DE171(570021),    -- 16-Port E1 Physical Interface Card(PIC,120ohm)
                     Add: subbname8090DEVME0D00P4CF70(570022),    -- 4-Port OC-3c/STM-1c POS-SFP Flexible Interface Card(FIC)
                     Add: subbname8090DEVME0DP2C1HF70(570023),    -- 2-Port OC-3c/STM-1c (or 1-Port OC-12c/STM-4C) POS-SFP  Physical Interface Card(PIC)
                     Add: subbname8090DEVME0D00AUXQ10(570024),    -- Auxiliary  Flexible Interface Card with 4-Port 100Base-RJ45 (FIC,Supporting 1588v2)
                     Add: subbname8090DEVME0D08CWDM70(570025),    -- 8-Channel CWDM Multiplexing & Demultiplexing (1471/1491/1511/1531/1551/1571/1591/1611nm) Physical Interface Card(PIC)
                     Add: subbname8090DEVME0D00C4T370(570026),    -- 4-Port Clear Channel E3/Channelized T3 Physical Interface Card (PIC)
                     Add: subbname8090DEVME0D0L2XFH71(570027),    -- 2-Port 10GBase LAN/WAN-SFP+  Physical Interface Card H (PIC-H)
                     Add: subbname8090DEVME0D0EAGFH70(570028),    -- 10-Port 100/1000Base-X-SFP  Physical Interface Card H (PIC-H)
                     Delete: subbname8090DEVCX6D00EAGF10(536755),    -- CX68EAGFD, 10-Port 100/1000Base-X-SFP Service Interface Card(SIC)
                     Delete: subbname8090DEVCX6DL1XE8G11(536756),    -- CX68L1XE8GFB, 1-Port 10GBase LAN/WAN-SFP+ + 8-Port 100/1000Base-X-SFP Service Interface Card(SIC)
                     Delete: subbname8090DEVCX6D00E8GE11(536757),    -- CX68E8GED, 8-Port 100/1000Base-RJ45 Service Interface Card(SIC)
                     Delete: subbname8090DEVCX6D00L4XF11(536758),    -- CX68L4XFD, 4-Port 10GBase LAN/WAN-SFP+ Service Interface Card(SIC)
                     Delete: subbname8090DEVCX6D00L2XF11(536759),    -- CX68L2XFC, 2-Port 10GBase LAN/WAN-SFP+ Service Interface Card(SIC)
             "
        REVISION    "201501291200Z"
        DESCRIPTION "V5.74,
                     Delete the conflict emu on node HWFrameType,HWPCBType and HWSubPCBType ,
                     Modify the bnameH82BCVMM(155825) to bnameH82BCVMMMA5662(155825)
                     "
     --  Revision history CCU add new mib
        REVISION    "201501281200Z"
        DESCRIPTION "V5.73,

                     ADD: fnameCCU(16719872),                 --CCU Frame
                     ADD: bnameCCUMAIN(16752640),             -- CCU main board
                     ADD: bnameUEU(16752641),                 -- UEU board
                     ADD: bnameEEU(16752642),                 -- EEU board
                     ADD: bnameAIU(16752643),                 -- AIU board
                     "

         --  Revision history PTNV100R007C00 add new mib
        REVISION    "201501271200Z"
        DESCRIPTION "V5.72,
                     Mod: virentPTN7900VPICTPA1EX12(229474),   --VPICTPA1EX12,12ch 10 Gigabit Ethernet Switching Processing Board-1*1   renew enum
                    "

         --  Revision history MxUV8R16C00 add new mib
        REVISION    "201501211200Z"
        DESCRIPTION "V5.71,
                     Add: fnameMA5633H821MABCP(561550),        --Virtual frame H821MABCP of horizontal MA5633(sd5130) device.
                     Add: fnameMA5633H821MABCQ(561551),        --Virtual frame H821MABCQ of vertical MA5633(sd5130) device.
                     Add: bnameHS33CDAE(155986),               --DOCSIS virtual service board of MA5633.
                     "

         --  Revision history CloudEngine add new fname
        REVISION    "201501101200Z"
        DESCRIPTION "V5.70,
                  Add: fnameSVFLEAF(688145),                -- CloudEngine Svf Leaf Frame
                  "

         --  Revision history MxUV800R016C00 add new mib
        REVISION    "201412291200Z"
        DESCRIPTION "V5.69,
                  Add: fnameMA5621ASH831Mabc(145955),   -- Virtual frame H831MABC of MA5621A(SD5132) device
                  Modify: bnameH821CCICM(148533) to bnameH821BVIC(148533)   -- Master board of MA5694_8VD device.
                  Delete: subbnameH821BVCM(155956)    -- Virtual  BVCM subboard of MA5694_8VD,
                  "

         --  Revision history 8090V8R7C10 add new mib
        REVISION    "201412231200Z"
        DESCRIPTION "V5.68,
                    Add: subbname8090DEVCR5D00T4XF70(564522),   -- CR5D00T4XF70, 4-Port OTU2-SFP+ Physical Interface Card(PIC)
                    Add: subbname8090DEVCR2D00T4XF70(564524),   -- CR2D00T4XF70, 4-Port OTU2-SFP+ Physical Interface Card(PIC)
                    Add: subbname8090DEVCR5D00E1MF70(564523),   -- CR5D00E1MF70, 1-Port 40GBase-CFP Physical Interface Card(PIC)
                    Add: subbname8090DEVCR2D00E1MF70(564525),   -- CR2D00E1MF70, 1-Port 40GBase-CFP Physical Interface Card(PIC)
                    Add: subbnameCR53P8CF(659454),  --8-Port OC-3c/STM-1c POS-SFP Flexible Card
                    Add: subbnameCR53P2CF(659455),  --2-Port OC-3c/STM-1C POS SFP Flexible Card
                    Add: subbname8090DEVCR5M0E8GFA30(561555),   --8-Port 100/1000Base-X-SFP Flexible Card A(P10-A,Supporting 1588v2)
                    Add: subbname8090DEVCR5D00C2CF70(564526),   --4-Port Channelized OC-3c/STM-1c POS-SFP Flexible Card
                    Add: subbname8090DEVCR5D00LAXF70(561548), -- 10-Port 10GBase LAN/WAN-SFP+ Flexible Card A(P240-A)
                    Add: subbname8090DEVCR5D00D2NT70(561549), -- 2-Port 100GE Tunable DWDM Integrated Line Processing Unit (LPUI-200)
                    Add: subbname8090DEVCX6D00EAGF10(561556),   -- CX68EAGFD, 10-Port 100/1000Base-X-SFP Service Interface Card(SIC)
                    Add: subbname8090DEVCX6DL1XE8G11(561557),   -- CX68L1XE8GFB, 1-Port 10GBase LAN/WAN-SFP+ + 8-Port 100/1000Base-X-SFP                                                                                                                                                                                                                                                                                                                                                                                                     Service Interface Card(SIC)
                    Add: subbname8090DEVCX6D00E8GE11(561558),   -- CX68E8GED, 8-Port 100/1000Base-RJ45 Service Interface Card(SIC)
                    Add: subbname8090DEVCX6D00L4XF11(561559),   -- CX68L4XFD, 4-Port 10GBase LAN/WAN-SFP+ Service Interface Card(SIC)
                    Add: subbname8090DEVCX6D00L2XF11(561560),   -- CX68L2XFC, 2-Port 10GBase LAN/WAN-SFP+ Service Interface Card(SIC)
                     "


         --  Revision history PTNV100R007C00 add new mib
        REVISION    "201412191200Z"
        DESCRIPTION "V5.67,
                     Add: fnamePTN7900TPC1AFBTBKP00A(229396),   --PTN 7900-12 Integrated Chassis Components
                     Add: bnamePTN7900TPA2XCS(229403),    --TPA2XCS,Switch Fabric Unit,1*1
                     Add: bnamePTN7900TPB2XCS(229404),    --TPB2XCS,Switch Fabric Unit,1*1
                     Add: bnamePTN7900TPC1XCS(229405),    --TPC1XCS,Switch Fabric Unit,1*1
                     Add: bnamePTN7900TPB2CXP(229406),    --TPB2CXP,System Control Communication and Switch Fabric Process Unit,1*1
                     Add: bnamePTN7900TPC1CXP(229407),    --TPC1CXP,System Control Communication and Switch Fabric Process Unit,1*1
                     Add: virentPTN7900TPB2VXCS(229472),      --TPB2VXCS, Switch Fabric Unit Board,1*1
                     Add: virentPTN7900TPC1VXCS(229473),      --TPC1VXCS, Switch Fabric Unit Board,1*1
                    "

         --  Revision history MxUV800R016C00 add new mib
        REVISION    "201412081200Z"
        DESCRIPTION "V5.66,
                     Modify: bnameH821BVCM(148532) to subbnameH821BVCM(155956) -- Virtual  BVCM subboard of MA5694_8VD,
                     Add: bnameH831ASLB(155985),        -- 8 POTS Vitual Board of MA5612
                     Add: bnameHS22COME(155987),        -- 4-channel Serial Board of MA5621A, RS485 mode only
                     Add: bnameH832CCIQ(155988),        -- Master board of MA5621A(SD5132) Box type device
                    "

         --  Revision history V800R007C00 add new mib
        REVISION    "201412041200Z"
        DESCRIPTION "V5.65,
                    Add: fname8031CX600-X3A(536921),           -- Quidway CX600-3A Carrier Switch.
                    Add: fname8090NE40E-X3A(562034),          -- Quidwy Ne40E-3A FRAME.
                    Add: fnameME60-X3A(159758),              -- Quidway ME60-X3A FRAME.
                    Add: fnamePTN6900-3A(229395),             --Integrated Chassis Components (PTN 6900-3A).
            Add: fname8031CX600-X3ADO(536921),           -- Quidway CX600-3ADO Carrier Switch.
                     "

         --  Revision history ATNV200R005C00 add new mib
        REVISION    "201412031200Z"
        DESCRIPTION "V5.64,
                    Add: NE08E/05E fname from 704512 to 704522
                    Add: NE08E/05E card from 704512 to 704545
                    Add: NE08E/05E bname from 704512 to 704523

                    Add: fnameETN500 708608/708609/708610
                    Add: subnameETN 708608/708609/708610
                    Add: virentETN708608/708609/708610

                    Add: ATN fname/card/bname. "


         --  Revision history MA5600V8R16C00 add new mib
        REVISION    "201412011200Z"
        DESCRIPTION "V5.63,
                     Add: bnameH809EPBD(146147),        --  8EPON board.
                     Add: bnameH801TOPB(146148),        --  TDM interface board of the MA5600.
                     Add: bnameH80DCCPE(146149),        --  64-channel POTS(combo) + Vectoring board of MA5600T device.
                     "

         --  Revision history MxUV800R016C00 add new mib
        REVISION    "201411271200Z"
        DESCRIPTION "V5.62,
                      Add: fnameMA5694-8VD-H821MABC(145954),      -- Virtual frame of the MA5694-8VD-H821MABC.
                      Add: bnameH821BVCM(148532),       -- Virtual H821BVCM board.
                      Add: bnameH821CCICM(148533),      -- Master board of MA5694_8VD device.
                      Add: gfast-port(807),             -- G.FAST PORT.
                     "

         --  Revision history MA5800V1R16C00 add new mib
        REVISION    "201411251200Z"
        DESCRIPTION "V5.61,
                 Add: virent8090DEVCR5DSFUIK06C(564902),     -- V8R7C10 for CR5DSFUIK06C(SBOM), X16 400G Cluster
             "

         --  Revision history MA5800V1R16C00 add new mib
        REVISION    "201411201200Z"
        DESCRIPTION "V5.60,
                     Add: fnameMA5800H901BPMB(148502),   -- Backplane of the MA5800
                     Add: bnameH901GPSF(148529),         --  16*GPON board of MA5800
                     Add: bnameH901EPHF(148530),         --  16*EPON board of MA5800
                     Add: bnameH901XEHD(148531),         --  8*10G EPON board of MA5800
                     "

        --  Revision history RPS add new mib
        REVISION    "201411141200Z"
        DESCRIPTION "V5.58,
                      Modify:fnameCPF104 to fnameRPF106.
                      Modify:bnameCPF318Power to bnameCPF318-EN11PDBE.
                      Modify:bnameRCM08 to bnameRPR008S-B.
                      Modify:bnameETP4890A2-Power(786642) to bnameETP4890A2-Power(786643).
              Modify:bnameCFS01 to CFS01Monitor.
                      Delete:bnameCFS01Power(786652).
              "

        --  Revision history MxUV800R016C00 add new mib
        REVISION    "201411051200Z"
        DESCRIPTION "V5.57,
              Add:subbname8090DEVBGWD0L5XFE70(561438),   -- 5-Port 10GBase LAN/WAN-SFP+ Flexible Card(BP100)
              Add:subbname8090DEVBGWD0LAXFE70(561439),   -- 10-Port 10GBase LAN/WAN-SFP+ Flexible Card(BP200)
              Add:subbname8090DEVME0D0LAXFH7H(561440),   -- 10-Port 10GBase LAN/WAN-SFP+ Flexible Card H(BP240-H)
              "

        --  Revision history MxUV800R016C00 add new mib
        REVISION    "201410221200Z"
        DESCRIPTION "V5.56,
                      Add: MA5811SH821MABC(145953),      -- Virtual frame H821MABC of MA5811S device.
                      Add: bnameHS35FDEM(155968),       -- 16G.FAST+VECTOR board of MA5811S FTTS device.
                      Add: bnameH835FDEM(155969),       -- Master board of MA5811S-DE16 FTTS device.
                      "


        --  Revision history RPS add new mib
        REVISION    "201410201200Z"
        DESCRIPTION "V5.55,
                     Add: fnameCPF104(786434),             --The RPS's with BT-C Power Frame backplane.
                     Add: fnameCFS02(786435),              --The RPS's with BT-C Fan Frame.
                     Add: fnameETP4830-A1(786436),         --The RPS's with AC-DC System Frame.
                     Add: fnameETP4890-A2(786437),         --The RPS's with AC-DC System Frame.
                     Add: fnameETP48150-A3(786438),        --The RPS's with AC-DC System Frame.
                     Add: fnameCPF104(786439),             --The RPS's with RTF-V Power Frame backplane.


                     Add: bnameCPF104Power(786637),        --BT-C Power input module board,with 0 port
                     Add: bnameCCM08B(786638),             --BT-C Up converter module board,with 8 DC output ports
                     Add: bnameRCM08(786639),              --BT-C Down converter module board,with 12 DC input ports
                     Add: bnameCFS02Power(786640),         --BT-C Power input module board,with 0 port
                     Add: bnameCFS02Monitor(786641),       --BT-C Fan module board,with 3 fan ports
                     Add: bnameETP4830-A1Power(786642),    --BT-C AC-DC System monitor input module board,with 0 port
                     Add: bnameETP4890-A2Power(786642),    --BT-C AC-DC System monitor input module board,with 0 port
                     Add: bnameETP48150-A3Power(786644),   --BT-C AC-DC System monitor input module board,with 0 port
                     Add: bnameSMU01B(786645),             --AC-DC System monitor Monitoring module board
                     Add: bnameSMU01C(786657),             --AC-DC System monitor Monitoring module board
                     Add: bnameR4830G1(786646),            --AC-DC System Power Supply Unit
                     Add: bnameR4830N2(786647),            --AC-DC System Power Supply Unit
                     Add: bnameR4815G1(786648),            --AC-DC System Power Supply Unit
                     Add: bnameR4815N1(786649),            --AC-DC System Power Supply Unit
                     Add: bnameCFS01Power(786650),         --RTF-C Power input module board,with 0 port
                     Add: bnameCVM02(786651),              --RTF-V Up converter module board,with 8 DC output ports
                     Add: bnameCFS01Power(786652),         --RTF-V Power input module board,with 0 port
                     Add: bnameRPF106Power(786653),        --RTF-V Power input module board,with 0 port
                     Add: bnameRMU01(786654),              --RTF-V Monitoring module board,with 0 port
                     Add: bnameRFS01(786655),              --RTF-V Fan module board,with 3 fan ports
                     Add: bnameRVM04(786656),              --RTF-V Down converter module board,with 12 DC input ports
                     "

         --  Revision history DC add new mib
        REVISION    "201410161200Z"
        DESCRIPTION "V5.54,
                     Add: fnameCE681048S4QLI(688140),          -- CloudEngine CE6810-48S4Q-LI Switch (48-Port 10GE SFP+,4-Port 40GE QSFP+)
                     Add: fnameCE681048SLI(688141),            -- CloudEngine CE6810-48S-LI Switch (48-Port 10GE SFP+)
                     Add: fnameCE12804S(688142),               -- CloudEngine 12800S,CE01PBK04AS,CE12804S Power Backplane,1*1
                     Add: fnameCE12808S(688143),               -- CloudEngine 12800S,CE01BAK08AS,CE12808S Backplane A,1*1
                     Add: fnameCE685048S6QHI(688144)           -- CloudEngine CE6850-48S6Q-HI Switch (48-Port 10GE SFP+,6-Port 40GE QSFP+)
                     Add: bnameCEL48GTEF(688187),              -- Manufactured Board,iCE,CE-L48GT-EF,48-Port 10/100/1000BASE-T Interface Card(EF,RJ45)-1*1
                     Add: bnameCE685048S6QHI(688189),          -- CloudEngine 6800,CE6850-48S6Q-HI Switch(48-Port 10GE SFP+,6-Port 40GE QSFP+)
                     Add: bnameCEMPUAS(688190),                -- Manufactured Board,CloudEngine 12800S,CE-MPUA-S
                     Add: bnameCEL48XTEC(688191),              -- Manufactured Board,CloudEngine 12800,CE-L48XT-EC,1*1
                     Add: bnameCEL12CFEG(688192),              -- Manufactured Board,CloudEngine 12800,CE-L12CF-EG,12-Port-100GE Interface Card(EG,CFP2),1*1
                     Add: bnameCEFWA(688193),                  -- Manufactured Board,CloudEngine 12800,CE-FWA,Fire Wall Card A,1*1
                     Add: bnameCEL08CCEC(688194),              -- Manufactured Board,CloudEngine 12800,CE-L08CC-EC,1*1
                     Add: bnameCEL24LQEC1(688195),             -- Manufactured Board,CE-L24LQ-EC1
                     Add: bnameCESFUBS(688196),                -- Manufactured Board,CloudEngine 12800S,CE-SFUB-S
                     Add: bnameCESFUCS(688197),                -- Manufactured Board,CloudEngine 12800S,CE-SFUC-S,CE-SFUC-S,1*1
                     Add: addentnameCMU(688128),               -- CMU  Module
             "
        --  Revision history MxUV8R15C00 add new mib
        REVISION    "201408301200Z"
        DESCRIPTION "V5.50,
        add by dinglingfeng 20140630
                Add:  bnameE8000EKW51ESPU(16748544),        --SPU Board ,Service Processing Unit
                Add:  bnameE8000EDCU(16748545),         --DCU Board ,Detection and Clean Unit
                Add:  bnameE8000ESUP3SPUA02(16748546),          --Service Processing Unit,with HS General Security Platform Software
                Add:  bnameE8000ECR52LPUKD1(16748547),     --Flexible Card Line Processing Unit(LPUF-21,2 sub-slots) B
                Add:  bnameE8000ESUP3SPUA02IPS(16748548),  --IPS Service Processing Unit,with HS General Security Platform Software
                Add:  bnameE8000EKW51ESPUIPS(16748549),      --IPS SPU Board ,Service Processing Unit
        Add:  bnameE8000ESU91SPUC(16748550),      --Eudemon8000E-X,SU91SPUC,X3 Service Processiong Unit(Base Board),with HS General Security Platform Software
        Add:  bnameE8000ESU91SPUD(16748551),      --Eudemon8000E-X,SU91SPUD,X8&X16 Service Processiong Unit(Base Board),with HS General Security Platform Software
                Add:  bnameE8000ESU91SPUC01(16748552),    --Eudemon8000E-X,SU91SPUC01,40G X3 Firewall Service Processing Unit ,with HW General Security Platform Software,include SPUC and 1*SPCC01
        Add:  bnameE8000ESU91SPUC02(16748553),    --Eudemon8000E-X,SU91SPUC02,20G X3 Firewall Service Processing Unit(oversea),with HW General Security Platform Software,include SPUC and 1*SPCB02
        Add:  bnameE8000ESU91SPUC03(16748554),    --Eudemon8000E-X,SU91SPUC03,60G X3 Firewall Service Processing Unit ,with HW General Security Platform Software
        Add:  bnameE8000ESU91SPUD01(16748555),    --Eudemon8000E-X,SU91SPUD01,40G X8&X16 Firewall Service Processing Unit ,with HW General Security Platform Software,include SPUD and  1*SPCC01
        Add:  bnameE8000ESU91SPUD02(16748556),    --Eudemon8000E-X,SU91SPUD02,80G X8&X16 Firewall Service Processiong Unit,with HW General Security Platform Software,include SPUD and 1*SPCB01
        Add:  bnameE8000ESU91SPUD03(16748557),    --Eudemon8000E-X,SU91SPUD03,20G X8&X16 Firewall Service Processing Unit(oversea),with HW General Security Platform Software,include SPUD and 1*SPCB02
                Add:  bnameE8000ESU91SPUC04(16748570),    --Eudemon8000E-X,SU91SPUC04,40G X3 Firewall Service Processing Unit ,Double CPUs,with HW General Security Platform Software,include SPUC and 1*SPCB04
                Add:  bnameE8000ESU91SPUD05(16748571),    --Eudemon8000E-X,SU91SPUD05,40G X8&X16 Firewall Service Processing Unit ,Double CPUs,with HW General Security Platform Software,include SPUD and  1*SPCB04
                Add:  bnameE8000ESU91LPUF100CA00(16748572), --Eudemon8000E-X,SU91LPUF100CA00,Flexible Card Line Processing Unit(LPUF-101,4 sub-slots),with HW General Security Platform Software
                Add:  bnameE8000ESU91LPUF100CA0(16748573),  --Eudemon8000E-X3,SU91LPUF100CA01,X3 Flexible Card Line Processing Unit(LPUF-100,4 sub-slots),with HW General Security Platform Software
                Add:  bnameE8000ESU91LPUI100CA00(16748574), --Eudemon8000E-X,SU91LPUI100CA00,10-Port 10GBase LAN/WAN-SFP+ Integrated Line Processing Unit (LPUI-100) ,with HW General Security Platform Software
                Add:  bnameE8000ESU91E1NC00(16748575),  --Eudemon8000E-X,SU91E1NC00,1-Port 100GBase-CFP Integrated Line Processing Unit (LPUI-101),with HW General Security Platform Software
                Add:  bnameEudemon8000ESU91EDXFB0(16748576),    --Eudemon8000E-X,SU91EDXFB0,16-Port 10GBase LAN-SFP+ Integrated Line Processing Unit (LPUI-100) ,with HW General Security Platform Software
                Add:  bnameEudemon8000ESU91E4XFA0(16748577),    --Eudemon8000E-X,SU91E4XFA0,4-Port 10GBase LAN-SFP+ Flexible Card(P100,1/4wide,Occupy one sub-slots)
                Add:  bnameEudemon8000ESU91LBXF0(16748578), --Eudemon8000E-X,SU91LBXF0,12-Port 10G Base LAN/WAN-SFP+ Flexible Card A(P120-A)

                Add:  subbnameEudemon8000ECR52E1XXT0(16748544), --CR52E1XX0,1*10GBase LAN-XFP Optical Interface LPU A
                Add:  subbnameEudemon8000ECR52W1XXT0(16748545), --CR52W1XX0,1*10GBase WAN-XFP Optical Interface LPU A
                Add:  subbnameEudemon8000ECR52P1XXT0(16748546), --CR52P1XX0,1*OC-192c/STM-64c POS-XFP Optical Interface LPU A
                Add:  subbnameEudemon8000ECR52R1XF(16748547),   --CR52R1XX0,1*OC-192c/STM-64c RPR-XFP Optical Interface LPU A
                Add:  subbnameEudemon8000ECR52E5GF(16748548),   --CR52E5GF,5-port GbE SFP Optical Interface LPU G
                Add:  subbnameEudemon8000ECR52C8E10(16748549),  --CR52C8E10,8-Port Channelized E1-RJ45 Flexible Service Interface Card
                Add:  subbnameEudemon8000ECR52C8T10(16748550),  --CR52C8T10,8-Port Channelized T1-RJ45 Flexible Service Interface Card
                Add:  subbnameEudemon8000ECR52C1CF1(16748551),  --CR52C1CF1,1 port Channelized OC-3/STM-1 Flexible Service Interface Card
                Add:  subbnameEudemon8000ECR52L1XX0(16748552),  --1-port 10GBase WAN/LAN XFP Flexible Interface Daughter Card
                Add:  subbnameEudemon8000ECR52EBGF0(16748553),  --12-port 100/1000Base-X SFP Flexible Interface Daughter Card
                Add:  subbnameEudemon8000ECR52EBGE0(16748554),  --12-port 10/100/1000Base-TX RJ45 Flexible Interface Daughter Card
                Add:  subbnameEudemon8000ECR52P1XXBZ0(16748555),--1 port OC-192c/STM-64c POS-XFP Flexible Card
        Add:  subbnameEudemon8000ESU91L4XX00(16748556),    --SU91L4XX00 4 Port 10G Base WAN/LAN-XFP
            Add:  subbnameEudemon8000ESU91L4XX01(16748557),    --SU91L4XX01 4 Port 10G Base LAN/LAN-XFP
            Add:  subbnameEudemon8000ESU91SPCB02(16748558),    --Eudemon8000E-X,SU91SPCB02,20G Firewall Performance Expansion Card(oversea),with HS General Security Platform Software
            Add:  subbnameEudemon8000ESU91SPCC01(16748559),    --Eudemon8000E-X,SU91SPCC01,40G Firewall Processing Card,with HS General Security Platform Software
            Add:  subbnameEudemon8000ESU91SPCB01(16748560),    --Eudemon8000E-X,SU91SPCB01,80G Firewall Processing card,with HS General Security Platform Software
            Add:  subbnameEudemon8000ESUP5SPCC(16748561),          --SUP,SUP5SPCC,Service Processing Card,1*1
                Add:  subbnameEudemon8000ESUP5SPCA(16748562),          --SUP,SUP5SPCA,Service Processing Card,1*1

                Add:  subbnameEudemon8000ESU91SPCB04(16748572), --Eudemon8000E-X,SU91SPCB04,40G Firewall Processing card,Double CPUs,with HW General Security Platform Software
                Add:  subbnameEudemon8000ESU91IPSC01(16748573), --Eudemon8000E-X,SU91IPSC01,IPS Service Processing Card, with HW General Security Platform Software
                Add:  subbnameEudemon8000ESU91L5XXA0(16748574), --Eudemon8000E-X,SU91L5XXA0,5-Port 10GBase LAN/WAN-SFP+ Flexible Card A(P101,1/2wide,Occupy two sub-slots)
                Add:  subbnameEudemon8000ESU91EFGFA0(16748575), --Eudemon8000E-X,SU91EFGFA0,24-Port 100/1000Base-X-SFP Flexible Card(P100,1/2wide,Occupy two sub-slots)
                Add:  subbnameEudemon8000ESU91E1MCB(16748576),  --Eudemon8000E-X,SU91E1MCB,1-Port 40GBase LAN CFP Flexible Card(P100,1/2wide,Occupy two sub-slots)
                Add:  subbnameEudemon8000ESU91E4XFA0(16748577), --Eudemon8000E-X,SU91E4XFA0,4-Port 10GBase LAN-SFP+ Flexible Card(P100,1/4wide,Occupy one sub-slots)
                Add:  subbnameEudemon8000ESU91LBXF0(16748578),  --Eudemon8000E-X,SU91LBXF0,12-Port 10G Base LAN/WAN-SFP+ Flexible Card A(P120-A)
                Add:  bnameSUA2MPUA(16719976),          --USG6600 Main Processing Unit
                Add:  bnameSUA2CSPUA(16719977),         --USG6600 Content Security Process Unit
                Add:  bnameSUA2X2G8(16719978),          --USG6600 2*10GE Optical Ports+8GE Electric Ports Interface Card
                Add:  bnameSUA2E2XSF(16719979),         --USG6600 2*10GE Optical Ports Interface Card
                Add:  bnameSUE3E8GF(16719980),          --USG6600 8GE Optical Ports Interface Card
                Add:  bnameSUE3E4BY(16719981),          --USG6600 4GE Electric Ports Bypass Card
                Add:  bnameSUE3E8GE(16719982),          --USG6600 8GE Electric Ports Interface Card
                Add:  bnameSUE5MPUA(16719983),          -- USG3600 Main Processing Unit
                Add:  bnameSUE5DSBB(16719984),          -- USG3600 HD Switch Board
                Add:  bnameSUA1MPUB(16719985),          -- USG3600 1U Main Processing Unit Board
                Add:  bnameSUE1EPSEC(16719986),         -- USG3600 The state password encryption Daughter card
                Add:  bnameSUE5FIBA(16719987),    --Fixed Interface Board
                Add:  bnameET1D2IPS0S00(16719988),    -- IPS Module A,with HW General Security Platform Software
                Add:  bnameET1D2FW00S00(16719989),    -- NGFW Module A,with HW General Security Platform Software
                Add:  bnameET1D2FW00S01(16719990),    -- NGFW Module B,with HW General Security Platform Software
                Add:  bnameET1D2FW00S02(16719991),    -- NGFW Module C,with HW General Security Platform Software
                Add:  bnameLE1D2FW00S01(16719992),    -- NGFW Module B,with HW General Security Platform Software
                Add:  bnameSUE6MPUA(16719993),    -- Manufactured Board,USG6600,SUE6MPUA,Main Processing Unit Board
                Add:  bnameSUE3MPUA(16719994),    -- Manufactured Board,USG6300,SUE3MPUA,Main Processing Unit Board
                Add:  bnameSUE3BPKA(16719995),    -- USG6300,SUE3BKPA,1U BackPlane Board
                "

        --  Revision history MxUV8R15C00 add new mib
        REVISION    "201407031200Z"
        DESCRIPTION "V5.37,
                      Merage VRP and IAS 'S mib together.
                      "
         --  Revision history RPS add new mib
        REVISION    "201406231200Z"
        DESCRIPTION "V5.36,
                     Add: fnameCPF318(786432),       --The RPS's Power Frame backplane.
                     Add: fnameCFS01(786433),        --The RPS's Fan Frame.

                     Add: bnameCMU01(786632),              --Monitoring module board,with 0 port.
                     Add: bnameCFS01(786633),              --Fan module board,with 3 fan ports
                     Add: bnameCPF318Power(786634),        --Power input module board,with 0 port
                     Add: bnameCCM08(786635),              --Up converter module board,with 8 DC output ports
                     Add: bnameRC12S(786636),              --Down converter module board,with 12 DC input ports

                     Add: fanPort(786932),                   --Fan module fan port
                     Add: dcoutputPort(786933),              --Up converter module DC output port
                     Add: dcinputPort(786694),               --Down converter module DC input port
                     "
        --  Revision history MxUV8R15C00 add new mib
        REVISION    "201406161200Z"
        DESCRIPTION "V5.35,
                     Add: fnameMA5694SCLKH821MABC(147455), -- Virtual frame H821MABC of MA5694S  GE 1588V2 SLAVE DOCK device.
                     Add: bnameHS22GE3A(155984),           -- 3GE LAN board of the MA5694S.
                     "

        --  Revision history MA5800V1R15C10 add new mib
        REVISION    "201406121200Z"
        DESCRIPTION "V5.34,
                     Add: bnameH801X2CK(146078),         --10GE synchronized Ethernet interface board
                     "

        --  Revision history MxUV8R15C10 add new mib
        REVISION    "201406111400Z"
        DESCRIPTION "V5.33,

                      Add: frameMA5611SDE48(DT)(143377) to frameMA5611SDE48-A(DT)(143377)
                      Add: bnameCCM(155982),       -- 48-channel Vectoring VDSL2 + POTS COMBO service board
                      Add: bnameVCP(155983),       -- 64-channel Vectoring VDSL2 + SPL service board
                      "
        --  Revision history MxUV8R15C10 add new mib
        REVISION    "201406101200Z"
        DESCRIPTION "V5.32,
                      Add: bnameH822CCKRC(155980),        -- Master board of MA5633(sd5130) device.
                      Add: bnameHS33CDAC(155981),         -- DOCSIS virtual board of MA5633.
                      "
        --  Revision history MA5800V1R15C00 add new mib
        REVISION    "201406061200Z"
        DESCRIPTION "V5.31,
                     Add: bnameH802SCUB(148011),         --  control board of MA5600T
                     Add: bnameH806CAME(146077),         -- 48-channel ADSL combo service board
                     "

        --  Revision history MA5800V1R15C00 add new mib
        REVISION    "201406041200Z"
        DESCRIPTION "V5.30,
                     Add: fnameMA5800H901BPLB(148501),     -- Backplane of the MA5800
                     Add: bnameH901MPLA(148501),         --  control board of MA5800
                     Add: bnameH901MPLB(148502),         --  control board of MA5800
                     Add: bnameH901XGHD(148521),         --  8*10G GPON board of MA5800
                     Add: bnameH901GPHF(148522),         --  16*GPON board of MA5800
                     Add: bnameH901OGHK(148523),         --  48 P2P board of MA5800
                     Add: bnameH901NXED(148524),         --  8*10GE board of MA5800
                     Add: bnameH901OXHD(148525),         --  8*10GE extend board of MA5800
                     Add: bnameH901PILA(148526),         --  Power board of MA5800
                     Add: bnameH901CIUA(148527),         --  GPIO board of MA5800
                     Add: subbnameH901CKUA(148501),          -- Clock subboard of MA5800 H901MPLB
                      "
         --  Revision history MA5600TV8R15C00 add new mib
        REVISION    "201405151200Z"
        DESCRIPTION "V5.29,
                      Add: bnameH801MPWE(146076),          -- Power board of MA5608T.
                      "

        --  Revision history MxUV8R15C00 modified mib
        REVISION    "201405061200Z"
        DESCRIPTION "V5.28,
                      Add: bnameH831EPFF(155965),          -- 2 GE Vitual Board of MA5612.
                      Add: bnameH82BDVJM(155966),          -- Master board of MA5611S-AE08(sd5130) FTTS device.
                      Add: bnameHS2BDVJM(155967),          -- 8 VDSL2 board of MA5611S-AE08(sd5130) FTTS device.
                      Add: frameMA5611SAE08(561221),       -- Virtual frame MA5611S-AE08 of MA5611S(sd5130) FTTS device.
                      "

        --  Revision history MxUV8R15C00 add new mib
        REVISION    "201402201400Z"
        DESCRIPTION "V5.27,
                      Modify: frameMA5611SCE48(561206) to frameMA5611SDE48-TELUS(561206).
                      Modify: frameMA5611SDE48(561193) to frameMA5611SDE48-A(561193)
                      "

        --  Revision history MxUV8R15C00 add new mib
        REVISION    "201402171700Z"
        DESCRIPTION "V5.26,
                      Add: bnameH823UPVBP(155976),         -- Master board of MA5611S-AE16(sd5130) FTTS device for Oman.
                      Add: bnameHS23UPVBP(155977),         -- 16 VDSL2 board of MA5611S-AE16(sd5130) FTTS device for Oman.
                      Add: bnameH826BVUP(155978),          -- Master board of MA5611S-DE16(sd5130) FTTS device for BT.
                      Add: bnameHS26BVUP(155979),          -- 16 VDSL2 board of MA5611S-DE16(sd5130) FTTS device for BT.
                      "

        --  Revision history MxUV8R15C00 add new mib
        REVISION    "201401291605Z"
        DESCRIPTION "V5.25,
                      Add: frameMA5611SCE48(561206),  -- Virtual frame MA5611S-CE48 of MA5611S(sd5103) FTTS device for TELUS.
                      Add: frameMA5611SAE16(561207),  -- Virtual frame MA5611S-AE16 of MA5611S(sd5130) FTTS device for Oman.
                      Add: frameMA5611SDE16(561208),  -- Virtual frame MA5611S-DE16 of MA5611S(sd5130) FTTS device for BT.
                      "

        --  Revision history MxUV8R15C00 add new mib
        REVISION    "201401071200Z"
        DESCRIPTION "V5.24,
                      Add:     bnameH831EDTB(155975),          -- E1 board of MA5616 for CCUE and CCUD.
                      "

        --  Revision history MxUV8R15C00 add new mib
        REVISION    "201312121200Z"
        DESCRIPTION "V5.23,
                      Add:     fnameMA5633H821MABCS(561197),   -- Virtual frame H821MABCS of mini MA5633(sd5130) device.
                      Add:     bnameH822CCKRB(155973),         -- Master board of mini MA5633(sd5130) device.
                      Add:     bnameHS33CDAB(155974),          -- DOCSIS virtual board of mini MA5633.
                      Add:     subbnameH831UP2E(155952),       -- Auto adapt upstream subboard of MA5633, It supports EQAM.
                      Add:     subbnameH831UP2F(155953),       -- Auto adapt upstream subboard of MA5633, It not supports EQAM.
                      Add:     subbnameHS21PWBB(155954),       -- Virtual power subboard of MA5633.
                      Add:     subbnameHS21MIXB(155955),       -- Virtual mixer subboard of MA5633.
                      "

        --  Revision history R15C00 add new mib
        REVISION    "201310161200Z"
        DESCRIPTION "V5.22,
                      Add:     bnameH80XVPG(146138),       -- support vector board of MA5600T.
                      Add:     bnameH806CCPE(146139),      -- 64-channel POTS(combo) + Vectoring board of MA5600T device.
                      Add:     bnameH801XGBD(146141),      -- 8 ports 10G GPON board.
                      Add:     bnameH803XEBD(146142),      -- 8 ports 10G EPON board.
                      Add:     bnameH805EPFD(146143),      -- 16EPON board.
                      Add:     bnameH802GPMD(146144),      -- 8GPON board.
                      Add:     bnameH805GPFD(146145),      -- 16GPON board.
                      Add:     bnameH802XEBD(146146),      -- 8 ports 10G EPON board.
                      Add:     bnameH802SCUH(148009),      -- control board of MA5600T.
                      Add:     bnameH802SCUV(148010),      -- control board of MA5600T.
                      "

        --  Revision history R312C91 add new mib
        REVISION    "201309161200Z"
        DESCRIPTION "V5.21,
                      Add:     fnameMA5611SAE-48(561205),  -- Virtual frame H831MABC of MA5611S-AE48 device.
                      Modify: bnameH831PAVD(155919),       -- Double DC Power board H832PDVAA of  the  MA5616.
                      Modify: bnameH831PAVDA(155937),      -- Double DC Power board H831PAVDA of  the  MA5616, witch vector vp subboard.
                      Modify: bnameH831CCLF(155952),       -- Master board of MA5678(sd5130)device.
                    "
    --  Revision history R313C10 add new mib
        REVISION    "201308151200Z"
        DESCRIPTION "V5.20,
                      Modify: bnameH82DVCMM(155949),     -- Master board of MA5611S-DE48(sd5130) FTTS device.
                      Modify: bnameHS2DVCMM(155962),     -- 48 VDSL + Vectoring board of MA5611S-DE48(sd5130) device.
                      "

        --  Revision history R313C10 add new mib
        REVISION    "201308031200Z"
        DESCRIPTION "V5.19,
                      Add: frameMA5611SDE48(561193),  -- Virtual frame frameMA5611S-DE48 of MA5611S(sd5130) device.
                      Add: bnameH82DVCMM2(155949),    -- Master board of MA5611S-DE48(sd5130) FTTS device.
                      Add: bnameHS2DVCMM2(155962),    -- 48 VDSL + Vectoring board of MA5611S(sd5130) device.
                      Modify:fnameMA5694SDSLH831MABC to fnameMA5694SDSLH821MABC.
                      Modify:fnameMA5694SPONH831MABC to fnameMA5694SPONH821MABC.
                      "

        --  Revision history R313C10 add new mib
        REVISION    "201307051200Z"
        DESCRIPTION "V5.18,
                      Add:     veiPort(805),                             -- Vei port of board NLV.
                      Add:     vdslNNIPort(806),                         -- VDSL upstream port.
                    "

        --  Revision history R13C00 add new mib
        REVISION    "201307041200Z"
        DESCRIPTION "V5.17,
                      Add:     fnameMA5600H802Mabc(145952),     -- Backplane of the P300 broadband master Frame: H802MABC.
                    "

            --  Revision history R13C10 add new mib
        REVISION    "201306081200Z"
        DESCRIPTION "V5.15,
                      Add:     bnameH801SPUC(155955),        -- Interface board.
                      Add:     bnameH802OPGE(146075),        -- H802OPGE BOARD
                      Add:     subbnameH801CKMD(888891),     -- Clock subboard.
                      Add:     bnameSHG(143447),             -- P300 32-channel G.SHDSL board of the SHG series.
                    "

        --  Revision history R312C91 add new mib
        REVISION    "201306071200Z"
        DESCRIPTION "V5.15,
                      Add:     fnameMA5611SDE-48(561204),              --  Virtual frame H831MABC of MA5611S-DE48 north Americal device.
                      Add:     bnameH82BCVMM(155972),                  --  Master board of MA5611S-DE48 north Americal device.
                      Modidy:  fnameMA5611S-AE16(561191),              --  Virtual frame H831MABC of MA5611S-AE16(sd5130) device.
                    "


        --  Revision history R13C10 add new mib
        REVISION    "201305150000Z"
        DESCRIPTION "V5.14,
                      Add:     fnameMA5694SDSLH821MABC(561199), -- Virtual frame H821MABC of MA5694S  DSL DOCK device.
                      Add:     fnameMA5694SPONH821MABC(561203), -- Virtual frame H821MABC of MA5694S  PON DOCK device.
                      Add:     bnameH822CC3G(155957),         --  DSL DOCK for MA5694S device.
                      Add:     bnameHS31EPFB(155959),         --  3GE LAN board of the MA5694S.
                      Add:     subbnameH831VD4A(155951),      -- VD4A  Subboard for MA5694S.
                      Add:     bnameH822UPWC(155970),         --  PON DOCK for MA5694S device.
                      Add:     bnameHS22GE4A(155971),         --  4GE LAN board of the MA5694S.

                      Add:     bnameHS22EPGE(155961),         -- Virtual 24GE board of the MA5821.
                      Add:     bnameH836VPAA(155963),      -- VPA  Subboard for MA5616.
                      Add:     bnameH832PDNAA(155964),        -- Power board for NLV  of the MA5616.
                      Add:     subbnameVPA(155950),           -- VECTOR Subboard VPA."

        --  Revision history R13C00 add new mib
        REVISION    "201305081200Z"
        DESCRIPTION "V5.13,
                      Add:     fnameMA5633(147527),           --  MDU device MA5633 used as remote frame.
                    "

        --  Revision history R313C00 add new mib
        REVISION    "201305020000Z"
        DESCRIPTION "V5.12,
                      Add: fnameMA5898H831Mabl(561202),  -- Backplane of the MA5898 master Frame: H831MABL.
                                        "

        --  Revision history R13C00 add new mib
        REVISION    "201303220000Z"
        DESCRIPTION "V5.11,
                      Add:     bnameH801MCUE(148006),         --  MA5608T control board H801MCUE.
                      Add:     bnameH801GPMD(148007),         --  gpon board of the MA5600T.
                      Add:     bnameH801SCUV(148008),         --  MA5600T control board H801SCUV.
                      Add:     subbnameH801CPCC(204934),      --  Clock subboard for the H801MCUE board."

        --  Revision history R313C00 add new mib
        REVISION    "201303210000Z"
        DESCRIPTION "V5.10,
                      Add: fnameMA5633H821Mabco(561192),  -- Virtual frame H821MABCO of MA5633(sd5130) device.
          "

    --  Revision history UA5000V100R019C07 add new mib
        REVISION    "201303190000Z"
        DESCRIPTION "V5.09,
                      Add:     bnameH601XP1A(204880),           -- UA5000 XPON board which unites Broadband and narrowband has 5*FE Electric Ports, 4*E1 Ports, 2*GE Optical Ports, 1GE Electric Port and 1GPON Port
                                        "

        --  Revision history R313C00 add new mib
        REVISION    "201303150000Z"
        DESCRIPTION "V5.08,
                      Add: fnameMA5622A-16(561200),    -- Virtual frame H831MABC of MA5622A-16 device.
                      Add: fnameMA5622A-8(561201),     -- Virtual frame H831MABC of MA5622A-8 device.
          "

        --  Revision history R313C00 add new mib
        REVISION    "201303140000Z"
        DESCRIPTION "V5.07,
                      Add: fnameMA5818H831Maba(561195),  -- Backplane of the MA5818 master Frame: H831MABA.
                      Add: fnameMA5818H831Mabb(561196),  -- Backplane of the MA5818 master Frame: H831MABB.
                                        "
        --  Revision history R312C00 add new mib
        REVISION    "201302280000Z"
        DESCRIPTION "V5.06,

              Add:  fnameSU1Z21UHA(16715776),                   -- USG2200,SU1Z21UHA,USG2210 Host
                      Add:  fnameSU1Z21UHB(16715777),                   -- USG2200,SU1Z21UHB,USG2220 Host
                      Add:  fnameSU1Z21UHC(16715778),                   -- USG2200,SU1Z21UHC,USG2230 Host
                      Add:  fnameSU1Z21UHD(16715779),                   -- USG2200,SU1Z21UHD,USG2250 Host
                      Add:  fnameSU1Z22UHA(16715780),                   -- USG2200,SU1Z22UHA,USG2210 Host,HuaweiSymantec Overseas
                      Add:  fnameSU1Z22UHB(16715781),                   -- USG2200,SU1Z22UHB,USG2220 Host,HuaweiSymantec Overseas
                      Add:  fnameSU1Z22UHC(16715782),                   -- USG2200,SU1Z22UHC,USG2230 Host,HuaweiSymantec Overseas
                      Add:  fnameSU1Z22UHD(16715783),                   -- USG2200,SU1Z22UHD,USG2250 Host,HuaweiSymantec Overseas
                      Add:  fnameFWGZ21UHA(16715784),                   -- Quidway Eudemon,FWGZ21UHA,E200E-C Host
                      Add:  fnameFWGZ21UHD(16715785),                   -- Quidway Eudemon,FWGZ21UHD,E200E-F Host
                      Add:  fnameSRGZ2020(16715786),                    -- SRG20 Secure Routing Gateway,SRGZ2020,SRG20-20 AC Host
                      Add:  fnameSRGZ2021(16715787),                    -- SRG20 Secure Routing Gateway,SRGZ2021,SRG20-21 AC Host
                      Add:  fnameSRGZ2030(16715788),                    -- SRG20 Secure Routing Gateway,SRGZ2030,SRG20-30 AC Host
                      Add:  fnameSRGZ2031(16715789),                    -- SRG20 Secure Routing Gateway,SRGZ2031,SRG20-31 AC Host
                      Add:  fnameSRGZ2020IE(16715790),                  -- SRG20 Secure Routing Gateway,SRGZ2020IE,SRG20-20 AC Host
                      Add:  fnameSRGZ2021IE(16715791),                  -- SRG20 Secure Routing Gateway,SRGZ2021IE,SRG20-21 AC Host
                      Add:  fnameSRGZ2030IE(16715792),                  -- SRG20 Secure Routing Gateway,SRGZ2030IE,SRG20-30 AC Host
                      Add:  fnameSRGZ2031IE(16715793),                  -- SRG20 Secure Routing Gateway,SRGZ2031IE,SRG20-31 AC Host
                      Add:  fnameSU0Z11UHB(16715794),                   -- USG2100-SU0Z11UHB-USG2130 Host,HuaweiSymantec Overseas
                      Add:  fnameSU0Z13UHB(16715795),                   -- USG2100-SU0Z13UHB-USG2160 Host,HuaweiSymantec Overseas
                      Add:  fnameSRGZ23UHT(16715796),                   -- SRG3260,SRGZ23UHT,SRG3260 Host,with HS General Security Platform Software
                      Add:  fnameSU2Z12UAH(16715797),                   -- USG5100,SU2Z12UAH,USG5120 AC Host,with HS General Security Platform Software
                      Add:  fnameSU2Z12UDH(16715798),                   -- USG5100,SU2Z12UDH,USG5120 DC Host,with HS General Security Platform Software
                      Add:  fnameSU2Z13UHT(16715799),                   -- USG5100,SU2Z13UHT,USG5150 Host,with HS General Security Platform Software
                      Add:  fnameSU2Z22UAH(16715800),                   -- USG5100,SU2Z22UAH,USG5120BSR AC Host,with HS General Security Platform Software
                      Add:  fnameSU2Z22UDH(16715801),                   -- USG5100,SU2Z22UDH,USG5120BSR DC Host,with HS General Security Platform Software
                      Add:  fnameSU2Z23UHT(16715802),                   -- USG5100,SU2Z23UHT,USG5150BSR Host,with HS General Security Platform Software
                      Add:  fnameSRGZ12UAH(16715803),                   -- SRG3230,SRGZ12UAH,SRG3230 AC Host,with HS General Security Platform Software
                      Add:  fnameSRGZ22UAH(16715804),                   -- SRG3240,SRGZ22UAH,SRG3240 AC Host,with HS General Security Platform Software
                      Add:  fnameSRGZ22UDH(16715805),                   -- SRG3240,SRGZ22UDH,SRG3240 DC Host,with HS General Security Platform Software
                      Add:  fnameSRGZ13UHT(16715806),                   -- SRG3250,SRGZ13UHT,SRG3250 Host,with HS General Security Platform Software
                      Add:  fnameSU1ZAH10FE(16715807),              -- USG2200,SU1ZAH10FE,USG2210 AC Basic Configuration,(2GE,10FE,with 2*5FE MIC),with HS General Security Platform Software
                      Add:  fnameSU2Z42UAH(16715808),                 -- USG5100,SU2Z42UAH,USG5120BSR AC Host,with HS General Security Platform Software
                      Add:  fnameSU2Z43UHTO1(16715809),               -- USG5100,SU2Z43UHT,USG5150BSR Host,with HS General Security Platform Software
                      Add:  fnameSU2Z43UHTO2(16715810),               -- USG5500 1U Frame Unit
                      Add:  fnameSU2Z43UHT(16715811),                 -- USG5500 3U Frame Unit
              Add:  fnameSUAB13UAC(16715812),               -- USG6600 SUAB13UAC  Frame Unit
              Add:  fnameNGFW1UL2(16715813),                    -- USG3600 L2 Frame Unit
              Add:  fnameNGFW1UL1(16715814),                    -- USG3600 L1 Frame Unit
              Add:  fnameNGFWSSM(16715815),                     -- NGFW SSM Frame Unit
                      Add:  bnameSU01MPUA(16719922),          -- SRG20,SU01MPUA,SRG20  Main Processing Unit ,2*1
                      Add:  bnameSU01MPUB(16719923),          -- SRG20,SU01MPUB,SRG20  Main Processing Unit ,2*1
                      Add:  bnameSU01MPUC(16719924),          -- SRG20,SU01MPUC,SRG20  Main Processing Unit ,2*1
                      Add:  bnameSU01ADPA(16719925),          -- SRG20,SU01ADPA,ADSL2+Multi-PVCs,2*2
                      Add:  bnameSU11SMX01(16719926),         -- Safety Product,SRG20,SU11SMX01,Enhanced Services Platform,ultra-low-end ,with CF Card, no Hard Disk
                      Add:  bnameSU11DMX02(16719927),         -- Safety Product,SRG20,SU11DMX02,Enhanced Services Platform,low-end , 2.5'' Hard Disk
                      Add:  bnameSU11DFX03(16719928),         -- Safety Product,SRG20,SU11DFX03, Enhanced Services Platform,mid-range , 2.5'' Hard Disk
                      Add:  bnameSU11DFX04(16719929),         -- Safety Product,SRG20,SU11DFX04, Enhanced Services Platform,mid-range , two 2.5'' Hard Disk
                      Add:  bnameSU11DFX05(16719930),         -- Safety Product,SRG20,SU11DFX05, Enhanced Services Platform,high-end ,with CF Card, two 2.5'' Hard Disk
                      Add:  bnameFWG2MPUA(16719931),          -- USG2200,FWG2MPUA,Main Process Unit Board,1*1
                      Add:  bnameSU11ADPA(16719932),          -- SRG20,SU11ADPA,ADSL2+Multi-PVCs,with HS General Security Platform Software,1*1
                      Add:  bnameFWF1E1FE(16719933),          -- USG2100,FWF1E1FE,1-Port Fast Ethernet Electrical Interface Board(RJ45),3*1
                      Add:  bnameSU11EPSEC(16719934),         -- USG5100,SU11EPSEC,High Speed IPsec Card,with HS General Security Platform Software
                      Add:  bnameSU51E4BY(16719935),          -- USG5100,SU51E4BY,4GE Electric Ports Bypass Card,with HS General Security Platform Software,1*1 duplicated with bnameSU51E4BY(16719960) add 'O'
                      Add:  bnameWCDMA(16719955),             --SVN5300,Security 3G board(WCDMA)
                      Add:  bnameTD-SCDMA(16719956),          --SVN5300,Security 3G board(TD-SCDMA)
                      Add:  bnameCDMA2000(16719957),          --SVN5300,Security 3G board(CDMA2000)
                      Add:  bnameSU51MPUB(16719958),          --USG5500,SU51MPUB,1U Main Processing Unit,1*1
                      Add:  bnameSU51SACC(16719959),          --USG5500,SU51SACC,Service Accelerate Card,1*1  duplicated with bnameSU51SACC(16719967) add 'O'
                      Add:  bnameSU51E4BY(16719960),          --USG5500,SU51E4BY,4GE Electric Ports Bypass Card,with HS General Security Platform Software,1*1
                      Add:  bnameSU51MPUA(16719961),          --USG5500,SU51MPUA,Main Processing Unit,1*1
                      Add:  bnameSU51X2G8(16719962),          --USG5500,SU51X2G8,2*10GE Optical Ports+8GE Electric Ports Interface Card,with HS General Security Platform Software,1*1
                      Add:  bnameSU51E2XSM(16719963),         --USG5500,SU51E2XSM,2*10GE Optical Ports Interface Card,with HS General Security Platform Software,3*1
                      Add:  bnameSU51E8GF(16719964),          --USG5500,SU51E8GF,8GE Optical Ports Interface Card,with HS General Security Platform Software,2*1
                      Add:  bnameSU51E8GE(16719965),          --USG5500,SU51E8GE,8GE Electric Ports Interface Card,with HS General Security Platform Software,1*1
                      Add:  bnameSU51E2XSF(16719966),         --USG5500,SU51E2XSF,2*10GE Optical Ports Interface Card,with HS General Security Platform Software,1*1
                      Add:  bnameSU51SACC(16719967),          --USG5500,SU51SACC,Service Accelerate Card,1*1
                      Add:  bnameSU51F2BY(16719968),          --USG5500,2 Link LC/UPC Optical Interface Bypass Protect Card
                      Add:  bnameSU51E8GFF(16719969),         --USG5500,8GE Optical Ports FIC Interface Card
                      Add:  bnameSU71DFX01(16719970),         --Safety Product,NIP5100,SU71DFX01,Enhanced Services Platform,High-end,for IPS
                      Add:  bnameSU51ESPA(16719971),          --NIP5100,ESP,SU51ESPA,X86 Process Card,1*1
                      Add:  bnameSU51ESPC(16719972),          --NIP5100,ESP,SU51ESPC,IPS Process Card,1*1
                      Add:  bnameSU51F2BY01(16719973),        --USG5500,SU51F2BY01,2 Link LC/UPC Multimode Optical Interface Bypass Protect Card,with HS General Security Platform Software
                      Add:  bnameSU51F2BY02(16719974),        --USG5500,SU51F2BY02,2 Link LC/UPC Singlemode Optical Interface Bypass Protect Card,with HS General Security Platform Software
                      Add:  bnameSUA1CPUA(16719975),          --Eudemon1000E-N CPU Card
                      Add:  bnameE8000ESU91SPUC(16748550),    --Eudemon8000E-X,SU91SPUC,X3 Service Processiong Unit(Base Board),with HS General Security Platform Software
                      Add:  bnameE8000ESU91SPUD(16748551),    --Eudemon8000E-X,SU91SPUD,X8&X16 Service Processiong Unit(Base Board),with HS General Security Platform Software
                      Add:  subbnameSVN5500CN1620(16740353),  -- SVN5500,SE41HSVA,High Speed SSL VPN Card,with HS General Security Platform Software,1*1
                      Add:  subbnameSUP34SFPCard(16732162),   --SUP,SUP34SFP,4-port GE Optical Interface Board(SFP),1*2
                      Add:  subbnameEudemon8000ESU91L4XX00(16748556),      --SU91L4XX00 4 Port 10G Base WAN/LAN-XFP
                      Add:  subbnameEudemon8000ESU91L4XX01(16748557),      --SU91L4XX01 4 Port 10G Base LAN/LAN-XFP
                      Add:  subbnameEudemon8000ESU91SPCB02(16748558),      --Eudemon8000E-X,SU91SPCB02,20G Firewall Performance Expansion Card(oversea),with HS General Security Platform Software
                      Add:  subbnameEudemon8000ESU91SPCC01(16748559),      --Eudemon8000E-X,SU91SPCC01,40G Firewall Processing Card,with HS General Security Platform Software
                      Add:  subbnameEudemon8000ESU91SPCB01(16748560),      --Eudemon8000E-X,SU91SPCB01,80G Firewall Processing card,with HS General Security Platform Software

                                        "

        --  Revision history R313C00
        REVISION    "201302250000Z"
        DESCRIPTION "V5.05,
                      Add:  frameMA5611S-DE16(561194),  -- Virtual frame MA5611S-DE16 of MA5611S FTTS device.
                      Add:  bnameHS26BVVS(155950),      -- 16 VDSL + Vectoring board of MA5611S FTTS device.
                      Add:  bnameH826BVVS(155951),      -- Master board of MA5611S FTTS device.
                                        "

        REVISION    "201301310000Z"
        DESCRIPTION "V5.03,
                      Modidy:  frameMa5662AH831MABC(561177),    -- Virtual Backplane of MA5662(SD5103) , master Frame:MA5662(SD5103).
                                        "

        --  Revision history R13C00 add new mib
        REVISION    "201301190000Z"
        DESCRIPTION "V5.02,
                      Add:     bnameH801XESD(146137),        --  8 ports 10G EPON board of MA5600T.
                                        "

        --  Revision history R312C00 add new mib
        REVISION    "201301140000Z"
        DESCRIPTION "V5.01,
                      Add:     subbnameVPD(155949),      -- VECTOR Subboard VPD
                      "

        --  Revision history R313C00 add new mib
        REVISION    "201301040000Z"
        DESCRIPTION "V5.00,
                      Add: fnameMA5611SH831Mabc(561191),  -- Virtual frame H831MABC of MA5652(sd5130) device.
                      Add: bnameH823UPVB(155947),         -- Master board of MA5652(sd5130) device.
                      Add: bnameHS23UPVB(155948),        -- 16 VDSL + Vectoring board of MA5652(sd5130) device.
                      "

        REVISION    "201211260000Z"
        DESCRIPTION "V4.99,
                      Add: bnameHS3BCVSB(155945),  -- 16 VDSL+16 POTS combo board of MA5622A.
                      Add: bnameHS3BCVSD(155946),  --  8 VDSL+ 8 POTS combo board of MA5622A.
                      "

        --  Revision history
        REVISION    "201211200000Z"
        DESCRIPTION "V4.98,
                      Add:     bnameH801MCUD1(148005),        --  control board of MA5608T.
                      "

        REVISION    "201211150000Z"
        DESCRIPTION "V4.97,
                      Add: fnameMA5821H821Mabc(561189),  -- Virtual frame H821MABC of MA5821(sd5133) device.
                      Add: fnameMA5822H821Mabc(561190),  -- Virtual frame H821MABC of MA5822(sd5133) device.
                      Add: bnameH825XPUB(155944),        -- Master board of MA582x(sd5133)device.
                      "

        --  Revision history
        REVISION    "201211120000Z"
        DESCRIPTION "V4.96,
                      Add: fnameMA5821H821Mabc(561189),  -- Virtual frame H821MABC of MA5821(sd5133) device.
                      Add: fnameMA5822H821Mabc(561190),  -- Virtual frame H821MABC of MA5822(sd5133) device.
                      Add: bnameH825XPUB(155942),        -- Master board of MA582x(sd5133)device.
                      "


        --  Revision history
        REVISION    "201210301500Z"
        DESCRIPTION "V4.95,
                      Add:     bnameH801SPUF(146073),        -- interface board.
                      Add:     bnameH801MPWD(146074),        -- Power board of MA5608T.
                      "

        REVISION    "201209060000Z"
        DESCRIPTION "V4.94,
                      Add:     bnameH801SCUK(148003),         --  MA5600T control board H801SCUK.
                      Add:     bnameH801SCUE(148004),         --  MA5600T control board H801SCUE.
                      "

        REVISION    "201209030000Z"
        DESCRIPTION "V4.93,
                      Modidy:  fnameMA5608H801Mabr(147525),    -- Backplane of the P300 broadband medium-capacity master Frame: H801MABR
                      "

        REVISION    "201208250000Z"
        DESCRIPTION "V4.92,
                      Add:     bnameH802SCUN(148001),         --  MA5600T control board H802SCUN.
                      Add:     bnameH801SPUH(148002),         --  interface board of the MA5600T.
                      "

        --  Revision history
        REVISION    "201208140000Z"
        DESCRIPTION "V4.91,
                      Add:     fnameMA5623AR(147526),          --  MDU device MA5623A used as remote frame.
                    "

        --  Revision history
        REVISION    "201208130000Z"
        DESCRIPTION "V4.90,
                      Modidy:  fnameMA5694H821Mabc(561187),    -- Virtual frame H821MABC of MA5694(sd5130) device.
                      Modidy:  bnameH821CCIC(155935),          -- Master board of MA5694(sd5130)device.
                      Modidy:  bnameHS21GE4A(155936),          -- 4GE baoard for MA5694.
                      "

        --  Revision history
        REVISION    "201207300000Z"
        DESCRIPTION "V4.89,
                      Add:     bnameH831PAVD(155942),          -- 400W AC for MA5616.
                      Add:     bnameH831PAVDA(155943),         -- 400W AC+Vector for MA5616.
                      Add:     subbnameH833XP1A(155935),       -- 10 GPON Subboard
                      Add:     subbnameH833XP1C(155936),       -- 10 GPON Subboard
                      "

        --  Revision history
        REVISION    "201207260000Z"
        DESCRIPTION "V4.88,
                      Add:     bnameH832PDVAA(155933),   -- Double DC Power board H832PDVAA of  the  MA5616, supportting vector vp subboard.
                      Add:     subbnameVPB(155934),      -- VECTOR Subboard VPB
                      Update:  bnameVPB(155922)
                      Modidy:  bnameH831CCMC(155941),    -- Master board of MA5698(sd5130)device.
                      "

       --  Revision history
        REVISION    "201207250000Z"
        DESCRIPTION "V4.87,
                      Add: fnameMA5698H821Mabc(561186),     -- Virtual frame H821MABC of MA5698(sd5130) device.
                      Add: fnameMA5691H821Mabc(561187),     -- Virtual frame H821MABC of MA5691(sd5130) device.
                      Add: fnameMA5678H821Mabc(561188),     -- Virtual frame H821MABC of MA5678(sd5130) device.
                      Add: bnameH831CCMC(155933),           -- Master board of MA5698(sd5130)device.
                      Add: bnameHS31GC4A(155934),           -- 4GE baoard(2GE+2GE COMBO) for MA5698.
                      Add: bnameH821CCIC(155935),           -- Master board of MA5691(sd5130)device.
                      Add: bnameHS21GE4A(155936),           -- 4GE baoard for MA5691.
                      Add: bnameH831CCLF(155937),           -- Master board of MA5678(sd5130)device.
                      Add: bnameH831E41B(155938),           -- 4E1 baoard for MA5678.
                      Add: bnameHS38ASRB(155939),           -- 32POTS baoard for MA5678.
                      Add: bnameHS31GE4A(155940),           -- 4GE baoard for MA5678.
                    "

       --  Revision history
       REVISION    "201207230000Z"
       DESCRIPTION "V4.86, Modified the illegal comment symbol for FT."


       --  Revision history
        REVISION    "201206130000Z"
        DESCRIPTION "V4.85,
                      Add:     bnameH801MABR(147525),         --  Backplane of the P300 broadband master Frame: H801MABR.
                      Add:     subbnameH801CPCA(204923),      --  Clock subboard for the H801MCUD board.
                      Add:     subbnameH801CPCA(204933),      --  Clock subboard for the H801MCUD board.
                      Update:  bnameAF11SPLTA(745751),        --  AF11SPLTA.
                      Update:  bnameAF11SPPTA(745752),        --  AF11SPPTA.
                    "

       --  Revision history
        REVISION    "201206070000Z"
        DESCRIPTION "V4.84,
                      Add: docsisPort(804),       -- docsis port of board HS33CDAA,the board has only one port(docsisPort).
                    "

       --  Revision history
        REVISION    "201205080000Z"
        DESCRIPTION "V4.83,
                      Add: bnameH822CCKRA(155930),       -- Master board of MA5633(sd5130)device.
                      Add: bnameHS33CDAA(155931),        -- DOCSIS virtual board of MA5633
                      Add: bnameH83BVCL(155932),         -- 32 VDSL + Vectoring board of MA5616
                      Add: fnameMA5633H821Mabc(561185),  -- Virtual frame H821MABC of MA5633(sd5130) device.
                    "

       --  Revision history
        REVISION    "201203060000Z"
        DESCRIPTION "V4.82,
                      Add:  bnameHS22CCVW(155928) ,    -- Master board of MA5623A(sd5130)device.
                      Add:  bnameHS3BVCMM(155929),        -- 48 VDSL baoard, supportting for vector
                      Add: fnameMA5623AH823Maba(561184),    -- Virtual frame H823MABA of MA5623A(sd5130) device.
                    "

        --  Revision history
        REVISION    "201202150000Z"
        DESCRIPTION "V4.80,
                    Add: fnameMA562XS2H821Mabc(561182),    -- Virtual frame H821MABC of MA562X(sd5130) device.
                    Add: fnameMA562XS3H821Mabc(561183),    -- Virtual frame H821MABC of MA562X(sd5132) device.
                    Add: bnameH831CCUD(155923),        -- Master board of MA5616(SD5130) Box type device
                    Add: bnameH831PAIBA(155924),       -- Power board H831PAIBA of the MA561X
                    Add: bnameH825EPUB(155925),        -- Master board of MA5620/26(SD5132) Box type device
                    Add: bnameH823EPUB(155926),        -- Master board of MA5626-8 PoE(SD5130) Box type device
                    Add: bnameHS22EPFG(155927),        -- 8 GE board of MA5626(SD5130)
                    Add: subbnameH832TP1C(155668),          --1*10G EPON subboard
                  "

        --  Revision history
        REVISION    "201202130000Z"
        DESCRIPTION "V4.79,
                    Add 8 ports GPON board, 16 ports GPON board, 8 ports EPON board, 16 ports EPON board. The range of type is 146102 to 146136.
                  "

        --  Revision history
        REVISION    "201202020000Z"
        DESCRIPTION "V4.78,
                    Add: bnameH801SCUH(146101),         --two GE port and two 10GE port H801SCUH control board of MA5600T.
                  "

        --  Revision history
        REVISION    "201201160000Z"
        DESCRIPTION "V4.77,
                    Add: subbnameH821PRCA(155667),          --RFT-C subboard
                    "

        --  Revision history
        REVISION    "201201130000Z"
        DESCRIPTION "V4.76,
                    Add: iODN devices to HWFrameType, HWPCBType, and HWSubPCBType, range 0x000B0000~0x000BFFFF, which are:
                    Add: fnameMPU3101B-AC-1U(720898),              --MPU3101B-AC-1U
                    Add: fnameMPU3101C-AC-1U(720899),              --MPU3101C-AC-1U
                    Add: fnameMPU3101D-AC-1U(720900),              --MPU3101D-AC-1U
                    Add: fnameMPU3101B-DC-1U(720901),              --MPU3101B-DC-1U
                    Add: fnameMPU3101C-DC-1U(720902),              --MPU3101C-DC-1U
                    Add: fnameMPU3101D-DC-1U(720903),              --MPU3101D-DC-1U
                    Add: fnameAF11FPUA(721153),                    --AF11FPUA
                    Add: fnameAF11FPUAT(721154),                   --AF11FPUAT
                    Add: fnameGPX147-iMODF-6U(721155),             --GPX147-iMODF-6U
                    Add: fnameAF11FATA(721156),                    --AF11FATA
                    Add: fnameAF11FATC(721409),                    --AF11FATC
                    Add: fnameAF11FATB(721410),                    --AF11FATB
                    Add: fnameGPX147-iODF3101(729089),             --GPX147-iODF3101
                    Add: fnameGXF147-iFDT3101(729090),             --GXF147-iFDT3101
                    Add: fnameGXF147-iFDT3101D(729091),            --GXF147-iFDT3101D
                    Add: fnameGXF147-FDT2107D(729092),             --GXF147-FDT2107D
                    Add: fnameGPX147-iFAT3101(729093),             --GPX147-iFAT3101
                    Add: fnameGPX147-iFAT3102-12(729094),          --GPX147-iFAT3102-12
                    Add: fnameGPX147-iFAT3102(729095),             --GPX147-iFAT3102
                    Add: fnameGPX147-ODF5101-CH2-1200mm(729096),   --GPX147-ODF5101-CH2-1200mm
                    Add: fnameGPX147-ODF5101-FH2-1200mm(729097),   --GPX147-ODF5101-FH2-1200mm
                    Add: fnameGPX147-ODF5101-CH2-900mm(729098),    --GPX147-ODF5101-CH2-900mm
                    Add: fnameGPX147-ODF5101-FH2-900mm(729099),    --GPX147-ODF5101-FH2-900mm
                    Add: fnameGPX147-ODF5101-CH9(729100),          --GPX147-ODF5101-CH9
                    Add: fnameGPX147-ODF5101-FH9(729101),          --GPX147-ODF5101-FH9
                    Add: fnameGXF147-iFDT3101D-A(729102),          --GXF147-iFDT3101D-A
                    Add: fnameGXF147-iFDT3103D-432(729104),        --GXF147-iFDT3103D-432
                    Add: fnameGPX147-iFAT3103T-16(729345),         --GPX147-iFAT3103T-16
                    Add: fnameGPX147-iFAT3103T-24(729346),         --GPX147-iFAT3103T-24
                    Add: fnameGPX147-iFAT3105T-32(729347),         --GPX147-iFAT3105T-32
                    Add: fnameGPX147-iFAT3105T-36(729348),         --GPX147-iFAT3105T-36
                    Add: fnameGPX147-iFAT3101TD-32(729349),        --GPX147-iFAT3101TD-32
                    Add: fnameGPX147-iFAT3101TD-36(729350),        --GPX147-iFAT3101TD-36
                    Add: fnameGPX147-iFAT3103TD-96-F(729351),      --GPX147-iFAT3103TD-96-F
                    Add: fnameGPX147-iFAT3103TD-96-P(729352),      --GPX147-iFAT3103TD-96-P
                    Add: fnameGPX147-SR5101-5U(737281),            --GPX147-SR5101-5U
                    Add: fnameGPX147-SR5101-5U-2(737282),          --GPX147-SR5101-5U-2
                    Add: fnameGPX147-SR5102-5U(737283),            --GPX147-SR5102-5U
                    Add: fnameGXF147-FAT5201T(737284),             --GXF147-FAT5201T

                    Add: bnameAF11TMSA(745473),                    -- AF11TMSA
                    Add: bnameAF11TMUA(745474),                    -- AF11TMUA
                    Add: bnameAF11TMLA(745475),                    -- AF11TMLA
                    Add: bnameAF11TMPA(745476),                    -- AF11TMPA
                    Add: bnameAF11STSA(745477),                    -- AF11STSA
                    Add: bnameAF11STUA(745478),                    -- AF11STUA
                    Add: bnameAF11STLA(745479),                    -- AF11STLA
                    Add: bnameAF11STPA(745480),                    -- AF11STPA
                    Add: bnameAF11SPSIA(745481),                   -- AF11SPSIA
                    Add: bnameAF11SPUIA(745482),                   -- AF11SPUIA
                    Add: bnameAF11SPLIA(745483),                   -- AF11SPLIA
                    Add: bnameAF11SPPIA(745484),                   -- AF11SPPIA
                    Add: bnameAF11SPSHA(745485),                   -- AF11SPSHA
                    Add: bnameAF11SPUHA(745486),                   -- AF11SPUHA
                    Add: bnameAF11SPLHA(745487),                   -- AF11SPLHA
                    Add: bnameAF11SPPHA(745488),                   -- AF11SPPHA
                    Add: bnameAF11SPSOA(745489),                   -- AF11SPSOA
                    Add: bnameAF11SPUOA(745490),                   -- AF11SPUOA
                    Add: bnameAF11SPLOA(745491),                   -- AF11SPLOA
                    Add: bnameAF11SPPOA(745492),                   -- AF11SPPOA
                    Add: bnameAF11SPSPA(745493),                   -- AF11SPSPA
                    Add: bnameAF11SPUPA(745494),                   -- AF11SPUPA
                    Add: bnameAF11SPLPA(745495),                   -- AF11SPLPA
                    Add: bnameAF11SPPPA(745496),                   -- AF11SPPPA
                    Add: bnameAF11SPSJA(745497),                   -- AF11SPSJA
                    Add: bnameAF11SPUJA(745498),                   -- AF11SPUJA
                    Add: bnameAF11SPLJA(745499),                   -- AF11SPLJA
                    Add: bnameAF11SPPJA(745500),                   -- AF11SPPJA
                    Add: bnameAF11SPSQA(745501),                   -- AF11SPSQA
                    Add: bnameAF11SPUQA(745502),                   -- AF11SPUQA
                    Add: bnameAF11SPLQA(745503),                   -- AF11SPLQA
                    Add: bnameAF11SPPQA(745504),                   -- AF11SPPQA
                    Add: bnameAF11SPSKA(745729),                   -- AF11SPSKA
                    Add: bnameAF11SPUKA(745730),                   -- AF11SPUKA
                    Add: bnameAF11SPLKA(745731),                   -- AF11SPLKA
                    Add: bnameAF11SPPKA(745732),                   -- AF11SPPKA
                    Add: bnameAF11SPSRA(745733),                   -- AF11SPSRA
                    Add: bnameAF11SPURA(745734),                   -- AF11SPURA
                    Add: bnameAF11SPLRA(745735),                   -- AF11SPLRA
                    Add: bnameAF11SPPRA(745736),                   -- AF11SPPRA
                    Add: bnameAF11SPSLA(745737),                   -- AF11SPSLA
                    Add: bnameAF11SPULA(745738),                   -- AF11SPULA
                    Add: bnameAF11SPLLA(745739),                   -- AF11SPLLA
                    Add: bnameAF11SPPLA(745740),                   -- AF11SPPLA
                    Add: bnameAF11SPSSA(745741),                   -- AF11SPSSA
                    Add: bnameAF11SPUSA(745742),                   -- AF11SPUSA
                    Add: bnameAF11SPLSA(745743),                   -- AF11SPLSA
                    Add: bnameAF11SPPSA(745744),                   -- AF11SPPSA
                    Add: bnameAF11SPSMA(745745),                   -- AF11SPSMA
                    Add: bnameAF11SPUMA(745746),                   -- AF11SPUMA
                    Add: bnameAF11SPLMA(745747),                   -- AF11SPLMA
                    Add: bnameAF11SPPMA(745748),                   -- AF11SPPMA
                    Add: bnameAF11SPSTA(745749),                   -- AF11SPSTA
                    Add: bnameAF11SPUTA(745750),                   -- AF11SPUTA
                    Add: bnameAF11SPLTA(745741),                   -- AF11SPLTA
                    Add: bnameAF11SPPTA(745742),                   -- AF11SPPTA
                    Add: bnameAF11STUB(745985),                    -- AF11STUB
                    Add: bnameAF11STSB(745986),                    -- AF11STSB
                    Add: bnameAF11STLB(745987),                    -- AF11STLB
                    Add: bnameAF11STPB(745988),                    -- AF11STPB
                    Add: bnameAF11STUC(745989),                    -- AF11STUC
                    Add: bnameAF11STSC(745990),                    -- AF11STSC
                    Add: bnameAF11STLC(745991),                    -- AF11STLC
                    Add: bnameAF11STPC(745992),                    -- AF11STPC
                    Add: bnameAF11TMUB(745993),                    -- AF11TMUB
                    Add: bnameAF11TMSB(745994),                    -- AF11TMSB
                    Add: bnameAF11TMLB(745995),                    -- AF11TMLB
                    Add: bnameAF11TMPB(745996),                    -- AF11TMPB
                    Add: bnameAF11TMUC(745997),                    -- AF11TMUC
                    Add: bnameAF11TMSC(745998),                    -- AF11TMSC
                    Add: bnameAF11TMLC(745999),                    -- AF11TMLC
                    Add: bnameAF11TMPC(746000),                    -- AF11TMPC

                    Add: subbnameAF11AMCX1(753921),                --AF11AMCX1
                    Add: subbnameAF11AMCB1(753922),                --AF11AMCB1
                    Add: subbnameAF11AMCC1(753923),                --AF11AMCC1
                    Add: subbnameAF11AMCD1(753924),                --AF11AMCD1
                    Add: subbnameAF11AMCX2(753925),                --AF11AMCX2
                    Add: subbnameAF11AMCB2(753926),                --AF11AMCB2
                    Add: subbnameAF11AMCC2(753927),                --AF11AMCC2
                    Add: subbnameAF11AMCD2(753928),                --AF11AMCD2
                    "
        REVISION    "201111220000Z"
        DESCRIPTION "V4.75,
                    Add: bnameH83BVCMM(155921),  -- 48 VDSL baoard, supportting for vectoring.
                    Add: bnameH831VPBB(155922),  -- vector control engine board.
                    "

        --  Revision history
        REVISION    "201111160000Z"
        DESCRIPTION "V4.74,
                    Add: bnameH80BCVME(146099),   -- 48-channel VDSL2+ and POTS(combo) service board.
                    Add: bnameH801XGBC(146100),   -- 4-channel 10GE GPON board.
                  "


        --  Revision history
        REVISION    "201111150000Z"
        DESCRIPTION "V4.73,
                    Add: bnameH80XVPE(146097),   -- support vector board.
                    Add: bnameH80XVCM(146098),   -- support vector board.
                    "

        --  Revision history
        REVISION    "201111020000Z"
        DESCRIPTION "V4.72,
                    Add: bnameH831CCUE(155912),        -- Master board of MA5616(SD5130) Box type device
                    "

        --  Revision history
        REVISION    "201110280000Z"
        DESCRIPTION "V4.71,
                    Add: subbnameH821MODA(155666),          --56K MODEM subboard
                    "

        --  Revision history
        REVISION    "201110200000Z"
        DESCRIPTION "V4.70,
                    Delete: bnameH806EPBD(146088),    -- 8EPON board.
                    Modify: bnameH803GPFD(146097) to bnameH803GPFD(146088).
                    "
        --  Revision history
        REVISION    "201110190000Z"
        DESCRIPTION "V4.69,
                    Add: bnameH806EPBD(146088),   -- 8EPON board.
                    Add: bnameH807EPBD(146089),   -- 8EPON board.
                    Add: bnameH808EPBD(146090),   -- 8EPON board.
                    Add: bnameH806EPFD(146091),   -- 16EPON board.
                    Add: bnameH806GPBD(146092),    -- 8GPON board.
                    Add: bnameH807GPBD(146093),    -- 8GPON board.
                    Add: bnameH808GPBD(146094),    -- 8GPON board.
                    Add: bnameH801GPFD(146095),    -- 16GPON board.
                    Add: bnameH802GPFD(146096),    -- 16GPON board.
                    Add: bnameH803GPFD(146097),    -- 16GPON board.
                    "

        --  Revision history
        REVISION    "201109300000Z"
        DESCRIPTION "V4.68,
                    Add: fnameMA5626POEH821Mabc(143451),  -- Virtual Frame of MA5626 POE Spec master Frame:H821MABC
                    Add: fnameMA5621AH831Mabc(561181),    -- Virtual Frame H831MABC of MA5621A device.
                    Add: bnameHS22EPFA(155910),         -- 24 POE board of 5626.
                    Add: bnameHS22EPFB(155911),         -- 16 POE board of 5626.
                    Add: bnameHS22EPFD(155913),         -- 8  POE board of 5626.
                    Add: bnameH832PDVA(155914),         -- Double DC Power board H832PDVA of  the  MA5616.
                    Add: bnameHS22EPFF(155915),        -- 4 FE board of MA5621A.
                    Add: bnameHS22COMF(155916),        -- 2-channel Serial board of MA5621A.
                    Add: bnameH823CCIQ(155917),        -- Master board of MA5621A Box type device.
                    Add: bnameH83BCVL(155918),         -- 32 VDSL+32 POTS combo board of MA5616.
                    Add: bnameHS22CCVB(155920),        -- Master board of MA5622A(SD5103) Box type device.
                    Add: subbnameH831XP1A(155665),     --10G GPON subboard.
                    Modify: bnameH822EPUC to bnameHS22CCVA.
                    Modify: bnameH828ASNB to bnameHS3BCVSE.
                    Modify: bnameHS25VDUE to bnameHS3BVDSE.
                    "

    --  Revision history
        REVISION    "201109260000Z"
        DESCRIPTION "V4.67,
                    Add: fnameMA5632DH821Mabc(561179),   -- Virtual frame H821MABC of 5632 device with GE and Auto.
                    Add: fnameMA5616H831Mabb(561180),   -- vector frame of 5616 ARM device.
                    Modify: fnameMA5632H821Mabc to fnameMA5632SH821Mabc.
                    "

        --  Revision history
        REVISION    "201109230000Z"
        DESCRIPTION "V4.66,
                    Add: fnameMA5603H802Mabo(147523),     -- Backplane of the P300 broadband medium-capacity master Frame: H802MABO
                    "

        --  Revision history
        REVISION    "201109160000Z"
        DESCRIPTION "V4.65,
                    Add: bnameH808EPSD(146087),   -- 8EPON board.
                    "

        --  Revision history
        REVISION    "201109050000Z"
        DESCRIPTION "V4.64,
                    Add: fnameMA5669H831Mabc(561178),   -- Virtual Frame H831MABC of MA5669 device.
                    Add: bnameH822EPUD(155827),         -- 1-port autoAdpt Master board of MA5669 Box type device.
                    Add: bnameH822UPIG(155828),         -- 2-port GE board without POE of MA5669.
                    Add: bnameH822UPWG(155829),         -- 2-port GE board with POE of MA5669.
                    Add: frameMa5662AH831MABC(561175),  -- Virtual Backplane of MA5662(SD5103) , master Frame:MA5662(SD5103).
                    Add: bnameH82BCVMM(155825),         -- Master board of MA5662(SD5103) Box type device.
                    Add: bnameHS3BVDMM(155826),         -- 48-channel VDSL2  board for MA5662(SD5103).
                    Modify: fnameMA5653H831Mabc to fnameMA5661H831Mabc.
                    Modify: bnameH832PAIA to bnameH831PAIC.
                    "

        --  Revision history
        REVISION    "201108250000Z"
        DESCRIPTION "V4.63,
                    Add: frameH612MainHABA(196615),      -- Rear-access PVM high-density master Frame, with the H612HABA backplane.
                    Add: frameH612SlaveHABA(196616),     -- Rear-access PVM high-density slave Frame, with the H612HABA backplane.
                    Add: bnameH612HWCB(262216),          -- H612HWCB board.
                    Add: bnameH612HWTB(262217),          -- H612HWTB board.
                    Add: bnameH612PVMD(262218),          -- H612PVMD main board.
                    "

        --  Revision history
        REVISION    "201108080000Z"
        DESCRIPTION "V4.62,
                    Add: frameH612SlaveHABD(196611),     -- Front-access PVM high-density slave Frame, with the H612HABD backplane.
                    Add: frameH612MainHABT(196612),      -- Front-access PVM high-density master Frame, with the H612HABD backplane.
                    Add: frameH612SlaveHABT(196613),     -- Front-access PVM high-density slave Frame, with the H612HABD backplane.
                    Add: frameH612SlaveHABT1(196614),    -- Front-access PVM high-density slave Frame, with the H612HABE backplane.
                    Add: bnameH612PVMT(262214),          -- H612PVMT board.
                    Add: bnameGIU(262215),               -- GIU board(H612IPMD).
                    "

        --  Revision history
        REVISION    "201107040000Z"
        DESCRIPTION "V4.61,
                    Add: fnameMA5631SH821Mabc(561176),  -- Virtual Backplane of MA5631(2 IN 2 OUT) Spec master Frame:H821MABC.
                    "

        --  Revision history
        REVISION    "201107010000Z"
        DESCRIPTION "V4.60,
                    Add: fnameMA5632H821Mabc(561173),   -- Virtual frame H821MABC of 5632 device.
                    Add: fnameMA5653H831Mabc(561174),   -- Virtual Frame H821MABC of 5653 device.
                    Add: fnameMA5612AH831MABL(561175),  -- Frame H831MABL of 5612A device.
                    Add: bnameH822CCJS(155817),         -- Master board of MA5632 Box type device.
                    Add: bnameH832PAIA(155818),         -- Power board H832PAIA of the MA5616.
                    Add: bnameH83BVDLE(155819),         -- 32-port VDSL interface board.
                    Add: bnameH836ADPE(155820),         -- 64-port ADSL2 interface board.
                    Add: bnameH82BCVRJ(155821),         -- Master board of MA5653 Box type device.
                    Add: bnameHS2CCVPE(155822),         -- 64 VDSL+64 POTS combo board of MA5653.
                    Add: bnameH821PTBA(155823),         -- Power board H821PTBA of the MA5653
                    Add: bnameHS21WF1A(155824),         -- WIFI board HS21WF1A of the MA5653.
                    "

        --  Revision history
        REVISION    "201106130000Z"
        DESCRIPTION "V4.59,
                    Change: eponOltPor to eponOltPort,
                    "

        --  Revision history
        REVISION    "201106070000Z"
        DESCRIPTION "V4.58, Add a new menu vdslPstnPort(701) of HWPortType
                    "
        REVISION    "201105030000Z"
        DESCRIPTION "V4.57,
                    Add: bnameH85BCVME(146070),    --48-channel VDSL2+ and POTS(combo) service board
                    Add: bnameH801VRGA(146071),    --Virtual Route Gateway Board
                    Add: bnameH806EPBD(146072),    --8EPON board
                    "

        REVISION    "201103010000Z"
        DESCRIPTION "V4.56,
                    Add: bnameH805EPBD(146086),    --8EPON board
                    "

        --  Revision history
        REVISION    "201102220000Z"
        DESCRIPTION "V4.55, The following boards are modified, and the fname of fnameMA5628OSH821Mabc(561172) is added.
                    bnameHS22GRVD(155810),  -- 8  VDSL2 + over POTS + RF board.
                    fnameMA5628OSH821Mabc(561172),    -- Backplane of MA5628O Spec master Frame:H821MABC
                    "
        --  Revision history
        REVISION    "201101270000Z"
        DESCRIPTION "V4.54, The following boards are modified.
                    serialSrvPort(799),              -- serial service port
                    fnameMA5626H821Mabc(143368),  -- Virtual Backplane of MA5626(Reduce Cost) Spec master Frame:H821MABC
                    "
        --  Revision history
        REVISION    "201101260000Z"
        DESCRIPTION "V4.53,
                    Change: bnameH80BVDPM to bnameH80XVDP,
                    Change: bnameH801ASPB to bnameH80XASP,
                    Delete: bnameH80BVDPE,
                    Add: bnameH805GPBD(146085),    -- 8GPON board
                    "

        --  Revision history
        REVISION    "201101140000Z"
        DESCRIPTION "V4.52, The following boards are modified.
                    bnameH831CCUC(155703),        -- Master board of MA5616(SD5103) Box type device
                    bnameH831CCUN(155716),        -- Master board of MA5631(SD5103) Box type device
                    "

         --  Revision history

        REVISION    "201101110000Z"
        DESCRIPTION "V4.51, The board of bnameH822CCGJA(155718) is added and changed."

        --  Revision history
        REVISION    "201012280000Z"
        DESCRIPTION "V4.50, The following boards are added.
                    bnameH803TPBA(146083),        -- 2-port 10G EPON interface board
                    bnameH803TPBC(146084),        -- 4-port 10G EPON interface board
                    "

        --  Revision history
        REVISION    "201012130000Z"
        DESCRIPTION "V4.49, The board of bnameH822CCGJA(155713) is added."

        REVISION    "201011260000Z"
        DESCRIPTION "V4.48, The following boards and subboard are added for MA5652 & MA5622 & MA5621 & MA5612 & MA5616 device:
                    fnameMA5622SH831Mabc(561169),  -- Backplane of MA5622 Spec master Frame:H831MABC.
                    fnameMA5652SH831Mabc(561170),  -- Backplane of MA5652 Spec master Frame:H831MABC.
                    fnameMA5621H831Mabc(561171),   -- Backplane of MA5621 Spec master Frame:H831MABC.
                    bnameH832PDIA(155803),  -- 2 DC input power board of MA5616
                    bnameH822EPUC(155804),  -- Master board of MA5622 Box type device.
                    bnameH828ASNB(155805),  -- 16-channel POTS board of MA5622.
                    bnameHS25VDUE(155806),  -- 16-channel vdsl2 board of MA5622.
                    bnameH832EPUA(155807),  -- Master board of MA5652 Box type device.
                    bnameHS22VDRE(155808),  -- 24 VDSL2 + over POTS board.
                    bnameHS22VDGE(155809),  -- 16 VDSL2 + over POTS board.
                    bnameHS22VDJE(155810),  -- 8  VDSL2 + over POTS board.
                    bnameHS22VDOE(155811),  -- 24 VDSL2 + over ISDN board.
                    bnameHS22VDHE(155812),  -- 16 VDSL2 + over ISDN board.
                    bnameHS22VDKE(155813),  -- 8  VDSL2 + over ISDN board.
                    bnameH822CCIQ(155814),  -- Master board of MA5621 Box type device.
                    bnameH821EPFF(155815),  -- 4-channel GE board of MA5621.
                    bnameH821COME(155816),  -- 4-channel Serial board of MA5621.
                    subbnameH832TP2C(155663),  --10G EPON subboard.
                    subbnameH832TP2D(155664),  --10G EPON subboard.
                    "

        REVISION    "201011150000Z"
        DESCRIPTION "V4.47, The following boards are added.
                    bnameH80BCAME(146069),        -- 48-channel ADSL2+ and POTS(combo) service board
                    bnameH80BVDPM(146066),        -- 64-channel VDSL2 over POTS service board
                    bnameH80BVDPE(146067),        -- 64-channel VDSL2 service board
                    bnameH801PAIC(146082),        -- H801PAIC Power board.
                    Modified the description of hwTrapType."

        REVISION    "201009290000Z"
        DESCRIPTION "V4.46, The following boards are added:
                    Add 48L VDSL board of MA5616:bnameH83BVDMM(155802)
                    "

        REVISION    "201009250000Z"
        DESCRIPTION "V4.45, The following boards are added:
                    Add 24L VDSL board of MA5616:bnameH83BVDSB(155800)
                    Add 24L POTS board of MA5612:bnameH837ASMB(155801)
                    "

        REVISION    "201009010000Z"
        DESCRIPTION "V4.44, modified the description of the objects in this MIB file for standard trap."

        REVISION    "201008110000Z"
        DESCRIPTION "V4.43, The following value are added for the MxU MA5631 device:
                    fnameMA5631SH821Mabc(561168), -- Virtual Backplane of MA5631(SD5103) Spec master Frame:H821MABC
                    bnameH832CCUC(155716),        -- Master board of MA5631(SD5103) Box type device
                    bnameH831HE1A(155717),        -- 1 port EoC board of MA5631(SD5103)
                    subbnameH831UP2D(155661),   -- Auto adapt upstream subboard, which is used for the MA5631(SD5103) upstream service
                    eocport(803),                 -- EoC master RF port
                    "

        REVISION    "201007300000Z"
        DESCRIPTION "V4.42, The following SubBoard is added for the MxU MA5616 device:
                    subbnameH836ASDM(155662),          --VOIP 128 Tunnel DSP Subboard H836ASDM
                    "

        REVISION    "201007150000Z"
        DESCRIPTION "V4.41, The following shelves, boards are added and changed.
                    Add 24L VDSL2(IFX,17a),GPON(RF) ,Over POTS service board of MA5652:bnameH821GRVAA(155713)
                    Change 24L VDSL2(IFX,17a),GPON(RF) ,Over POTS service board of MA5652:bnameH821GRVAB(155715)"

        REVISION    "201007080000Z"
        DESCRIPTION "V4.40, The following Backplane is added for the SCU 300mm Frame:
                    fnameMA5600H801Mabv(143359),     -- Backplane(19 Inch) of the P300 new broadband master Frame: H801MABV"

        REVISION    "201006170000Z"
        DESCRIPTION "V4.39, Modify the Chinese characters in Mib files."

        REVISION    "201006010000Z"
        DESCRIPTION "V4.38, The following shelves, boards are added.
                    Add 24L VDSL2(IFX,17a),GPON(RF) ,Over POTS service board of MA5652:bnameH821GRVA(155713)
                    Add 64-channel VoIP POTS service board of MA5616: bnameASP(155714)"

        REVISION    "201005150000Z"
        DESCRIPTION "V4.37, Add Virtual Backplane of MA5628(SD5103) Spec master Frame: fnameMA5628SH821Mabc,
                    Add Master board of MA5628(SD5103) Box type device: bnameH822CCGJ,
                    Add 4E1 Vitual board of H822CCGJ: bnameH831EDVB."

        REVISION    "201004280000Z"
        DESCRIPTION "V4.36, The following shelves, boards are added.
                    fnameSRGFWG2BKPA(190001),       -- SRG master Frame: FWG2BKPA(R2 1U)
                    fnameSRGSU11BKPA(190002),       -- SRG master Frame: SU11BKPA(R2 2U)
                    fnameSRGSU21BKPA(190003),       -- SRG master Frame: SU21BKPA(R2 3U)
                    bnameSU11EWFS(190012),          -- 32-pots fxs board
                    bnameSU11E4MS(190013),          -- 4-pots fxs board
                    bnameSU11E4MO(190014),          -- 4-pots fxo board
                    bnameSU11E4MM(190015),          -- 2-pots fxs + 2-pots fxo board
                    bnameSU11E2MV(190016),          -- 2-pots ve1 board
                    bnameSU11UP2A(190017),          -- PON board(3 mode)"

        REVISION    "201004230000Z"
        DESCRIPTION "V4.35, The following shelves, boards, subboard are added.
                    fnameWLANWS6603(160000): Backplane of the WLAN V1R2 master Frame: WS6603.
                    fnameWLANWAC(160001): Backplane of the WLAN V1R3 master Frame: WAC.
                    bnameWA611WACA(160000): Master board of WS6603(WLAN V1R2) Box type device.
                    bnameWA611PAIA(160001): power board of WS6603(WLAN V1R2) Box type device.
                    bnameWA611PDIA(160002): power board of WS6603(WLAN V1R2) Box type device.
                    bnameH801WACA(160003): AC service Board of WS6800/WS6803(WLAN V1R3).
                    subbnameWA611POEA(160000): Power Subboard of WA611WACA."

        REVISION    "201004090000Z"
        DESCRIPTION "V4.34, The board of bnameH802P2CA(146065) is added."

        REVISION    "201003260000Z"
        DESCRIPTION "V4.33, Modified the revision."

        REVISION    "201003230000Z"
        DESCRIPTION "V4.32, DT requirements are implemented and the syntax and semantics of SIMPLETEST are changed."

        REVISION    "201003090000Z"
        DESCRIPTION "V4.31, The following boards are added.
                    bnameE8000ESUP3SPUA02IPS(16748548):IPS Service Processing Unit,
                    with HS General Security Platform S
                    bnameE8000EKW51ESPUIPS(16748549): IPS SPU Board ,Service Processing Unit
                    subbnameUSG9100E2XS(16748570): 2*SFP+ Interface Broad,
                    with HS General Security Platform Software
                    subbnameUSG9100E16GF(16748571): 16*SFP Interface Board,
                    with HS General Security Platform Software."

        REVISION    "201003020000Z"
        DESCRIPTION "V4.30, The board of bnameH821EPFE(155709) is added."

        REVISION    "201002220000Z"
        DESCRIPTION "V4.29, The enumerated value of H802EDTB is added."

        REVISION    "201002110000Z"
        DESCRIPTION "V4.28, The NMS enumerated value of H85BVDMD is added and revision description is added."

        REVISION    "201001290000Z"
        DESCRIPTION "V4.27, 1 The syntax of SIMPLETEST MIB BROWSER is changed.
                     2 The MIB description is changed."

        REVISION    "201001260000Z"
        DESCRIPTION "V4.26, One board is added for the SVN5300.
                    bnameSE21MPUA(16719954): SVN5300,Security virtual Gateway Mainboard(4GE). "

        REVISION    "201001120000Z"
        DESCRIPTION "V4.25, Two types for daughter board subbnameH801CKMA are recorded in MIB files.
                    One enumerated value is 145935 and another enumerated value is 146020.
                    The two values, however, refers to the same daughter board, and enumerated
                    value 145935 is used in codes. Therefore, enumeration definition of value 146020 is deleted."

        REVISION    "200912170000Z"
        DESCRIPTION "V4.24,The following shelves are added.
                    fnameSRGZ23UHT(16715796):SRG3260,SRGZ23UHT,SRG3260 Host,
                    with HS General Security Platform Software.
                    fnameSU2Z12UAH(16715797):USG5100,SU2Z12UAH,USG5120 AC Host,
                    with HS General Security Platform Software.
                    fnameSU2Z12UDH(16715798): USG5100,SU2Z12UDH,USG5120 DC Host,
                    with HS General Security Platform Software.
                    fnameSU2Z13UHT(16715799):USG5100,SU2Z13UHT,USG5150 Host,
                    with HS General Security Platform Software.
                    fnameSU2Z22UAH(16715800):USG5100,SU2Z22UAH,USG5120BSR AC Host,
                    with HS General Security Platform Software.
                    fnameSU2Z22UDH(16715801): USG5100,SU2Z22UDH,USG5120BSR DC Host,
                    with HS General Security Platform Software.
                    fnameSU2Z23UHT(16715802): USG5100,SU2Z23UHT,USG5150BSR Host,
                    with HS General Security Platform Software.
                    fnameSRGZ12UAH(16715803):SRG3230,SRGZ12UAH,SRG3230 AC Host,
                    with HS General Security Platform Software.
                    fnameSRGZ22UAH(16715804):SRG3240,SRGZ22UAH,SRG3240 AC Host,
                    with HS General Security Platform Software.
                    fnameSRGZ22UDH(16715805): SRG3240,SRGZ22UDH,SRG3240 DC Host,
                    with HS General Security Platform Software.
                    fnameSRGZ13UHT(16715806): SRG3250,SRGZ13UHT,SRG3250 Host,
                    with HS General Security Platform Software."

        REVISION    "200912080000Z"
        DESCRIPTION "V4.23, Daughter board H801M2XA(146025) is added."

        REVISION    "200912040000Z"
        DESCRIPTION "V4.22,The following boards are added.
                    bnameSRGM1WCDMA(16719917): SRG,SRGM1WCDMA,USB 3G WCDMA Card.
                    bnameSRGM1CD2K(16719918): SRG,SRGM1CD2K,USB 3G CDMA2000.
                    bnameSRGM1TD(16719919): SRG,SRGM1TD,USB 3G TDSCDMA.
                    bnameSU11X86HS02(16719920): Safety Product,USG2200,SU11X86HS02,
                    Enhanced Services Platform Enterprise Version,X86 Board,CPU T7500,
                    2GB Memory,160G Enterprise Hard Disk.
                    bnameSU11X86HS01(16719921): Safety Product,USG2200,SU11X86HS01,
                    Enhanced Services Platform Common Version,X86 Board,CPU T7500,
                    2GB Memory,160G Universal Hard Disk."

        REVISION    "200911250000Z"
        DESCRIPTION "V4.21,The following boards are added for the USG2200 V3R2.
                    bnameSU11F8E1(16719905): SRG20,SU11F8E1,8-port E1 Interface Card-DB44-75ohm.
                    bnameSU11FC8E1(16719906): SRG20,SU11FC8E1,8-port Channelized E1 Interface Card-DB44-75ohm.
                    bnameSU11F4E1(16719907): SRG20,SU11F4E1,4-port E1 Interface Card-DB44-75ohm.
                    bnameSU11FC4E1(16719908): SRG20,SU11FC4E1,4-port Channelized E1 Interface Card-DB44-75ohm.
                    bnameSU11APWN(16719909): SRG20,SU11APWN,WLAN Service Board.
                    bnameSU21MPUA(16719910): USG5100,SU21MPUA,Main Process Unit Board .
                    bnameSU11MPUA(16719911): USG5100,SU11MPUA,Main Process Unit Board .
                    bnameFWE1E4GE(16719912): USG5100,FWE1E4GE,4-port Gigabit Ethernet Interface Card(RJ45).
                    bnameFWG1F2F2C(16719913): USG2200,FWG1F2F2C,2FE(RJ45)+2FE(RJ45&SFP) MIXED INTERFACE CARD.
                    bnameSU21F18S2(16719914): USG5100,SU21F18S2,18FE(RJ45)+2GE(SFP) Mixed Interface Card.
                    bnameSU21G16S4(16719915): USG5100,SU21G16S4,16GE(RJ45)+4GE(SFP) Mixed Interface Card.
                    bnameSU11E8F2G(16719916): SRG20,SU11E8F2G,8FE(RJ45)+2GE(RJ45) Mixed Interface Card."

        REVISION    "200911190000Z"
        DESCRIPTION "V4.20, The boards of the following two types are added for the USG2100.
                    bnameFWF1MPUCO1(16719903),bnameSU11ADPAO2(16719904),
                    The boards of the following four types are added for the USG3000.
                    bnameRTB21CT1(16719950),bnameRRTB21CE1(16719951),bnameRTB21T1(16719952),
                    bnameRTB21E1(16719953).
                    The daughter board of the following type is added for the TUSG9100.
                    subbnameUSG9100SU61X2G16(16748569).
                    The following port is added for the USG3000.T1(16711685)."

        REVISION    "200911170000Z"
        DESCRIPTION "V4.19, Many MIB compilation problems are found in DT tests.
                    These compilation problems are solved and MIBs are archived."

        REVISION    "200911110000Z"
        DESCRIPTION "V4.18, MIB enumerated values are added for the 562x, the 5612,
                    and the 5616 that are in SD5103 architecture.
                    The following boards are added.
                    bnameH822EPUB(155702): Master board of MA562X(SD5103) Box type device.
                    bnameH832CCUB(155703): Master board of MA5616(SD5103) Box type device.
                    bnameH832CCFE(155704): Master board of MA5612(SD5103) Box type device.
                    bnameH835CALE(155705): 32 ADSL+32 POTS combo board .
                    bnameH831EIUD(155706): 4GE(combo)+4FE board.
                    bnameH831E81A(155707): 8E1 board.
                    bnameH831EPWA(155708): POE board.
                    The following shelves are added.
                    fnameMA562XSH821Mabc(561164): Virtual Backplane of MA562X(SD5103) Spec master Frame H821MABC.
                    fnameMA5616SH831MABA(561165): Backplane of the MA5616(SD5103) master Frame  H831MABA.
                    fnameMA5612SH831MABL(561166): Backplane of the MA5612(SD5103) master Frame  H831MABL.
                    The following daughter boards are added:
                    subbnameH831UP2A(155658)L: Auto adapt upstream subboard, which is used for the MDU upstream service.
                    subbnameH831UP2C(155659): Auto adapt upstream subboard with Clock, which is used for the MDU upstream service.
                    subbnameH831GR1A(155660): RF upstream subboard, which is used for the MDU upstream service.
                    The following ports are added.
                    autoAdptPort(800): auto adpt port.
                    catvPort(801): CATV port.
                    In addition, MIB compilation of version 4.17 fails; 3G in version 4.18 is changed to _3G."

        REVISION    "200910300000Z"
        DESCRIPTION "V4.17, VEPort(16711681): The Virtual Ethernet (VE) is applied to the PPPoEoA and IPoEoA.
                    It functions on the interface board. Externally it features Ethernet attributes.
                    3GPort(16711682):3G supports three wireless communication mode,
                    including both WCDMA/CDMA2000/TD-SCDMA and corresponding 2G mode.
                    SerialPort(16711683): The serial port is used for the exchange of information between computers
                    or devices one bit at a time over a single channel. Serial communications can be synchronous
                    or asynchronous. Both sender and receiver must use the same baud rate, parity, and control information.
                    DialerPort(16711684):The dialer interface is used as dialing interface of pppoe client, supports pppoe protocol."

        REVISION    "200910290000Z"
        DESCRIPTION "V4.16, The NMS enumerated value of H802OPGD needs to be added for the MA5600V8R8."

        REVISION    "200910280000Z"
        DESCRIPTION "V4.15, The NMS enumerated value of H801CKMC and the enumerated value of H808ASPB.
                    are added for V8R7.
                    bnameH808ASPB(146081): H808ASPB BOARD 64-channel voice service board of the MA5600.
                    subbnameH801CKMC(146024):Clock subboard for the H801SCUL and H801SCUN board."

        REVISION    "200910270000Z"
        DESCRIPTION "V4.14, The following shelf, control board, ADSL board and power board are added for the ATN931.
                    fnameATN931TNC1AFB(561163): Backplane of the ATN931 master Frame: TNC1AFB.
                    bnameH831CCEL(155699): Master board of ATN931 Box type device.
                    bnameH835BVJA(155700): adsl board of ATN931 Box type device.
                    bnameTNC1PIU(155701): power board of ATN931 Box type device."

        REVISION    "200910160000Z"
        DESCRIPTION "V4.13,The following boards are added for the USG2100.
                    bnameFWF1SPUA(16719900):FWF1SPUA,Main Process Unit Board,USG2100.
                    bnameFWF1SPUB(16719901):FWF1SPUB,Main Process Unit Board,USG2100.
                    bnameFWF1MPUD(16719902):FWF1MPUD,Main Process Unit Board,USG2100."

        REVISION    "200910130000Z"
        DESCRIPTION "V4.12,  USG2200,USG2100
                    wifi(233):WIFI card communicates with WIFI terminals as a wireless AP,
                    and supports IEEE 802.11b/ 802.11g."

        REVISION    "200910120000Z"
        DESCRIPTION "V4.11, 1.Mother board H831CCIK is added because the MXU ATN930 is independent of the OT920.
                    The NMS enumerated value corresponding to the mother board needs to be applied for.
                    Apply for the NMS enumerated value:
                    bnameH831CCIK(155698):Master board of ATN930 Box type device.
                    2. The 5620 supports 8 FE + 8 POTS mother board. The name of the virtual 8 POTS board
                    is changed from H822ASL to H848ASLB according to naming rules.
                    The NMS enumerated value (155697) that is applied for is not changed.
                    bnameH848ASLB(155697): MA562XP 8POTS."

        REVISION    "200306280000Z"
        DESCRIPTION "V1.00, Complete the Draft."
            ::= { huawei 20021210 }

        HWErrorCode ::= TEXTUAL-CONVENTION
            STATUS deprecated
            DESCRIPTION
                "This object is not used any longer.SNMP expand Error code defintion."
            SYNTAX Integer32

        HWFrameType ::= TEXTUAL-CONVENTION
            STATUS current
            DESCRIPTION
                "This data type is used as the syntax of the
                hwframeType object in the definition of
                HUAWEI-DEVICE-MIBs hwframeTable.

                The definition of this textual convention with the
                addition of newly assigned values is published
                periodically by the Huawei MIB Criterion Group, every
                value indicate a frame produced by Huawei.
                  "
            SYNTAX INTEGER
                {
                fnameUnknow(1),
-- MD5500:
                fnameMd16(2),                   -- MD 16 Slot Frame
                fnameMd8(3),                    -- MD 8  Slot Frame
                fnameMd4(4),                    -- MD 4  Slot Frame
                fnameMa16(5),                   -- MA 16 Slot Frame
                fnameMa8(6),                    -- MA 8  Slot Frame
                fnameMa4(7),                    -- MA 4  Slot Frame
                fnameSmx16(8),                  -- MA 16 Slot Slave Frame
                fnameRsa(9),                    -- RSA Frame
                fnameRsp19(10),                 -- RSP 19 Slot Frame
                fnameRsp15(11),                 -- RSP 15 Slot Frame
                fnameRsp14(12),                 -- RSP 14 Slot Frame
                fnameRsp12(13),                 -- RSP 12 Slot Frame
                fnameRsp10(14),                 -- RSP 10 Slot Frame
                fnameRsp6A(15),                 -- RSP 6  Slot A Type Frame
                fnameRsp6B(16),                 -- RSP 6  Slot B Type Frame
                fnamePv819(17),                 -- PV8 19 Slot Frame
                fnamePv815(18),                 -- PV8 15 Slot Frame
                fnamePv814(19),                 -- PV8 14 Slot Frame
                fnamePv812(20),                 -- PV8 12 Slot Frame
                fnamePv810(21),                 -- PV8 10 Slot Frame
                fnamePv86A(22),                 -- PV8 6 Slot A Type Frame
                fnamePv86B(23),                 --PV8 6 Slot B Type Frame
-- New UA3000 Frame
                fnameHubm(24),                  -- Rear-access master Frame of the HONET
                fnameHube(25),                  -- Front-access master Frame of the HONET
                fnameHubf(26),                  -- Front-access slave Frame of the HONET
-- New MD5500 Frame that supports the UA management
                fnameUamr(27),                  -- UA R Frame, with an HUBM backplane
                fnameUasr(28),                  -- UA R Frame, with an HUBS backplane
                fnameUafmr(29),                 -- UA R Frame, with an HUBE backplane
                fnameUafsr(30),                 -- UA R Frame, with an HUBF backplane
                fnameUamv(31),                  -- UA V Frame, with an HUBM backplane
                fnameUasv(32),                  -- UA V Frame, with an HUBS backplane
                fnameUafmv(33),                 -- UA V Frame, with an HUBE backplane
                fnameUafsv(34),                 -- UA V Frame, with an HUBF backplane
                fnameUabmr(35),                 -- UA R Frame, with an HUBB backplane
                fnameOnu60ar(36),               -- UA R Frame, with an HUBO backplane
                fnameOnuf01D100r(37),           -- UA R Frame, with an HUBL backplane
                fnameUabmv(38),                 -- UA V Frame, with an HUBB backplane
                fnameOnu60av(39),               -- UA V Frame, with an HUBO backplane
                fnameOnuf01D100v(40),           -- UA V Frame, with an HUBL backplane
                fnameHubs(41),                  -- UA broadband service Frame, with an HUBS backplane
                fnameHubb(42),                  -- UA broadband service Frame, with an HUBB backplane
                fnameHubl(43),                  -- UA broadband service Frame, with an HUBL backplane
                fnameMa7(44),                   -- MA5103 master Frame that provides seven slots
                fnameSmxMa4(45),                -- MA5103 slave Frame that provides four slots
                fnameSmxMa7(46),                -- MA5103 slave Frame that provides seven slots
                fnameMdb16(47),                 -- Large-capacity backplane of the MD5500
-- Uniformed Frame of the Musa:
                fnameMusa(50),
-- MA5200:
                fnameMusa5200E(51),             -- The MA5200E is a box-shaped device of 1 U height.
                fnameMusa5200F(52),             -- The MA5200F is a box-shaped device of 2 U height.
-- AG:
                fnamePvm10(60),
                fnamePvm6B(61),
                fnamePvm6A(62),                 -- AG's 160A master Frame, with an HMB backplane
                fnamePvmUam(63),                -- AG's maser Frame, with an HUBM backplane. The PVM board is inserted in the UAM Frame.
                fnamePvmUafm(64),               -- AG's mater Frame, with an HUBE backplane. The PVM board is inserted in the UAFM Frame.
                fnamePvmUafs(65),               -- AG's mater Frame, with an HUBF backplane. The PVM board is inserted in the UAFS Frame.
                fnamePvmUas(66),                -- AG's master Frame, with an HUBS backplane. The PVM board is inserted in the UAS Frame.
                fnamePvmUamb(67),               -- AG's mater Frame, with an HUBB backplane. The PVM board is inserted in the UAMB Frame.
                fnamePvmOnuf01D100(68),         -- AG's master Frame, with an HUBL backplane. The PVM board is inserted in the ONUF01D100 Frame.
                fnameOnu04(262176),             -- ONU04 Frame with remote power supply
                fnameOnu08(262177),             -- ONU08 Frame with remote power supply
-- A8010:
                fnameA8010U18(70),              -- A8010 integrated cabinet of 18 U height
                fnameA8010U5(71),               -- A8010 small-capacity integrated cabinet of 5 U height
-- MA5105:
                fnameMA5105(80),                -- MA5105
                fnameBSL(81) ,                  -- BSL
                fnameB08(82),                   -- B08
-- MA5300:
                fnameMA5306(83),                -- The MA5306 provides 13 horizontal slots and two power modules. Its BOM is 02000204.
                fnameMA5300(84),                -- The MA5300 provides 16 vertical front slots, 16 vertical rear slots, and three power modules.
                fnameS3026V(85),                -- Box-shaped S3026V Frame

                fnameOnuf01D100H602Hublr(86),   -- RSP slave Frame, with an H602HUBL backplane
                fnameOnuf01D100H602Hublv(87),   -- PV8 slave Frame, with an H602HUBL backplane
                fnameAmgH602Hubl(88),           -- AMG's mater Frame, with an H602HUBL backplane
                fnameUaH602Hubl(89),            -- UA master Frame, with an H602HUBL backplane
                fnameHaba(90),                  -- Backplane of the UA rear-access high-density splitter mater Frame
                fnameHabb(91),                  -- Backplane of the UA rear-access high-density integrated mater Frame
                fnameHabd(92),                  -- Backplane of the UA front-access high-density splitter master Frame
                fnameHabe(93),                  -- Backplane of the UA front-access high-density integrated master Frame
                fnameHabl(94),                  -- UA front-access, high-density, small-capacity, and outdoor backplane
                fnameHabt(95),                  -- UABT backplane
                fnameApsbHabe(96),              -- UA front-access high-density integrated control Frame backplane, with the APSB board, as the slave Frame
                fnameApsrHabe(97),              -- UA front-access high-density integrated control Frame backplane, with the APSR board, as the slave Frame
-- 8040:
                fname1760(100),                 -- Quidway R1760 FRAME, 1 MIM slot and 2 SIC slot
                fname2610(101),                 -- Quidway R2610 FRAME, 1 MIM slot and 2 SIC slot
                fname2611(102),                 -- Quidway R2611 FRAME, 1 MIM slot and 2 SIC slot
                fname2620(103),                 -- Quidway R2620 FRAME, 2 MIM slot
                fname2621(104),                 -- Quidway R2621 FRAME, 2 MIM slot
                fname2630(105),                 -- Quidway R2630 FRAME, 3 MIM slot
                fname2631(106),                 -- Quidway R2631 FRAME, 3 MIM slot
                fname3640(107),                 -- Quidway R3640 FRAME, 4 MIM slot
                fname3680(108),                 -- Quidway R3680 FRAME, 8 MIM slot
-- 8060:
                fname4620(120),                 -- Quidway R4620 FRAME, 1RPU+2IfCard+2PWR+1FAN
                fname4640(121),                 -- Quidway R4640 FRAME, 1RPU+4IfCard+2PWR+1FAN
                fname4680(122),                 -- Quidway R4680 FRAME, 1RPU+8IfCard+1NPU+2PWR+1FAN
                fnameNE20-2(123),               -- Quidway NE20-2 FRAME, 1RPU+2IfCard+1NPU+2PWR+1FAN
                fnameNE20-4(124),               -- Quidway NE20-4 FRAME, 1RPU+4IfCard+1NPU+2PWR+1FAN
                fnameNE20-8(125),               -- Quidway NE20-8 FRAME, 1RPU+8IfCard+1NPU+2PWR+1FAN
                fnameNE20E-4(126),              -- Quidway NE20E-4 FRAME, 2RPU+4IfCard+2NPU+2PWR+1FAN+2COP
                fnameNE20E-8(127),              -- Quidway NE20E-8 FRAME, 2RPU+8IfCard+2NPU+2PWR+1FAN+2COP
-- 8070:
                fnameNE05(130),                 -- Quidway NE05 FRAME, 4 VIU Slot, 1 RSU slot
                fnameNE08(131),                 -- Quidway NE08 FRAME, 7 VIU slot, 1 RSU slot
                fnameNE16(132),                 -- Quidway NE16 FRAME, 12 VIU slot, 2 RSU slot
                fnameNE08E(133),                -- Quidway NE08E FRAME, 6 VIU slot, 2 RSU slot
                fnameNE16E(134),                -- Quidway NE16E FRAME, 12 VIU slot, 2 RSU slot
-- 8011:
                fnameNE80(140),                 -- Quidway NE80 FRAME,
                fnameNE40-8(141),               -- Quidway NE40-8 FRAME,
                fnameNE40-4(142),               -- Quidway NE40-4 FRAME,
                fnameNE40-2(143),               -- Quidway NE40-2 FRAME,
-- MA
                fnameMA5600H511upba(800),       -- The MA5600's H511UPBA backplane, with double CELLBUS and GE bus
                fnameMa5600MA5100(801),         -- The MA5600's MA5100 backplane, on which the SCUA control board is inserted
                fnameMa5600MA5103(802),         -- The MA5600's MA5103 backplane, on which the SCUA control board is inserted
                fnameMa5600MA5106(803),         -- The MA5600's MA5106 backplane, on which the SCUA control board is inserted
                fnameMa5600MA5603(804),         -- The MA5600's MA5603 backplane, on which the SCU control board is inserted
-- PVU mater Frame
                fnamePvuMainHaba(900),          -- Rear-access PVU high density master Frame, with the H601HABA backplane
                fnamePvuMainHabb(901),          -- Rear-access PVU high-density master Frame, with the H601HABB backplane
                fnamePvuMainH601Habd(902),       -- Front-access PVU high-density master Frame, with the H601HABD backplane
                fnamePvuMainHabe(903),          -- Front-access PVU high-density master Frame, with the H601HABE backplane
                fnamePvuMainHabl(904),          -- Front-access PVU high-density master Frame, with the H601HABL backplane

-- PVM mater Frame
                fnamePvmMainHaba(1000),         -- Rear-access PVM high-density master Frame, with the H601HABA backplane
                fnamePvmMainHabb(1001),         -- Rear-access PVM high-density master Frame, with the H601HABB backplane
                fnamePvmMainHabd(1002),         -- Front-access PVM high-density master Frame, with the H601HABD backplane
                fnamePvmMainHabe(1003),         -- Front-access PVM high-density master Frame, with the H601HABE backplane
                fnamePvmMainHabl(1004),         -- Front-access PVM high-density master Frame, with the H601HABL backplane
                fnamePvuMainHabt(1005),         -- BT HUBT Frame

                frameH612MainHaba(1006),        -- Rear-access PVM high-density master Frame, with the H612HABA backplane
                frameH612SlaveHABB(1007),       -- Rear-access PVM high-density integrated slave Frame, with the H612HABB backplane
                frameH612MainHABD(1008),        -- Front-access PVM high-density master Frame, with the H612HABD backplane
                frameH612SlaveHabe(1009),       -- Front-access PVM high-density integrated slave Frame, with the H612HABE backplane
                frameH612MainHabl(1010),        -- Front-access PVM high-density master Frame, with the H612HABL backplane
                frameH601MainHabm(1011),        -- Front-access PVM high-density master Frame, with the H601HABM backplane
                frameH601MainHabo(1012),        -- Front-access PVM high-density master Frame, with the H601HABO backplane
                frameH602MainHABD(196608),      -- Front-access PVM high-density master Frame, with the H612HABD backplane
                frameH602SlaveHABE(196609),     -- Front-access PVM high-density master Frame, with the H612HABE backplane
                frameH602SlaveHABD(196610),     -- Front-access PVM high-density master Frame, with the H612HABD backplane
                frameH612SlaveHABD(196611),     -- Front-access PVM high-density slave Frame, with the H612HABD backplane
                frameH612MainHABT(196612),      -- Front-access PVM high-density master Frame, with the H612HABD backplane
                frameH612SlaveHABT(196613),     -- Front-access PVM high-density slave Frame, with the H612HABD backplane
                frameH612SlaveHABT1(196614),    -- Front-access PVM high-density slave Frame, with the H612HABE backplane
                frameH612MainHABA(196615),      -- Rear-access PVM high-density master Frame, with the H612HABA backplane
                frameH612SlaveHABA(196616),     -- Rear-access PVM high-density slave Frame, with the H612HABA backplane



-- Narrowband slave shelves without the control board
                fnamePvuSlaveHabb(1500),        -- Rear-access PVU high-density slave Frame, with the H601HABB backplane and without the master node board
                fnamePvuSlaveH601Habe(1501),        -- Front-access PVU high-density slave Frame, with the H601HABE backplane and without the master node board
                fnamePvuSlaveHaba(1502),        -- Rear-access PVU high-density slave Frame, with the H601HABA backplane and without the master node board
                fnamePvuSlaveH601Habd(1503),        -- Front-access PVU high-density slave Frame, with the H601HABD backplane and without the master node board
-- RSUA slave shelves that the MD subtends
                fnameRsuSlaveHaba(1600),             --Rear-access PVM high-density master Frame, with the H601HABA backplane
                fnameRsuSlaveH601Habd(1601),             --Front-access PVM high-density master Frame, with the H601HABD backplane
                fnameRsuSlaveHabl(1602),            --Front-access PVM high-density master Frame, with the H601HABL backplane
                fnameRsuSlaveH602Habd(200706),             --Front-access PVM high-density master Frame, with the H602HABD backplane

-- MA5100
                fnameMA5100ecua(131082),           -- The MA5100's MA5100 backplane, on which the ECUA control board is inserted
                fnameMA5103ecua(131083),           -- The MA5100's MA5103 backplane, on which the ECUA control board is inserted
                fnameMA5106ecua(131084),           -- The MA5100's MA5106 backplane, on which the ECUA control board is inserted
-- MA5105
                fnameMa5605(134912)  ,           -- The MA5605, 2 U high

--  MA5200 add definitiong of frame 0x21000(135168) ~ 0x21FFF(139263)
                fnameMA5200G2(135168),             -- Quidway MA5200G-2 FRAME,
                fnameMA5200G4(135169),             -- Quidway MA5200G-4 FRAME,
                fnameMA5200G8(135170),              -- Quidway MA5200G-8 FRAME,

--WA5700:
                fnameWA5700(155648),             -- WA5700 Frame

-- MA5633
                fnameMA5633H821MABCP(561550),    -- Virtual frame H821MABCP of horizontal MA5633(sd5130) device.
                fnameMA5633H821MABCQ(561551),    -- Virtual frame H821MABCQ of vertical MA5633(sd5130) device.
                fnameMA5633H821MABCR(561554),    -- Virtual frame H821MABCR of vertical MA5633(sd5130) device.
                fnameMA5633H821MABCT(561571),    -- R18C00 Virtual frame H821MABCT of   MA5633(sd5130) device
                fnameH821MABCV(561659),          -- Virtual frame H821MABCV of vertical MA5833 device.
                fnameH821MABCU(561660),          -- Virtual frame H821MABCU of vertical MA5833 device.
-- MA5620
                fnameH821MABC-MA5620(561662),  -- Virtual frame H821MABC of MA5620(sd5133) device.

-- MA5626
                fnameMA5626H821MABC(561661),  -- Virtual frame H821MABC of MA5626(sd5133) device.

-- MA5878
                fnameH831MABL-H833CCFE(561555),    --MA5878  new frame  H831MABL.
                fnameH832MABL(561563),             --Virtual frame H832MABL of the MA5878(SD5568) device.

-- MA582X
                fnameH821MABCMA5821GE(561564),     --Virtual frame H821MABC of the MA5821(GE) device.
                fnameH821MABCMA5822GE(561565),     --Virtual frame H821MABC of the MA5822(GE) device.

-- MA582x R019C30
                fnameMA5626HH821Mabc(561669),      -- Virtual frame H821MABC of MA5626H device.
                fnameMA5821SH821Mabc(561670),      -- Virtual frame H821MABC of MA5821S device.
                fnameMA5620HH821Mabc(561671),      -- Virtual frame H821MABC of MA5620H device.
                fnameMA5822SH821Mabc(561672),      -- Virtual frame H821MABC of MA5821S device.
                fnameMA5821SPOEH821Mabc(561673),   -- Virtual frame H821MABC of MA5821S-POE device.
                fnameP815EH821Mabc(561674),        -- Virtual frame H821MABC of P815E device.
                fnameP805EH821Mabc(561675),        -- Virtual frame H821MABC of P805E device.

-- MA5694S
               fnameMA5694SDCH821MABC(561552),  -- Virtual frame H821MABC of MA5694S  PON DOCK  DC device.

-- MA5811S-AE08
               fnameMA5811S-AE08(561553),  --Virtual frame MA5811S-AE08 of MA5811S_AE08 device
               fnameMA5811S-AE48(561566),  --Virtual frame MA5811S-AE48 of MA5811S_AE48 device.
               fnameMA5811S-DE48(561567),  --Virtual frame MA5811S-DE48 of MA5811S_DE48 device.
               fnameMA5811SMA5811SAE08PD(561577),      --Virtual Frame MA5811S-AE08 of the MA5811S-AE08 G.fast pd device.

-- MA5811S-G5
               fnameMA5811S-G5-AE08(561654),  --Virtual frame MA5811S-AE08 of MA5811S_AE08 device.
               fnameMA5811S-G5-DE48(561655),  --Virtual frame MA5811S-DE48 of MA5811S_DE48 device.
	       fnameMA5811S-G5-AE16(561656),  --Virtual frame MA5811S-AE16 of MA5811S_AE16 device.
               fnameMA5811S-G5-DE16(561657),  --Virtual frame MA5811S-DE16 of MA5811S_DE16 device.
               fnameMA5811S-G5-8SV-AE16(561658),  --Virtual frame MA5811S-AE16 of MA5811S_AE16(8SV uplink) device.

-- MA5812S
               fnameMA5812S-G5-AE08(561663),  --Frame MA5812S-AE08 of the MA5812S device.
-- MA5818
               fnameH831MABMMA5818(561568),   --Frame H831MABM of the MA5818 device.

-- MA5621
               fnameMA5621-FE(561569),        --Frame MA5621-FE of the MA5621(sd5130) device(AC).
               fnameMA5621-FE-DC(561572),        --Frame MA5621-FE-DC of the MA5621(sd5130) device(DC).
               fnameMA5621H831MABC-DC(561573),   --Backplane of MA5621(SD5103) Spec master Frame:H831MABC(DC).

-- MA5621H
               fnameMA5621HH831Mabc(561664),  --Frame of the MA5621H device.


-- MA5821
               fnameH821MABCMA5821(561570),   --Virtual frame H821MABC of MA5821(sd5568) device.
               fnameMA5821-24GE-POE(561574),   --Virtual Frame H821MABC of the MA5821 24GE poe device.

-- MA5898
               fnameMA5898H831Mabl-DC(561633),   -- Virtual Frame H831MABL of the MA5898 DC device.

-- MA5821A
               fnameMA5821A-24GE(561578),        -- Virtual Frame H821MABS of the MA5821A-24GE device.

-- MA5626B
               fnameMA5626BH821Mabc(561634),     -- Virtual Frame H821MABC of the MA5626B device.
-- EA5821
               fnameEA5821-GE(561638),	--Virtual frame H821MABC of the EA5821 GE(8/16/24) device.
               fnameEA5821-GE-POE(561639),	--Virtual Frame H821MABC of the EA5821 GE(24) POE device.
-- MA5600
-- SCU 300mm Frame
                fnameMA5600H801Mabv(143359),     -- Backplane(19 Inch) of the P300 new broadband master Frame: H801MABV
                fnameMA5600H801Maba(143360),     -- Backplane of the P300 broadband master Frame: H801MABA
                fnameMA5600H801Spba(143361),     -- Backplane of the P300 broadband SPL Frame: H801SPBA
                fnameMA5600H801Mabh(143362),     -- Backplane(19 Inch) of the P300 new broadband master Frame: H801MABH
                fnameMA5600H801Mabc(145949),     -- Backplane of the P300 broadband master Frame: H801MABC
                fnameMA5600H801Mabd(145950),     -- Backplane of the P300 broadband master Frame: H801MABD
                fnameMA5600H801Mabi(145951),     -- Backplane(19 Inch) of the P300 new broadband master Frame: H801MABI
                fnameMA5600H802Mabc(145952),     -- Backplane of the P300 broadband master Frame: H802MABC
                fnameMA5600H803Mabc(147529),     -- Backplane of the P300 broadband master Frame: H803MABC
                fnameMA5600H802Mabh(147571),     -- Backplane(19 Inch) of the P300 new broadband master Frame: H802MABH

--MA5811S  R016C00
                fnameMA5811SH821MABC(145953),  -- Virtual frame H821MABC of MA581S device.
--MA5694_8VD  R016C00
                fnameMA5694-8VD-H821MABC(145954),      -- Virtual frame of the MA5694-8VD-H821MABC.

--MA5621A  R016C00
                fnameMA5621ASH831Mabc(145955),    -- Virtual frame H831MABC of MA5621A(SD5132) device.

--MA5694-4VD  R016C00
                fnameMA56944VD(145956),          -- Virtual frame MA5694-VD of the MA5694(4VD) device.
                fnameMA56944VD-DC(145972),       -- Virtual frame MA5694-VD of the MA5694(4VD) DC device.

--MA5811S_BT
                fnameMA5811S-BT-H821MABC(145957),    -- Virtual frame H821MABC of MA5811S_BT device .

--MA5694-8VD  R016C00
                fnameMA56948VD-DC(145958),       -- Virtual frame MA5694-VD of the MA5694(8VD) DC device.
                fnameMA56948VD(145959),          -- Virtual frame MA5694-VD of the MA5694(8VD) device.

--MA5621A-4  R016C00
                fnameMA5621A4(145960),          -- Virtual frame MA5621A-4 of the MA5621A(4 serial port) device.

-- SCU remote Frame
                fnameMA5623AR(147526),           -- MDU device MA5623A used as remote frame
                fnameCABLE(147527),             -- MDU device MA5633 used as remote frame

                fnameRemoteReserve30(147530),     -- Remote Frame of the MA5800, reserve for support new frame in old version.
                fnameRemoteReserve31(147531),     -- Remote Frame of the MA5800, reserve for support new frame in old version.
                fnameRemoteReserve32(147532),     -- Remote Frame of the MA5800, reserve for support new frame in old version.
                fnameRemoteReserve33(147533),     -- Remote Frame of the MA5800, reserve for support new frame in old version.
                fnameRemoteReserve34(147534),     -- Remote Frame of the MA5800, reserve for support new frame in old version.
                fnameRemoteReserve35(147535),     -- Remote Frame of the MA5800, reserve for support new frame in old version.
                fnameRemoteReserve36(147536),     -- Remote Frame of the MA5800, reserve for support new frame in old version.
                fnameRemoteReserve37(147537),     -- Remote Frame of the MA5800, reserve for support new frame in old version.
                fnameRemoteReserve38(147538),     -- Remote Frame of the MA5800, reserve for support new frame in old version.
                fnameRemoteReserve39(147539),     -- Remote Frame of the MA5800, reserve for support new frame in old version.
-- MA5800C
		fnameH805MABC(147540),         -- H805MABC Frame
		fnameH805MABO(147541),         -- H805MABO Frame
--OFA5920
                fnameOFA5920H801MABE(145938),    -- ETSI full-specification backplane
                fnameOFA5920H801MABB(145940),    -- 23'NEBS backplane (full-specification backplane), with rear-access line

-- MCU 300 mm Frame
                fnameMA5600H801Mabm(143363),     -- Backplane of the MA5606T master Frame: H801MABM
                fnameH801MABP(143446),           -- Backplane of the MA5606T master Frame: H801MABP
                fnameMA5636(143365),             -- MA5636 outdoor Frame
-- MA5626E
                fnameMA562XH821Mabc(143366),     -- Virtual Backplane of MA5626E Spec master Frame:H821MABC

-- MA562XP +-
                fnameMA562XPH821Mabc(143367),    -- Virtual Frame of MA562XP Spec master Frame:H821MABC
                fnameMA5626H821Mabc(143368),     -- Virtual Frame of MA5626(Reduce Cost)/MA5620 Spec master Frame:H821MABC
                fnameMA5626POEH821Mabc(143451),  -- Virtual Frame of MA5626 POE Spec master Frame:H821MABC
                fnamePvuMainH602Habd(200705),    -- Front-access PVU high-density master Frame, with the H602HABD backplane
-- OT929S
                fnameH821MABA(143447),           -- Virtual Backplane of OT929S Spec master Frame:H821MABA
-- MA5603T
-- SCU 5 U Frame
               fnameMA5603H801Mabn(143364),     -- Backplane of the P300 broadband medium-capacity master Frame: H801MABN
               fnameMA5603H801Mabf(143369),     -- Backplane of the P300 broadband medium-capacity master Frame: H801MABF
               fnameMA5603H801Mabo(143370),     -- Backplane of the P300 broadband medium-capacity master Frame: H801MABO
               fnameMA5603H802Mabo(147523),     -- Backplane of the P300 broadband medium-capacity master Frame: H802MABO
-- MA5608T
-- SCU 2 U Frame
               fnameMA5608H801Mabr(147525),     -- Backplane of the P300 broadband medium-capacity master Frame: H801MABR
               fnameMA5608H802Mabr(147572),     -- Backplane of the P300 broadband medium-capacity master Frame: H802MABR
--MA5800
               fnameMA5800H901BPLB(148501),     -- Backplane of the MA5800
               fnameMA5800H901BPMB(148502),     -- Backplane of the MA5800
               fnameMA5801-GP08(148503),        -- Backplane of the MA5801-GP08
               fnameMA5801-CG04(148504),        -- Backplane of the MA5801-CG04
               fnameEA5801-GP08(148505),        -- Backplane of the EA5801-GP08
               fnameEA5801-CG04(148506),        -- Backplane of the EA5801-CG04
               fnameMA5800H901BPLE(148511),     -- Backplane of the MA5800
               fnameMA5800H901BPIB(148512),     -- 19inch, 200G backplane for MA5800-X15
               fnameMA5800H901BPSB(148513),     -- Backplane of the MA5800-X2

               fnameMA5800H901BPLD(148514),     -- Backplane of the MA5800
               fnameMA5801FL16(148515),         -- Backplane of the MA5801-FL16.
               fnameMA5801SFL16(148516),        -- Backplane of the MA5801S-FL16.
               fnameMA5801GP16(148517),         -- Backplane of the MA5801-GP16.
               fnameMA5801SGP16(148518),        -- Backplane of the MA5801S-GP16.
               fnameEA5801EGP16(148519),        -- Backplane of the EA5801E-GP16.
               fnameMA5801SGP16S1(148520),      -- Backplane of the MA5801S-GP16-S1.
               fnameMA5801GP08H2(148521),       -- Backplane of the MA5801-GP08-H2.
               fnameMA5801CG16H1(148522),        -- Backplane of the MA5801-CG16-H1.
               fnameMA5801FL16H1(148523),        -- Backplane of the MA5801-FL16-H1.
               fnameEA5801EGP08H2(148524),       -- Backplane of the EA5801E-GP08-H2.
               fnameEA5801SGP16H1(148525),       -- Backplane of the EA5801S-GP16-H1.
               fnameMA5801GP16H2(148526),       -- Backplane of the MA5801-GP16-H2.
               fnameMA5801GP08H3(148527),       -- Backplane of the MA5801-GP08-H3.
               fnameEA5801EGP04H1(148528),       -- Backplane of the EA5801E-GP04-H1.
               fnameMA5801SGP16S2(148529),       -- Backplane of the MA5801S-GP16-S2.
               fnameMA5800Reserve30(148530),     -- Backplane of the MA5800, reserve for support new frame in old version.
               fnameMA5800Reserve31(148531),     -- Backplane of the MA5800, reserve for support new frame in old version.
               fnameMA5800Reserve32(148532),     -- Backplane of the MA5800, reserve for support new frame in old version.
               fnameMA5801SGP16H2(148533),       -- Backplane of the MA5801S-GP16-H2.
               fnameEA5801EGP16H2(148534),       -- Backplane of the EA5801E-GP16-H2.
               fnameEA5801EGP08H3(148535),       -- Backplane of the EA5801E-GP08-H3.
               fnameEA5801EGP04H2(148536),       -- Backplane of the EA5801E-GP04-H2.
               fnameEA5801SGP16H2(148537),       -- Backplane of the EA5801S-GP16-H2.
               fnameEA5801EFL16H1(148538),       -- Backplane of the EA5801E-FL16-H1.
               fnameMA5801SFL16H2(148539),       -- Backplane of the MA5801S-FL16-H2.
               fnameEA5801SFL16H2(148540),       -- Backplane of the EA5801S-FL16-H2.
               fnameMA5800TX17HA01BPLA(148541),  -- Backplane of the MA5800T-X17.
               fnameMA5801FL04H1(148542),     	 -- Backplane of the MA5801-FL04-H1.
               fname5800TX8HA01BPMA(148543),     -- Backplane of the MA5800T-X8/EA5800T-X8.
               fname5800TX15HA01BPIA(148544),    -- Backplane of the MA5800T-X15.
               fnameMA5801CG04H2(148545),        -- Backplane of MA5801.
               fnameMC5101C04Q40E(148546),       -- Backplane of the MC5101-C04Q40E.
               fnameMA5801CFL08(148547),         -- Backplane of the MA5801C-FL08.
               fnameMA5801FL08H1(148548),        -- Backplane of MA5801-FL08-H1.
               fnameMA5801FL16H2(148549),        -- Backplane of MA5801-FL16-H2.
               fnameMA5800Reserve50(148550),     -- Backplane of the MA5800, reserve for support new frame in old version.
               fnameMA5800Reserve51(148551),     -- Backplane of the MA5800, reserve for support new frame in old version.
               fnameMA5800Reserve52(148552),     -- Backplane of the MA5800, reserve for support new frame in old version.
               fnameMA5800Reserve53(148553),     -- Backplane of the MA5800, reserve for support new frame in old version.
               fnameMA5800Reserve54(148554),     -- Backplane of the MA5800, reserve for support new frame in old version.
               fnameMA5800Reserve55(148555),     -- Backplane of the MA5800, reserve for support new frame in old version.
               fnameMA5800Reserve56(148556),     -- Backplane of the MA5800, reserve for support new frame in old version.
               fnameMA5800Reserve57(148557),     -- Backplane of the MA5800, reserve for support new frame in old version.
               fnameMA5800Reserve58(148558),     -- Backplane of the MA5800, reserve for support new frame in old version.
               fnameMA5800Reserve59(148559),     -- Backplane of the MA5800, reserve for support new frame in old version.
               fnameMA5800Reserve60(148560),     -- Backplane of the MA5800, reserve for support new frame in old version.

-- WLAN
               fnameWLANWS6603(160000),     -- Backplane of the WLAN V1R2 master Frame: WS6603
               fnameWLANWAC(160001),        -- Backplane of the WLAN V1R3 master Frame: WAC

-- SRG
               fnameSRGFWG1BKPA(190000),       -- SRG master Frame: FWG1BKPA(R1 1U)
               fnameSRGFWG2BKPA(190001),       -- SRG master Frame: FWG2BKPA(R2 1U)
               fnameSRGSU11BKPA(190002),       -- SRG master Frame: SU11BKPA(R2 2U)
               fnameSRGSU21BKPA(190003),       -- SRG master Frame: SU21BKPA(R2 3U)

-- MD
-- Narrowband slave shelves with the control board
                fnameRspHubt(200710),           -- RSP HUBT slave Frame
                fnamePv8Hubt(200711),           -- PV8 HUBT slave Frame
                fnameONU60ARSUG(200712),       -- Remote indoor small-size subscriber unit, with the RSUG control board


-- UA Broadband products (204800 and after)
                fnameApsbHaba(204810),          -- UA local rear-access high-density SPL slave Frame
                fnameApsrHaba(204811),          -- UA remote rear-access high-density SPL slave Frame
                fnameApsbHabd(204812),          -- UA local front-access high-density SPL salve Frame
                fnameApsrHabd(204813),          -- UA remote front-access high-density SPL slave Frame
                fnameApsbHabb(204814),          -- UA local rear-access high-density SPL slave Frame
                fnameApsrHabb(204815),          -- UA remote rear-access high-density SPL slave Frame
                fnameUa5000H612Habd(204816),    -- New BT high-density master Frame
                fnameUa5000H612Habe(204817),    -- New BT high-density master Frame
                fnameApsbH612Habe(204818),      -- New BT local high-density slave Frame
                fnameH612Habl(204819),          -- UA remote rear-access high-density SPL slave Frame
                fnameH602Habd(204820),          -- UA front-access high-density SPL master Frame, based on the H601
                fnameH602Habe(204821),          -- UA front-access high-density integrated master Frame, based on the H601
                fnameApsbH602Habd(204822),      -- UA local front-access high-density SPL slave Frame, based on the H601
                fnameApsbH602Habe(204823),      -- UA local front-access high-density integrated slave Frame, based on the H601
                frameH601Habm(204825),          -- UA front-access high-density integrated master Frame
                frameH601Habn(204826),          -- UA front-access high-density integrated master Frame

-- AG
-- PVM 300 mm Frame
                fnameAmgH801MabaMain(262144),    -- Backplane of the P300 narrowband master Frame: H801MABA
                fnameAmgH801MabaSlave(262145),   -- Backplane of the P300 narrowband slave Frame: H801MABA

                --fnameOnu04(262176),               ONU04 Frame with the remote power supply
                -- fnameOnu08(262177),               ONU08 Frame with the remote power supply
                fnameH601Habc(262178),           -- H601HABC Frame
                fnameRsuHabc(262664),            -- The H601HABC Frame serves as an RSU slave Frame.
                fnameRsuHabl(262665),            -- The H601HABL Frame serves as an RSU slave Frame.
                fnameHwtaHib1(262666),            -- HIB Frame
                fnameHwtaHib2(262667),            -- HIB Frame
                fnameHwtaHib3(262668),            -- HIB Frame
-- 8031:
                fname8031CXUNKN(536576),             -- Unknown frame
                fname8031CX200A(536577),             -- Quidway CX200A Carrier Switch
                fname8031CX200B(536578),             -- Quidway CX200B Carrier Switch
                fname8031CX300A(536579),             -- Quidway CX300A Carrier Switch
                fname8031CX300B(536580),             -- Quidway CX300B Carrier Switch
                fname8031CX380(536581),              -- Quidway CX380 Carrier Switch
                fname8031CX6008(536582),             -- Quidway CX600-8 Carrier Switch
                fname8031CX60016(536583),            -- Quidway CX600-16 Carrier Switch

                fname8031CX200C(536584),             -- Quidway CX200C Metro Service Platform

                fname8031CX200DAC(536585),      -- Quidway CX200D-AC Metro Service Platform
                fname8031CX200DDC(536586),      -- Quidway CX200D-DC Metro Service Platform

                fname8031S2326PEIAC(536587),      -- Quidway S2326P-EI-AC Metro Service Platform
                fname8031S2326PEIDC(536588),      -- Quidway S2326P-EI-DC Metro Service Platform

                fname8031S2318PEIAC(536589),     -- Quidway S2318P-EI-AC Metro Service Platform
                fname8031S2318PEIDC(536590),     -- Quidway S2318P-EI-DC Metro Service Platform

                fname8031S2309PEIAC(536591),      -- Quidway S2309P-EI-AC Metro Service Platform
                fname8031S2309PEIDC(536592),      -- Quidway S2309P-EI-DC Metro Service Platform

                fname8031S2326PSIAC(536593),      -- Quidway S2326P-SI-AC Metro Service Platform
                fname8031S2318PSIAC(536594),      -- Quidway S2318P-SI-AC Metro Service Platform
                fname8031S2309PSIAC(536595),      -- Quidway S2309P-SI-AC Metro Service Platform

                fname8031S3352PEIAC(536596),      -- Quidway S3352P-EI-AC Metro Service Platform
                fname8031S3352PEIDC(536597),      -- Quidway S3352P-EI-DC Metro Service Platform

                fname8031S3328TPEIAC(536598),     -- Quidway S3328TP-EI-AC Metro Service Platform
                fname8031S3328TPEIDC(536599),      -- Quidway S3328TP-EI-DC Metro Service Platform

                fname8031S3352PSIAC(536600),     -- Quidway S3352P-SI-AC Metro Service Platform
                fname8031S3352PSIDC(536601),      -- Quidway S3352P-SI-DC Metro Service Platform

                fname8031S3328TPSIAC(536602),      -- Quidway S3328TP-SI-AC Metro Service Platform
                fname8031S3328TPSIDC(536603),      -- Quidway S3328TP-SI-DC Metro Service Platform

                fname8031CX200DMCAC(536604),      -- Quidway CX200DMC-AC Metro Service Platform
                fname8031CX200DMCDC(536605),     -- Quidway CX200DMC-DC Metro Service Platform

                fname8031CX200DEAAC(536606),      -- Quidway CX200DEA-AC Metro Service Platform
                fname8031CX200DEADC(536607),      -- Quidway CX200DEA-DC Metro Service Platform

                fname8031CX6004(536608),            -- Quidway CX600-4 Carrier Switch

                fname8031CX200DEAMCAC(536609),     -- Quidway CX200DEA-MC-AC Metro Service Platform
                fname8031CX200DEAMCDC(536610),      -- Quidway CX200DEA-MC-DC Metro Service Platform

                fname8031S3328TPEI24SAC(536611),       -- Quidway S3328TP-EI-24S-AC Metro Service Platform
                fname8031S3328TPEI24SDC(536612),       -- Quidway S3328TP-EI-24S-DC Metro Service Platform
                fname8031S3328TPSI24SAC(536613),       -- Quidway S3328TP-SI-24S-AC Metro Service Platform
                fname8031S3328TPSI24SDC(536614),       -- Quidway S3328TP-SI-24S-DC Metro Service Platform

                fname8031S3352PEI24SAC(536615),        -- Quidway S3352P-EI-24S-AC  Metro Service Platform
                fname8031S3352PEI24SDC(536616),        -- Quidway S3352P-EI-24S-DC  Metro Service Platform

                fname8031S3352PEI48SAC(536617),        -- Quidway S3352P-EI-48S-AC  Metro Service Platform
                fname8031S3352PEI48SDC(536618),        -- Quidway S3352P-EI-48S-DC  Metro Service Platform
                fname8031S3352PSI48SAC(536619),        -- Quidway S3352P-SI-48S-AC  Metro Service Platform
                fname8031S3352PSI48SDC(536620),        -- Quidway S3352P-SI-48S-DC  Metro Service Platform

                fname8031S2309TPEIAC(536621),        -- Quidway S2309TP-EI-AC  Metro Service Platform
                fname8031S2309TPEIDC(536622),        -- Quidway S2309TP-EI-DC  Metro Service Platform
                fname8031S2309TPSIAC(536623),        -- Quidway S2309TP-SI-AC  Metro Service Platform

                fname8031S2318TPEIAC(536624),        -- Quidway S2318TP-EI-AC  Metro Service Platform
                fname8031S2318TPEIDC(536625),        -- Quidway S2318TP-EI-DC  Metro Service Platform
                fname8031S2318TPSIAC(536626),        -- Quidway S2318TP-SI-AC  Metro Service Platform

                fname8031S2326TPEIAC(536627),        -- Quidway S2326TP-EI-AC  Metro Service Platform
                fname8031S2326TPEIDC(536628),        -- Quidway S2326TP-EI-DC  Metro Service Platform
                fname8031S2326TPSIAC(536629),        -- Quidway S2326TP-SI-AC  Metro Service Platform

                fname8031S2352PEIAC(536630),         -- Quidway S2352P-EI-AC  Metro Service Platform
                fname8031S2352PEIDC(536631),         -- Quidway S2352P-EI-DC  Metro Service Platform
                fname8031CX6003DC(536632),           -- Quidway CX600-3 DC Carrier Switch
                fname8031CX6003AC(536633),           -- Quidway CX600-3 AC Carrier Switch

                fname8031S5328CEI(536634),         -- Quidway S5328C-EI  Metro Service Platform
                fname8031S5328CEI24S(536635),      -- Quidway S5328C-EI-24S  Metro Service Platform
                fname8031S5352CEI(536636),         -- Quidway S5352C-EI  Metro Service Platform
                fname8031S5324TPSIAC(536637),         -- Quidway S5324TP-SI-AC Metro Service Platform
                fname8031S5324TPSIDC(536638),         -- Quidway S5324TP-SI-DC Metro Service Platform
                fname8031S5348TPSIAC(536639),         -- Quidway S5348TP-SI-AC Metro Service Platform
                fname8031S5348TPSIDC(536640),         -- Quidway S5348TP-SI-DC Metro Service Platform
                fname8031S5324TPPWRSI(536641),         --Quidway S5324TP-PWR-SI Metro Service Platform
                fname8031S5348TPPWRSI(536642),         --Quidway S5348TP-PWR-SI Metro Service Platform
                fname8031S5328CSI(536643),            -- Quidway S5328C-SI Metro Service Platform
                fname8031S5352CSI(536644),            -- Quidway S5352C-SI Metro Service Platform
                fname8031S5328CPWRSI(536645),         -- Quidway S5328C-PWR-SI  Metro Service Platform
                fname8031S5352CPWRSI(536646),         -- Quidway S5352C-PWR-SI  Metro Service Platform
                fname8031S5328CPWREI(536647),         -- Quidway S5328C-PWR-EI  Metro Service Platform
                fname8031S5352CPWREI(536648),         -- Quidway S5352C-PWR-EI  Metro Service Platform
                fname8031S2309TPPWREI(536649),         --Quidway S2309TP-PWR-EI Metro Service Platform
                fname8031S2326TPPWREI(536650),         --Quidway S2326TP-PWR-EI Metro Service Platform
                fname8031S3328TPPWREI(536651),         --Quidway S3328TP-PWR-EI Metro Service Platform
                fname8031S3352PPWREI(536652),         -- Quidway S3352P-PWR-EI  Metro Service Platform
                fname8031CX600X8(536653),             -- Quidway CX600-X8 Carrier Switch
                fname8031CX600X16(536654),            -- Quidway CX600-X16 Carrier Switch
                fname8031CX6008LCD(536655),             --Quidway CX600-8 Carrier Switch, with LCD
                fname8031CX600X1(536656),             --Quidway CX600-X1 Carrier Switch
                fname8031CX600X2(536657),             --Quidway CX600-X2 Carrier Switch

                fname8031S6324C(536658),              -- Quidway S6324C  Metro Service Platform
                fname8031S6348C(536659),              -- Quidway S6348C  Metro Service Platform
                fname8031S5328C-HI(536660),           -- Quidway S5328C-HI  Metro Service Platform
                fname8031S5328C-HI-24S(536661),       -- Quidway S5328C-HI-24S  Metro Service Platform
                fname8031S5306TP-SI(536662),          -- Quidway S5306TP-SI  Metro Service Platform
                fname8031S3326C-HI(536663),           -- Quidway S3326C-HI  Metro Service Platform

                fname8031S2709TPEIAC(536664),        -- Quidway S2709TP-EI-AC Metro Service Platform
                fname8031S2709TPEIDC(536665),        -- Quidway S2709TP-EI-DC Metro Service Platform
                fname8031S2709TPSIAC(536666),        -- Quidway S2709TP-SI-AC Metro Service Platform
                fname8031S2718TPEIAC(536667),        -- Quidway S2718TP-EI-AC Metro Service Platform
                fname8031S2718TPEIDC(536668),        -- Quidway S2718TP-EI-DC Metro Service Platform
                fname8031S2718TPSIAC(536669),        -- Quidway S2718TP-SI-AC Metro Service Platform
                fname8031S2726TPEIAC(536670),        -- Quidway S2726TP-EI-AC Metro Service Platform
                fname8031S2726TPEIDC(536671),        -- Quidway S2726TP-EI-DC Metro Service Platform
                fname8031S2726TPSIAC(536672),        -- Quidway S2726TP-SI-AC Metro Service Platform
                fname8031S2752PEIAC(536673),         -- Quidway S2752P-EI-AC Metro Service Platform
                fname8031S2752PEIDC(536674),         -- Quidway S2752P-EI-DC Metro Service Platform
                fname8031S2709TPPWREI(536675),         --Quidway S2709TP-PWR-EI Metro Service Platform
                fname8031S2726TPPWREI(536676),         --Quidway S2726TP-PWR-EI Metro Service Platform

                fname8031S3728TPEI24SAC(536677),       -- Quidway S3728TP-EI-24S-AC Metro Service Platform
                fname8031S3728TPEI24SDC(536678),       -- Quidway S3728TP-EI-24S-DC Metro Service Platform
                fname8031S3728TPEIAC(536679),     -- Quidway S3728TP-EI-AC Metro Service Platform
                fname8031S3728TPEIDC(536680),      -- Quidway S3728TP-EI-DC Metro Service Platform
                fname8031S3728TPSIAC(536681),      -- Quidway S3728TP-SI-AC Metro Service Platform
                fname8031S3728TPSIDC(536682),      -- Quidway S3728TP-SI-DC Metro Service Platform
                fname8031S3728TPPWREI(536683),         --Quidway S3728TP-PWR-EI Metro Service Platform
                fname8031S3728TPEIMCAC(536684),         --Quidway S3728TP-EI-MC-AC Metro Service Platform

                fname8031S3752PEIDC(536685),      -- Quidway S3752P-EI-DC Metro Service Platform
                fname8031S3752PEIAC(536686),      -- Quidway S3752P-EI-AC Metro Service Platform
                fname8031S3752PSIAC(536687),     -- Quidway S3752P-SI-AC Metro Service Platform
                fname8031S3752PEI24SAC(536688),        -- Quidway S3752P-EI-24S-AC Metro Service Platform
                fname8031S3752PEI24SDC(536689),        -- Quidway S3752P-EI-24S-DC Metro Service Platform
                fname8031S3752PEI48SAC(536690),        -- Quidway S3752P-EI-48S-AC Metro Service Platform
                fname8031S3752PEI48SDC(536691),        -- Quidway S3752P-EI-48S-DC Metro Service Platform
                fname8031S3752PSI48SAC(536692),        -- Quidway S3752P-SI-48S-AC Metro Service Platform
                fname8031S3752PSI48SDC(536693),        -- Quidway S3752P-SI-48S-DC Metro Service Platform
                fname8031S3752PPWREI(536694),         -- Quidway S3752P-PWR-EI  Metro Service Platform

                fname8031S5728CEIAC(536695),         -- Quidway S5728C-EI  Metro Service Platform
                fname8031S5728CEI24SAC(536696),      -- Quidway S5728C-EI-24S  Metro Service Platform
                fname8031S5752CEIAC(536697),         -- Quidway S5752C-EI  Metro Service Platform
                fname8031S5728CPWREI(536698),         -- Quidway S5728C-PWR-EI Metro Service Platform
                fname8031S5752CPWREI(536699),         -- Quidway S5752C-PWR-EI Metro Service Platform

                fname8031S5724TPSIAC(536700),         -- Quidway S5724TP-SI-AC Metro Service Platform
                fname8031S5724TPSIDC(536701),         -- Quidway S5724TP-SI-DC Metro Service Platform
                fname8031S5748TPSIAC(536702),         -- Quidway S5748TP-SI-AC Metro Service Platform
                fname8031S5748TPSIDC(536703),         -- Quidway S5748TP-SI-DC Metro Service Platform
                fname8031S5724TPPWRSI(536704),         --Quidway S5724TP-PWR-SI Metro Service Platform
                fname8031S5748TPPWRSI(536705),         --Quidway S5748TP-PWR-SI Metro Service Platform
                fname8031S5728CSI(536706),            -- Quidway S5728C-SI Metro Service Platform
                fname8031S5752CSI(536707),            -- Quidway S5752C-SI Metro Service Platform
                fname8031S5728CPWRSI(536708),         -- Quidway S5728C-PWR-SI Metro Service Platform
                fname8031S5752CPWRSI(536709),         -- Quidway S5752C-PWR-SI Metro Service Platform

                fname8031S6724EI(536710),          -- Quidway S6700-24-EI  Metro Service Platform
                fname8031S6748EI(536711),          -- Quidway S6700-48-EI  Metro Service Platform
                fname8031CX600X1DO(536712),             --Quidway CX600-X1 Carrier Switch
                fname8031CX600X2DO(536713),             --Quidway CX600-X2 Carrier Switch
                fname8031CX6003DCDO(536714),           -- Quidway CX600-3 DC Carrier Switch
                fname8031CX6003ACDO(536715),           -- Quidway CX600-3 AC Carrier Switch
                fname8031CX600X8DO(536716),             -- Quidway CX600-X8 Carrier Switch
                fname8031CX600X16DO(536717),            -- Quidway CX600-X16 Carrier Switch

                fname8031S3328TPEIMC(536718),           --Quidway S3328TP-EI-MC Metro Service Platform
                fname8031S3318TPEIMC(536719),          -- Quidway S3318TP-EI-MC Metro Service Platform
                fname8031S3728TPEIMC(536720),           --Quidway S3728TP-EI-MC Metro Service Platform
                fname8031S5728CHI(536721),          -- Quidway S5728C-HI  Metro Service Platform
                fname8031S5728CHI24S(536722),       -- Quidway S5728C-HI-24S Metro Service Platform
                fname8031S5706HI(536723),          -- Quidway S5706TP-LI-AC  Metro Service Platform
                fname8031S3726HI(536724),       -- Quidway S3726C-HI Metro Service Platform
                fname8031S5728PLI(536725),       -- Quidway S5700-28P-LI Metro Service Platform
                fname8031S5728PPWRLI(536726),    -- Quidway S5700-28P-PWR-LI Metro Service Platform
                fname8031S5752PLI(536727),       -- Quidway S5700-52P-LI Metro Service Platform
                fname8031S5752PPWRLI(536728),    -- Quidway S5700-52P-PWR-LI Metro Service Platform
                fname8031S5728XEI(536729),       -- Quidway S5700-28X-EI Metro Service Platform
                fname8031S5752XEI(536730),       -- Quidway S5700-52X-EI Metro Service Platform
                fname8031S5352CPWREIB(536770),   --Quidway S5300-28C-PWR-EI Metro Service Platform
                fname8031S5328CPWREIB(536771),   --Quidway S5300-52C-PWR-EI Metro Service Platform
                fname8031S5328PLI(536772),       -- Quidway S5300-28P-LI Metro Service Platform
                fname8031S5352PLI(536773),       -- Quidway S5300-52P-LI Metro Service Platform
                fname8031S5728PLIDC(536774),       -- Quidway S5700-28P-LI-DC Metro Service Platform
                fname8031S5752PLIDC(536775),       -- Quidway S5700-52P-LI-DC Metro Service Platform
                fname8031S5328PLIDC(536776),   --Quidway S5300-28P-LI-DC Metro Service Platform
                fname8031S5352PLIDC(536777),   --Quidway S5300-52P-LI-DC Metro Service Platform
                fname8031S57S28PLIAC(536778),   -- Quidway S5700S-28P-LI-AC Metro Service Platform
                fname8031S57S52PLIAC(536779),   -- Quidway  S5700S-52P-LI-AC Metro Service Platform

                fname8031S271052PSI(536780),        -- Quidway S2710S-52P-SI Metro Service Platform
                fname8031S271026TPPWRSI(536781),    -- Quidway S2710-26TP-PWR-SI Metro Service Platform
                fname8031S271052PPWRSI(536782),    -- Quidway S2710-52P-PWR-SI Metro Service Platform
                fname8031S270052PPWREI(536783),    -- Quidway S2700-52P-PWR-EI Metro Service Platform
                fname8031S370052PPWRSI(536784),    -- Quidway S3700-28TP-PWR-SI Metro Service Platform
                fname8031S370028TPPWRSI(536785),    -- Quidway S3700-52P-PWR-SI Metro Service Platform
                fname8031S571028CPWRLI(536786),    -- Quidway S5710-28C-PWR-LI Metro Service Platform
                fname8031S571052CPWRLI(536787),    -- Quidway S5710-52C-PWR-LI Metro Service Platform
                fname8031S571028CLI(536788),    -- Quidway S5710-28C-LI  Metro Service Platform
                fname8031S571052CLI(536789),    -- Quidway S5710-52C-LI  Metro Service Platform
                fname8031S5710PLIAC(536790),    -- Quidway S5700-10P-LI-AC Metro Service Platform
                fname8031S5710PPWRLIAC(536791),    -- Quidway S5700-10P-PWR-LI-AC Metro Service Platform
                fname8031S5726XSI12SAC(536792),    -- Quidway S5700-26X-SI-12S-AC Metro Service Platform
                fname8031S5728XLIAC(536793),    -- Quidway S5700-28X-LI-AC Metro Service Platform
                fname8031S5728XLIDC(536794),    -- Quidway S5700-28X-LI-DC Metro Service Platform
                fname8031S5752XLIAC(536795),    -- Quidway S5700-52X-LI-AC Metro Service Platform
                fname8031S5752XLIDC(536796),    -- Quidway S5700-52X-LI-DC Metro Service Platform
                fname8031S5728XPWRLIAC(536797),              -- Quidway S5700-28X-PWR-LI-AC Metro Service Platform
                fname8031S5752XPWRLIAC(536798),              -- Quidway S5700-52X-PWR-LI-AC Metro Service Platform
                fname8031S5710108CPWRHIAC(536799),           -- Quidway S5710-108C-PWR-HI-AC Metro Service Platform
                fname8031S5710108CHIAC(536800),              -- Quidway S5710-108C-HI-AC Metro Service Platform
                fname8031S6348CE6000(536801),                -- Quidway S6348C_E6000 Metro Service Platform
                fname8031S571028CPWREI(536802),              -- Quidway S5710-28C-PWR-EI Metro Service Platform
                fname8031S571052CPWREI(536803),              -- Quidway S5710-52C-PWR-EI Metro Service Platform
                fname8031S5310PLIAC(536804),                 -- Quidway S5300-10P-LI-AC Metro Service Platform
                fname8031S531028CEI(536805),                 -- Quidway S5310-28C-EI Metro Service Platform
                fname8031S531052CEI(536806),                 -- Quidway S5310-52C-EI Metro Service Platform
                fname8031S2328PEIAC(536807),                 -- Quidway S2328P-EI-AC Metro Service Platform
                fname8031S275026TPPWREIAC(536808),           -- Quidway S2750-26TP-PWR-EI-AC Metro Service Platform
                fname8031S235026TPPWREIAC(536809),           -- Quidway S2350-26TP-PWR-EI-AC Metro Service Platform
                fname8031S275126TPPWREIAC(536810),           -- Quidway S2751-26TP-PWR-EI-AC Metro Service Platform
                fname8031S235028TPEIAC(536811),              -- Quidway S2350-28TP-EI-AC Metro Service Platform
                fname8031S275028TPEIAC(536812),              -- Quidway S2750-28TP-EI-AC Metro Service Platform
                fname8031S235018TPPWREIAC(536813),           -- Quidway S2350-18TP-PWR-EI-AC Metro Service Platform
                fname8031S275018TPPWREIAC(536814),           -- Quidway S2750-18TP-PWR-EI-AC Metro Service Platform
                fname8031S330052PEI(536815),                 -- Quidway S3300-52P-EI Metro Service Platform
                fname8031CX600-X1-M4(536816),                --Quidway CX600-X1-M4 Carrier Switch for V8R5
                fname8031CX600-X2-M8(536817),                --Quidway CX600-X2-M8 Carrier Switch for V8R5,AC. compatitable with old panel, no "AC" in name
                fname8031CX600-M4-DO(536818),             --Quidway CX600-X1-M4 Carrier Switch for V8R5,overseas
                fname8031CX600-M8-DO(536819),             --Quidway CX600-X2-M8 Carrier Switch for V8R5,AC,overseas.  compatitable with old panel, no "AC" in name
                fname8031CX600-X2-M16(536820),               --Quidway CX600-X2-M16 Carrier Switch for V8R5
                fname8031CX600-M16-DO(536821),            --Quidway CX600-X2-M16 Carrier Switch for V8R5,overseas
                fname8031S5700-28X-LI-24S-DC(536822),        --S5700-28X-LI-24S-DC Mainframe(20 GE SFP,4 GE Combo,4 10GE SFP+,DC -48V)
                fname8031S5300-28X-LI-24S-DC(536823),        --S5300-28X-LI-24S-DC Mainframe(20 GE SFP,4 GE Combo,4 10GE SFP+,DC -48V)
                fname8031S5700-28X-LI-24S-AC(536824),        --S5700-28X-LI-24S-AC Mainframe(20 GE SFP,4 GE Combo,4 10GE SFP+,AC 110/220V)
                fname8031S5300-28X-LI-24S-AC(536825),        --S5300-28X-LI-24S-AC Mainframe(20 GE SFP,4 GE Combo,4 10GE SFP+,AC 110/220V)
                fname8031S5300-28X-LI-DC(536826),            --5300-28X-LI-DC Mainframe(24 GE RJ45,4 10GE SFP+,DC -48V)
                fname8031S5300-28X-LI-AC(536827),            --S5300-28X-LI-AC Mainframe(24 GE RJ45,4 10GE SFP+,AC 110/220V)
                fname8031S2750-28TP-PWR-EI-AC(536828),       --S2750-28TP-PWR-EI-AC Mainframe(24 FE RJ45,2 GE SFP,2 GE COMBO,PoE,AC 110/220V)
                fname8031S2350-28TP-PWR-EI-AC(536829),       --S2350-28TP-PWR-EI-AC  Mainframe(24 FE RJ45,2 GE SFP,2 GE COMBO,PoE,AC 110/220V)
                fname8031S2751-28TP-PWR-EI-AC(536830),       --S2751-28TP-PWR-EI-AC  Mainframe(24FE RJ45,2 GE SFP,2 GE COMBO,12 PoE,AC 110/220V)
                fname8031S2350-20TP-PWR-EI-AC(536831),       --S2350-20TP-PWR-EI-AC Mainframe(16 FE RJ45,2 GE SFP,2 GE COMBO,PoE,AC 110/220V)
                fname8031S2750-20TP-PWR-EI-AC(536832),       --S2750-20TP-PWR-EI-AC Mainframe(16 FE RJ45,2 GE SFP,2 GE COMBO,PoE,AC 110/220V)
                fname8031S2350-28TP-EI-AC(536833),           --S2350-28TP-EI-AC Mainframe(24 FE RJ45,2 GE SFP,2 GE COMBO,AC 110/220V)
                fname8031S2750-28TP-EI-AC(536834),           --S2750-28TP-EI-AC  Mainframe(24 FE RJ45,2 GE SFP,2 GE COMBO,AC 110/220V)
                fname8031S3700-28TP-EI-24S-DC(536835),       -- S3700-28TP-EI-24S-DC
                fname8031CX600-X2-M8-DC(536836),             --Quidway CX600-X2-M8 Carrier Switch for V8R5,DC
                fname8031CX600-X2-M8-DC-DO(536837),          --Quidway CX600-X2-M8 Carrier Switch for V8R5,DC,overseas

                fname8031S5701-28X-LI-AC(536838),            --S5701-28X-LI-AC       Metro Service Platform for V2R3C00
                fname8031S5701-28X-LI-24S-AC(536839),        --S5701-28X-LI-24S-AC   Metro Service Platform for V2R3C00
                fname8031S5700-28P-LI-BAT(536840),           --S5700-28P-LI-BAT      Metro Service Platform for V2R3C02
                fname8031S5700-28P-LI-4AH(536841),           --S5700-28P-LI-4AH      Metro Service Platform for V2R3C02
                fname8031S5700-28P-LI-24S-BAT(536842),       --S5700-28P-LI-24S-BAT  Metro Service Platform for V2R3C02
                fname8031S5700-28P-LI-24S-4AH(536843),       --S5700-28P-LI-24S-4AH  Metro Service Platform for V2R3C02
                fname8031S5300-28P-LI-BAT(536844),           --S5300-28P-LI-BAT      Metro Service Platform for V2R3C02
                fname8031S5300-28P-LI-4AH(536845),           --S5300-28P-LI-4AH      Metro Service Platform for V2R3C02
                fname8031S5300-28P-LI-24S-BAT(536846),       --S5300-28P-LI-24S-BAT  Metro Service Platform for V2R3C02
                fname8031S5300-28P-LI-24S-4AH(536847),       --S5300-28P-LI-24S-4AH  Metro Service Platform for V2R3C02
                fname8031S5700-28X-LI-24CS-AC(536848),       --S5700-28X-LI-24CS-AC  Metro Service Platform for V2R3C02
                fname8031S5700-28X-LI-24CS-DC(536849),       --S5700-28X-LI-24CS-DC  Metro Service Platform for V2R3C02
                fname8031S5300-28X-LI-24CS-AC(536850),       --S5300-28X-LI-24CS-AC  Metro Service Platform for V2R3C02
                fname8031S5300-28X-LI-24CS-DC(536851),       --S5300-28X-LI-24CS-DC  Metro Service Platform for V2R3C02

                fname8031S5310-108C-PWR-HI(536852),          --S5310-108C-PWR-HI     Metro Service Platform for V2R5C00
                fname8031S5300-10P-PWR-LI-AC(536853),        --S5300-10P-PWR-LI-AC   Metro Service Platform for V2R5C00
                fname8031S5300-28P-PWR-LI-AC(536854),        --S5300-28P-PWR-LI-AC   Metro Service Platform for V2R5C00
                fname8031S5300-52P-PWR-LI-AC(536855),        --S5300-52P-PWR-LI-AC   Metro Service Platform for V2R5C00
                fname8031S5300-52X-LI-AC(536856),            --S5300-52X-LI-AC       Metro Service Platform for V2R5C00
                fname8031S5300-52X-LI-DC(536857),            --S5300-52X-LI-DC       Metro Service Platform for V2R5C00
                fname8031S5300-28X-PWR-LI-AC(536858),        --S5300-28X-PWR-LI-AC   Metro Service Platform for V2R5C00
                fname8031S5300-52X-PWR-LI-AC(536859),        --S5300-52X-PWR-LI-AC   Metro Service Platform for V2R5C00
                fname8031S2350-28TP-EI-DC(536860),           --S2350-28TP-EI-DC      Metro Service Platform for V2R5C00
                fname8031S5700-28TP-LI-AC(536861),           --S5700-28TP-LI-AC      Metro Service Platform for V2R3C10
                fname8031S5700-28TP-PWR-LI-AC(536862),       --S5700-28TP-PWR-LI-AC  Metro Service Platform for V2R3C10
                fname8031S5701-28TP-PWR-LI-AC(536863),       --S5701-28TP-PWR-LI-AC  Metro Service Platform for V2R3C10
                fname8090CX600-X8A-AC(536864),                    --Quidway CX600-X8A-AC Carrier Switch
                fname8090CX600-X16A-AC(536865),                   --Quidway CX600-X16A-AC Carrier Switch
                fname8031S5720-56C-HI-AC(536866),            --S5720-56C-HI-AC       Metro Service Platform for V2R6C00
                fname8031S5720-56C-PWR-HI-AC(536867),        --S5720-56C-PWR-HI-AC   Metro Service Platform for V2R6C00
                fname8031S5720-32C-HI-24S-AC(536868),        --S5720-32C-HI-24S-AC   Metro Service Platform for V2R6C00
                fname8090CX600-X8A-DC(536869),               --Quidway CX600-X8A-DC Carrier Switch
                fname8090CX600-X16A-DC(536870),              --Quidway CX600-X16A-DC Carrier Switch
                fname8031CX600-M2E(536871),                    --Quidway CX600-M2E Carrier Switch for V8R5
                fname8031CX600-M2F(536872),                    --Quidway CX600-M2F Carrier Switch for V8R5
                fname8031S1720-28GFR-4TP(536873),            --S1720-28GFR-4TP   Metro Service Platform for V2R6C10
                fname8031S1720-20GFR-4TP(536874),            --S1720-20GFR-4TP   Metro Service Platform for V2R6C10
                fname8031S2720-28TP-EI-AC(536875),           --S2720-28TP-EI-AC  Metro Service Platform for V2R6C10

                fname8031S5720-36C-EI-28S-AC(536876),        --S5720-36C-EI-28S-AC   Metro Service Platform for V2R7C00
                fname8031S5320-36C-EI-28S-AC(536877),        --S5320-36C-EI-28S-AC   Metro Service Platform for V2R7C00
                fname8031S5320-36C-EI-28S-DC(536878),        --S5320-36C-EI-28S-DC   Metro Service Platform for V2R7C00
                fname8031S5720-56C-EI-48S-AC(536879),        --S5720-56C-EI-48S-AC   Metro Service Platform for V2R7C00
                fname8031S5320-56C-EI-48S-AC(536880),        --S5320-56C-EI-48S-AC   Metro Service Platform for V2R7C00
                fname8031S5320-56C-EI-48S-DC(536881),        --S5320-56C-EI-48S-DC   Metro Service Platform for V2R7C00
                fname8031S5720-36C-EI-AC(536882),            --S5720-36C-EI-AC       Metro Service Platform for V2R7C00
                fname8031S5320-36C-EI-AC(536883),            --S5320-36C-EI-AC       Metro Service Platform for V2R7C00
                fname8031S5320-36C-EI-DC(536884),            --S5320-36C-EI-DC       Metro Service Platform for V2R7C00
                fname8031S5720-36PC-EI-AC(536885),           --S5720-36PC-EI-AC      Metro Service Platform for V2R7C00
                fname8031S5320-36PC-EI-AC(536886),           --S5320-36PC-EI-AC      Metro Service Platform for V2R7C00
                fname8031S5320-36PC-EI-DC(536887),           --S5320-36PC-EI-DC      Metro Service Platform for V2R7C00
                fname8031S5720-56C-EI-AC(536888),            --S5720-56C-EI-AC       Metro Service Platform for V2R7C00
                fname8031S5320-56C-EI-AC(536889),            --S5320-56C-EI-AC       Metro Service Platform for V2R7C00
                fname8031S5320-56C-EI-DC(536890),            --S5320-56C-EI-DC       Metro Service Platform for V2R7C00
                fname8031S5720-56PC-EI-AC(536891),           --S5720-56PC-EI-AC      Metro Service Platform for V2R7C00
                fname8031S5320-56PC-EI-AC(536892),           --S5320-56PC-EI-AC      Metro Service Platform for V2R7C00
                fname8031S5320-56PC-EI-DC(536893),           --S5320-56PC-EI-DC      Metro Service Platform for V2R7C00
                fname8031S5720-36C-PWR-EI-AC(536894),        --S5720-36C-PWR-EI-AC   Metro Service Platform for V2R7C00
                fname8031S5320-36C-PWR-EI-AC(536895),        --S5320-36C-PWR-EI-AC   Metro Service Platform for V2R7C00
                fname8031S5320-36C-PWR-EI-DC(536896),        --S5320-36C-PWR-EI-DC   Metro Service Platform for V2R7C00
                fname8031S5720-56C-PWR-EI-AC(536897),        --S5720-56C-PWR-EI-AC   Metro Service Platform for V2R7C00
                fname8031S5320-56C-PWR-EI-AC(536898),        --S5320-56C-PWR-EI-AC   Metro Service Platform for V2R7C00
                fname8031S5720-56C-PWR-EI-AC1(536899),       --S5720-56C-PWR-EI-AC1  Metro Service Platform for V2R7C00
                fname8031S5720-32X-EI-24S-AC(536900),        --S5720-32X-EI-24S-AC   Metro Service Platform for V2R7C00
                fname8031S5320-32X-EI-24S-AC(536901),        --S5320-32X-EI-24S-AC   Metro Service Platform for V2R7C00
                fname8031S5320-32X-EI-24S-DC(536902),        --S5320-32X-EI-24S-DC   Metro Service Platform for V2R7C00
                fname8031S5720-50X-EI-46S-AC(536903),        --S5720-50X-EI-46S-AC   Metro Service Platform for V2R7C00
                fname8031S5320-50X-EI-46S-AC(536904),        --S5320-50X-EI-46S-AC   Metro Service Platform for V2R7C00
                fname8031S5320-50X-EI-46S-DC(536905),        --S5320-50X-EI-46S-DC   Metro Service Platform for V2R7C00
                fname8031S5720-32X-EI-AC(536906),            --S5720-32X-EI-AC       Metro Service Platform for V2R7C00
                fname8031S5320-32X-EI-AC(536907),            --S5320-32X-EI-AC       Metro Service Platform for V2R7C00
                fname8031S5320-32X-EI-DC(536908),            --S5320-32X-EI-DC       Metro Service Platform for V2R7C00
                fname8031S5720-32P-EI-AC(536909),            --S5720-32P-EI-AC       Metro Service Platform for V2R7C00
                fname8031S5320-32P-EI-AC(536910),            --S5320-32P-EI-AC       Metro Service Platform for V2R7C00
                fname8031S5320-32P-EI-DC(536911),            --S5320-32P-EI-DC       Metro Service Platform for V2R7C00
                fname8031S5720-52X-EI-AC(536912),            --S5720-52X-EI-AC       Metro Service Platform for V2R7C00
                fname8031S5320-52X-EI-AC(536913),            --S5320-52X-EI-AC       Metro Service Platform for V2R7C00
                fname8031S5320-52X-EI-DC(536914),            --S5320-52X-EI-DC       Metro Service Platform for V2R7C00
                fname8031S5720-52P-EI-AC(536915),            --S5720-52P-EI-AC       Metro Service Platform for V2R7C00
                fname8031S5320-52P-EI-AC(536916),            --S5320-52P-EI-AC       Metro Service Platform for V2R7C00
                fname8031S5320-52P-EI-DC(536917),            --S5320-52P-EI-DC       Metro Service Platform for V2R7C00
                fname8031S5720-50X-EI-AC(536918),            --S5720-50X-EI-AC       Metro Service Platform for V2R7C00
                fname8031S5320-50X-EI-AC(536919),            --S5320-50X-EI-AC       Metro Service Platform for V2R7C00
                fname8031S5320-50X-EI-DC(536920),            --S5320-50X-EI-DC       Metro Service Platform for V2R7C00

                fname8031CX600-X3A(536921),                  -- Quidway CX600-3A Carrier Switch

                fname8031S5720S-28P-SI-AC(536922),           --S5720S-28P-SI-AC           Metro Service Platform for V2R8C00
                fname8031S5321-28P-SI-AC(536923),            --S5321-28P-SI-AC            Metro Service Platform for V2R8C00
                fname8031S5720S-28X-SI-AC(536924),           --S5720S-28X-SI-AC           Metro Service Platform for V2R8C00
                fname8031S5321-28X-SI-AC(536925),            --S5321-28X-SI-AC            Metro Service Platform for V2R8C00
                fname8031S5321-28X-SI-DC(536926),            --S5321-28X-SI-DC            Metro Service Platform for V2R8C00
                fname8031S5720S-52P-SI-AC(536927),           --S5720S-52P-SI-AC           Metro Service Platform for V2R8C00
                fname8031S5321-52P-SI-AC(536928),            --S5321-52P-SI-AC            Metro Service Platform for V2R8C00
                fname8031S5720S-52X-SI-AC(536929),           --S5720S-52X-SI-AC           Metro Service Platform for V2R8C00
                fname8031S5321-52X-SI-AC(536930),            --S5321-52X-SI-AC            Metro Service Platform for V2R8C00
                fname8031S5321-52X-SI-DC(536931),            --S5321-52X-SI-DC            Metro Service Platform for V2R8C00
                fname8031S5720-28P-SI-AC(536932),            --S5720-28P-SI-AC            Metro Service Platform for V2R8C00
                fname8031S5320-28P-SI-AC(536933),            --S5320-28P-SI-AC            Metro Service Platform for V2R8C00
                fname8031S5720-28X-SI-AC(536934),            --S5720-28X-SI-AC            Metro Service Platform for V2R8C00
                fname8031S5320-28X-SI-AC(536935),            --S5320-28X-SI-AC            Metro Service Platform for V2R8C00
                fname8031S5720-52P-SI-AC(536936),            --S5720-52P-SI-AC            Metro Service Platform for V2R8C00
                fname8031S5320-52P-SI-AC(536937),            --S5320-52P-SI-AC            Metro Service Platform for V2R8C00
                fname8031S5720-52X-SI-AC(536938),            --S5720-52X-SI-AC            Metro Service Platform for V2R8C00
                fname8031S5320-52X-SI-AC(536939),            --S5320-52X-SI-AC            Metro Service Platform for V2R8C00
                fname8031S5720-28X-PWR-SI-AC(536940),        --S5720-28X-PWR-SI-AC        Metro Service Platform for V2R8C00
                fname8031S5320-28X-PWR-SI-AC(536941),        --S5320-28X-PWR-SI-AC        Metro Service Platform for V2R8C00
                fname8031S5720-52X-PWR-SI-AC(536942),        --S5720-52X-PWR-SI-AC        Metro Service Platform for V2R8C00
                fname8031S5720-52X-PWR-SI-ACF(536943),       --S5720-52X-PWR-SI-ACF       Metro Service Platform for V2R8C00
                fname8031S5320-52X-PWR-SI-AC(536944),        --S5320-52X-PWR-SI-AC        Metro Service Platform for V2R8C00
                fname8031S5710-28X-LI-AC(536945),            --S5710-28X-LI-AC            Metro Service Platform for V2R8C00
                fname8031S5710-52X-LI-AC(536946),            --S5710-52X-LI-AC            Metro Service Platform for V2R8C00
                fname8031S6720-30C-EI-24S-AC(536947),        --S6720-30C-EI-24S-AC        Metro Service Platform for V2R8C00
                fname8031S6320-30C-EI-24S-AC(536948),        --S6320-30C-EI-24S-AC        Metro Service Platform for V2R8C00
                fname8031S6320-30C-EI-24S-DC(536949),        --S6320-30C-EI-24S-DC        Metro Service Platform for V2R8C00
                fname8031S6720-54C-EI-48S-AC(536950),        --S6720-54C-EI-48S-AC        Metro Service Platform for V2R8C00
                fname8031S6320-54C-EI-48S-AC(536951),        --S6320-54C-EI-48S-AC        Metro Service Platform for V2R8C00
                fname8031S6320-54C-EI-48S-DC(536952),        --S6320-54C-EI-48S-DC        Metro Service Platform for V2R8C00
                fname8031S5700S-28X-LI-AC(536953),           --S5700S-28X-LI-AC           Metro Service Platform for V2R8C00
                fname8031S5700S-52X-LI-AC(536954),           --S5700S-52X-LI-AC           Metro Service Platform for V2R8C00
                fname8031S5700S-28P-PWR-LI-AC(536955),       --S5700S-28P-PWR-LI-AC       Metro Service Platform for V2R8C00
                fname8031E628(536956),                       --E628                       Metro Service Platform for V2R8C00
                fname8031E628-X(536957),                     --E628-X                     Metro Service Platform for V2R8C00
                fname8031E652(536958),                       --E652                       Metro Service Platform for V2R8C00
                fname8031E652-X(536959),                     --E652-X                     Metro Service Platform for V2R8C00

                fname8031S5720-14X-PWH-SI-AC(536960),        --S5720-14X-PWH-SI-AC        Metro Service Platform for V2R9C00
                fname8031S6720S-26Q-EI-24S-AC(536961),       --S6720S-26Q-EI-24S-AC       Metro Service Platform for V2R9C00
                fname8031S6720S-26Q-EI-24S-DC(536962),       --S6720S-26Q-EI-24S-DC       Metro Service Platform for V2R9C00
                fname8031S6320-26Q-EI-24S-AC(536963),        --S6320-26Q-EI-24S-AC        Metro Service Platform for V2R9C00
                fname8031S6320-26Q-EI-24S-DC(536964),        --S6320-26Q-EI-24S-DC        Metro Service Platform for V2R9C00
                fname8031S5300-28TP-PWR-LI-AC(536965),       --S5300-28TP-PWR-LI-AC       Metro Service Platform for V2R9C00
                fname8031S5300-10P-PWR-LI-AC-NEW(536966),    --S5300-10P-PWR-LI-AC        Metro Service Platform for V2R9C00
                fname8031S5320-28X-SI-DC(536967),            --S5320-28X-SI-DC            Metro Service Platform for V2R9C00
                fname8031S5320-52X-SI-DC(536968),            --S5320-52X-SI-DC            Metro Service Platform for V2R9C00
                fname8031S5720-28X-PWR-SI-DC(536969),        --S5720-28X-PWR-SI-DC        Metro Service Platform for V2R9C00
                fname8031S5720-52X-PWR-SI-DC(536970),        --S5720-52X-PWR-SI-DC        Metro Service Platform for V2R9C00
                fname8031S5320-52X-PWR-SI-ACF(536971),       --S5320-52X-PWR-SI-ACF       Metro Service Platform for V2R9C00
                fname8031S5720-28X-SI-DC(536972),            --S5720-28X-SI-DC            Metro Service Platform for V2R9C00
                fname8031S5720-52X-SI-DC(536973),            --S5720-52X-SI-DC            Metro Service Platform for V2R9C00
                fname8031S5720S-28X-SI-DC(536974),           --S5720S-28X-SI-DC           Metro Service Platform for V2R9C00
                fname8031S5720S-52X-SI-DC(536975),           --S5720S-52X-SI-DC           Metro Service Platform for V2R9C00
                fname8031S5720-32X-EI-DC(536976),            --S5720-32X-EI-DC            Metro Service Platform for V2R9C00
                fname8031S5720-50X-EI-DC(536977),            --S5720-50X-EI-DC            Metro Service Platform for V2R9C00
                fname8031S5720-32X-EI-24S-DC(536978),        --S5720-32X-EI-24S-DC        Metro Service Platform for V2R9C00
                fname8031S5720-50X-EI-46S-DC(536979),        --S5720-50X-EI-46S-DC        Metro Service Platform for V2R9C00
                fname8031S5720-36C-EI-DC(536980),            --S5720-36C-EI-DC            Metro Service Platform for V2R9C00
                fname8031S5720-56C-EI-DC(536981),            --S5720-56C-EI-DC            Metro Service Platform for V2R9C00
                fname8031S5720-36C-PWR-EI-DC(536982),        --S5720-36C-PWR-EI-DC        Metro Service Platform for V2R9C00
                fname8031S5720-56C-PWR-EI-DC(536983),        --S5720-56C-PWR-EI-DC        Metro Service Platform for V2R9C00
                fname8031S5720-36C-EI-28S-DC(536984),        --S5720-36C-EI-28S-DC        Metro Service Platform for V2R9C00
                fname8031S5720-56C-EI-48S-DC(536985),        --S5720-56C-EI-48S-DC        Metro Service Platform for V2R9C00
                fname8031S5320-56C-HI-AC(536986),            --S5320-56C-HI-AC            Metro Service Platform for V2R9C00
                fname8031S5320-56C-HI-DC(536987),            --S5320-56C-HI-DC            Metro Service Platform for V2R9C00
                fname8031S5320-32C-HI-24S-DC(536988),        --S5320-32C-HI-24S-DC        Metro Service Platform for V2R9C00
                fname8031S5320-32C-HI-24S-AC(536989),        --S5320-32C-HI-24S-AC        Metro Service Platform for V2R9C00
                fname8031S6720-30C-EI-24S-DC(536990),        --S6720-30C-EI-24S-DC        Metro Service Platform for V2R9C00
                fname8031S6720-54C-EI-48S-DC(536991),        --S6720-54C-EI-48S-DC        Metro Service Platform for V2R9C00
                fname8031S5720-56C-PWR-HI-AC1(536992),       --S5720-56C-PWR-HI-AC1       Metro Service Platform for V2R9C00

                fname8090CX600-X16ADO-AC(536993),               --Quidway CX600-X16ADO-AC Carrier Switch
                fname8090CX600-X16ADO-DC(536994),            --Quidway CX600-X16ADO-DC Carrier Switch
                fname8090CX600-X8ADO-AC(536995),                --Quidway CX600-X8ADO-AC Carrier Switch
                fname8090CX600-X8ADO-DC(536996),             --Quidway CX600-X8ADO-DC Carrier Switch
                fname8031CX600-X3ADO(536997),                -- Quidway CX600-3ADO Carrier Switch
                fname8031CX600-M8A(536998),                  --Quidwy CX600-M8A-AC FRAME
                fname8031CX600-M8A-DC(536999),               --Quidwy CX600-M8A-DC FRAME
                fname8031CX600-M8ADO(537000),                --Quidwy CX600-M8ADO-AC FRAME
                fname8031CX600-M8ADO-DC(537001),             --Quidwy CX600-M8ADO-DC FRAME
                fname8031CX600-M16A(537002),                 --Quidwy CX600-M16AFRAME
                fname8031CX600-M16ADO(537003),               --Quidwy CX600-M16ADO-AC FRAME

                fname8031S6720S-26Q-EI-24S(537004),          --S6720S-26Q-EI-24S          Metro Service Platform for V2R9C00
                fname8031S6320-26Q-EI-24S(537005),           --S6320-26Q-EI-24S           Metro Service Platform for V2R9C00
                fname8031S5320-28X-SI(537006),               --S5320-28X-SI               Metro Service Platform for V2R9C00
                fname8031S5320-52X-SI(537007),               --S5320-52X-SI               Metro Service Platform for V2R9C00
                fname8031S5320-36C-EI(537008),               --S5320-36C-EI               Metro Service Platform for V2R9C00
                fname8031S5320-56C-EI(537009),               --S5320-56C-EI               Metro Service Platform for V2R9C00
                fname8031S5320-36C-EI-28S(537010),           --S5320-36C-EI-28S           Metro Service Platform for V2R9C00

                fname8031Huawei-S5700-8P-G(537011),           --S5720-10T-PWR-LI           Metro Service Platform for V2R10C00 modify S5720-10T-PWR-LI to  Huawei-S5700-8P-G
                fname8031S5720-12TP-LI-AC(537012),           --S5720-12TP-LI-AC           Metro Service Platform for V2R10C00
                fname8031S5720S-12TP-LI-AC(537013),          --S5720S-12TP-LI-AC          Metro Service Platform for V2R10C00
                fname8031S5320-12TP-LI-AC(537014),           --S5320-12TP-LI-AC           Metro Service Platform for V2R10C00
                fname8031S1720-10GW-2P(537015),              --S1720-10GW-2P             Metro Service Platform for V2R10C00
                fname8031S5720-12TP-PWR-LI-AC(537016),       --S5720-12TP-PWR-LI-AC       Metro Service Platform for V2R10C00
                fname8031S5720S-12TP-PWR-LI-AC(537017),      --S5720S-12TP-PWR-LI-AC      Metro Service Platform for V2R10C00
                fname8031S5320-12TP-PWR-LI-AC(537018),       --S5320-12TP-PWR-LI-AC       Metro Service Platform for V2R10C00
                fname8031S1720-10GW-PWR-2P(537019),          --S1720-10GW-PWR-2P         Metro Service Platform for V2R10C00
                fname8031S5720-28P-LI-AC(537020),            --S5720-28P-LI-AC            Metro Service Platform for V2R10C00
                fname8031S5720S-28P-LI-AC(537021),           --S5720S-28P-LI-AC           Metro Service Platform for V2R10C00
                fname8031S5320-28P-LI-AC(537022),            --S5320-28P-LI-AC            Metro Service Platform for V2R10C00
                fname8031S1720-28GWR-4P(537023),             --S1720-28GWR-4P             Metro Service Platform for V2R10C00
                fname8031S5720-28X-LI-AC(537024),            --S5720-28X-LI-AC            Metro Service Platform for V2R10C00
                fname8031S5720-28X-LI-DC(537025),            --S5720-28X-LI-DC            Metro Service Platform for V2R10C00
                fname8031S5320-28X-LI-AC(537026),            --S5320-28X-LI-AC            Metro Service Platform for V2R10C00
                fname8031S5320-28X-LI-DC(537027),            --S5320-28X-LI-DC            Metro Service Platform for V2R10C00
                fname8031S5720S-28X-LI-AC(537028),           --S5720S-28X-LI-AC           Metro Service Platform for V2R10C00
                fname8031S628X-E(537029),                    --S628X-E                    Metro Service Platform for V2R10C00
                fname8031S1720-28GWR-4X(537030),             --S1720-28GWR-4X             Metro Service Platform for V2R10C00
                fname8031S5720-28P-PWR-LI-AC(537031),        --S5720-28P-PWR-LI-AC        Metro Service Platform for V2R10C00
                fname8031S5720S-28P-PWR-LI-AC(537032),       --S5720S-28P-PWR-LI-AC       Metro Service Platform for V2R10C00
                fname8031S5320-28P-PWR-LI-AC(537033),        --S5320-28P-PWR-LI-AC        Metro Service Platform for V2R10C00
                fname8031S5720-28P-PWR-LI-ACF(537034),       --S5720-28P-PWR-LI-ACF       Metro Service Platform for V2R10C00
                fname8031S1720-28GWR-PWR-4P(537035),         --S1720-28GWR-PWR-4P         Metro Service Platform for V2R10C00
                fname8031S5720-28X-PWR-LI-AC(537036),        --S5720-28X-PWR-LI-AC        Metro Service Platform for V2R10C00
                fname8031S5320-28X-PWR-LI-AC(537037),        --S5320-28X-PWR-LI-AC        Metro Service Platform for V2R10C00
                fname8031S5720-28X-PWR-LI-ACF(537038),       --S5720-28X-PWR-LI-ACF       Metro Service Platform for  V2R*,on 2016.12.24
                fname8031S5320-28X-PWR-LI-ACF(537039),       --S5320-28X-PWR-LI-ACF       Metro Service Platform for  V2R*,on 2016.12.24
                fname8031S5720S-28X-PWR-LI-AC(537040),       --S5720S-28X-PWR-LI-AC       Metro Service Platform for V2R10C00
                fname8031S628X-PWR-E(537041),                --S628X-PWR-E                Metro Service Platform for V2R10C00
                fname8031S1720-28GWR-PWR-4X(537042),         --S1720-28GWR-PWR-4X         Metro Service Platform for V2R10C00
                fname8031S5720-52P-LI-AC(537043),            --S5720-52P-LI-AC            Metro Service Platform for V2R10C00
                fname8031S5720S-52P-LI-AC(537044),           --S5720S-52P-LI-AC           Metro Service Platform for V2R10C00
                fname8031S5320-52P-LI-AC(537045),            --S5320-52P-LI-AC            Metro Service Platform for V2R10C00
                fname8031S652-E(537046),                     --S652-E                     Metro Service Platform for V2R10C00
                fname8031S5720S-52X-LI-AC(537047),           --S5720S-52X-LI-AC           Metro Service Platform for V2R10C00
                fname8031S652X-E(537048),                    --S652X-E                    Metro Service Platform for V2R10C00
                fname8031S5720-52X-LI-AC(537049),            --S5720-52X-LI-AC            Metro Service Platform for V2R10C00
                fname8031S5720-52X-LI-DC(537050),            --S5720-52X-LI-DC            Metro Service Platform for V2R10C00
                fname8031S5320-52X-LI-AC(537051),            --S5320-52X-LI-AC            Metro Service Platform for V2R10C00
                fname8031S5320-52X-LI-DC(537052),            --S5320-52X-LI-DC            Metro Service Platform for V2R10C00
                fname8031S1720-52GWR-4P(537053),             --S1720-52GWR-4P             Metro Service Platform for V2R10C00
                fname8031S1720-52GWR-4X(537054),             --S1720-52GWR-4X             Metro Service Platform for V2R10C00
                fname8031S5720-52P-PWR-LI-AC(537055),        --S5720-52P-PWR-LI-AC        Metro Service Platform for V2R10C00
                fname8031S5720S-52P-PWR-LI-AC(537056),       --S5720S-52P-PWR-LI-AC       Metro Service Platform for V2R10C00
                fname8031S5320-52P-PWR-LI-AC(537057),        --S5320-52P-PWR-LI-AC        Metro Service Platform for V2R10C00
                fname8031S652-PWR-E(537058),                 --S652-PWR-E                 Metro Service Platform for V2R10C00
                fname8031S5720-52P-PWR-LI-ACF(537059),       --S5720-52P-PWR-LI-ACF       Metro Service Platform for V2R10C00
                fname8031S5720S-52X-PWR-LI-AC(537060),       --S5720S-52X-PWR-LI-AC       Metro Service Platform for V2R10C00
                fname8031S652X-PWR-E(537061),                --S652X-PWR-E                Metro Service Platform for V2R10C00
                fname8031S5720-52X-PWR-LI-AC(537062),        --S5720-52X-PWR-LI-AC        Metro Service Platform for V2R10C00
                fname8031S5320-52X-PWR-LI-AC(537063),        --S5320-52X-PWR-LI-AC        Metro Service Platform for V2R10C00
                fname8031S5720-52X-PWR-LI-ACF(537064),       --S5720-52X-PWR-LI-ACF       Metro Service Platform for V2R*,on 2016.12.24
                fname8031S5320-52X-PWR-LI-ACF(537065),       --S5320-52X-PWR-LI-ACF       Metro Service Platform for V2R*,on 2016.12.24
                fname8031S1720-52GWR-PWR-4P(537066),         --S1720-52GWR-PWR-4P         Metro Service Platform for V2R10C00
                fname8031S1720-52GWR-PWR-4X(537067),         --S1720-52GWR-PWR-4X         Metro Service Platform for V2R10C00
                fname8031S5720-28X-SI-24S-AC(537068),        --S5720-28X-SI-24S-AC        Metro Service Platform for V2R10C00
                fname8031S5720-28X-SI-24S-DC(537069),        --S5720-28X-SI-24S-DC        Metro Service Platform for V2R10C00
                fname8031S5321-28X-SI-24S-AC(537070),        --S5321-28X-SI-24S-AC        Metro Service Platform for V2R10C00
                fname8031S5321-28X-SI-24S-DC(537071),        --S5321-28X-SI-24S-DC        Metro Service Platform for V2R10C00
                fname8031S5720-28X-LI-24S-AC(537072),        --S5720-28X-LI-24S-AC        Metro Service Platform for V2R10C00
                fname8031S5720S-28X-LI-24S-AC(537073),       --S5720S-28X-LI-24S-AC       Metro Service Platform for V2R10C00
                fname8031S5720-28X-LI-24S-DC(537074),        --S5720-28X-LI-24S-DC        Metro Service Platform for V2R10C00
                fname8031S5320-28X-LI-24S-AC(537075),        --S5320-28X-LI-24S-AC        Metro Service Platform for V2R10C00
                fname8031S5320-28X-LI-24S-DC(537076),        --S5320-28X-LI-24S-DC        Metro Service Platform for V2R10C00
                fname8031S5720-28TP-PWR-LI-ACL(537077),      --S5720-28TP-PWR-LI-ACL      Metro Service Platform for V2R10C00
                fname8031S5720S-28TP-PWR-LI-ACL(537078),     --S5720S-28TP-PWR-LI-ACL     Metro Service Platform for V2R10C00
                fname8031S1720-28GWR-PWR-4TP(537079),        --S1720-28GWR-PWR-4TP        Metro Service Platform for V2R10C00
                fname8031S5720-28TP-PWR-LI-AC(537080),       --S5720-28TP-PWR-LI-AC       Metro Service Platform for V2R10C00
                fname8031S628-PWR-E(537081),                 --S628-PWR-E                 Metro Service Platform for V2R10C00
                fname8031S5720-28TP-LI-AC(537082),           --S5720-28TP-LI-AC           Metro Service Platform for V2R10C00
                fname8031S628-E(537083),                     --S628-E                     Metro Service Platform for V2R10C00
                fname8031S1700-28GR-4X(537084),              --S1700-28GR-4X              Metro Service Platform for  V2R11,v2r10c00 del v2r11 new
                fname8031S1700-52GR-4X(537085),              --S1700-52GR-4X              Metro Service Platform for  V2R11,v2r10c00 del v2r11 new
                fname8031S5720-28X-SI-12S-AC(537086),        --S5720-28X-SI-12S-AC        Metro Service Platform for  V2R*,on 2016.12.24
                fname8031S5720S-28X-SI-12S-AC(537087),       --S5720S-28X-SI-12S-AC       Metro Service Platform for  V2R*,on 2016.12.24
                fname8031S5720-30C-LI-AC(537088),            --S5720-30C-LI-AC            Metro Service Platform for  V2R*,on 2016.12.24
                fname8031S5720-30C-LI-DC(537089),            --S5720-30C-LI-DC            Metro Service Platform for V2R10C00
                fname8031S5720-54C-LI-AC(537090),            --S5720-54C-LI-AC            Metro Service Platform for V2R*,on 2016.12.24
                fname8031S5720-54C-LI-DC(537091),            --S5720-54C-LI-DC            Metro Service Platform for V2R10C00
                fname8031S5720-30C-PWR-LI-AC(537092),        --S5720-30C-PWR-LI-AC        Metro Service Platform for V2R*,on 2016.12.24
                fname8031S5720-30C-PWR-LI-DC(537093),        --S5720-30C-PWR-LI-DC        Metro Service Platform for V2R10C00
                fname8031S5720-54C-PWR-LI-AC(537094),        --S5720-54C-PWR-LI-AC        Metro Service Platform for V2R*,on 2016.12.24
                fname8031S5720-54C-PWR-LI-DC(537095),        --S5720-54C-PWR-LI-DC        Metro Service Platform for V2R10C00
                fname8031S5720-28X-SI-C(537096),             --S5720-28X-SI-C             Metro Service Platform for V2R10C00
                fname8031S5720-52X-SI-C(537097),             --S5720-52X-SI-C             Metro Service Platform for V2R10C00
                fname8031S5720-28X-PWR-SI-C(537098),         --S5720-28X-PWR-SI-C         Metro Service Platform for V2R10C00
                fname8031S5720-52X-PWR-SI-C(537099),         --S5720-52X-PWR-SI-C         Metro Service Platform for V2R10C00
                fname8031S5320-28X-PWR-SI-DC(537100),        --S5320-28X-PWR-SI-DC        Metro Service Platform for V2R10C00
                fname8031S5320-52X-PWR-SI-DC(537101),        --S5320-52X-PWR-SI-DC        Metro Service Platform for V2R10C00
                fname8031CX600-M2H(537102),                  --Quidway CX600-M2H FRAME for V8R9C00
                fname8031S5320-28P-SI-DC(537103),            --S5320-28P-SI-DC            Metro Service Platform for V2R10C00
                fname8031S5320-52P-SI-DC(537104),            --S5320-52P-SI-DC            Metro Service Platform for V2R10C00
                fname8031S5320-56C-PWR-EI-ACF(537105),       --S5320-56C-PWR-EI-ACF       Metro Service Platform for V2R10C00
                fname8031S5320-12TP-LI-DC(537106),           --S5320-12TP-LI-DC           Metro Service Platform for V2R10C00
                fname8031S5321-52X-LI-AC(537107),            --S5321-52X-LI-AC            Metro Service Platform for V2R10C00
                fname8031S5320-28X-PWR-SI(537108),           --S5320-28X-PWR-SI           Metro Service Platform for V2R10C00
                fname8031S5320-52X-PWR-SI(537109),           --S5320-52X-PWR-SI           Metro Service Platform for V2R10C00
                fname8031S5320-28P-SI(537110),               --S5320-28P-SI               Metro Service Platform for V2R10C00
                fname8031S5322-52X-LI-AC(537111),            --S5322-52X-LI-AC            Metro Service Platform for V2R10C00
                fname8031S6320-54C-EI-48S(537112),           --S6320-54C-EI-48S           Metro Service Platform for V2R10C00
                fname8031S5720-16X-PWH-LI-AC(537113),        --S5720-16X-PWH-LI-AC        Metro Service Platform for V2R10C00
                fname8031S5720-28X-PWH-LI-AC(537114),        --S5720-28X-PWH-LI-AC        Metro Service Platform for V2R11C00
                fname8031S5320-28X-PWH-LI-AC(537115),        --S5320-28X-PWH-LI-AC        Metro Service Platform for V2R11C00  del				

--M2K wwx365872 add
                fname8031CX600-M2K(675942),                  --Quidway CX600-M2K FRAME for V8R10C10
                fname8090NE40E-M2K(675943),                  --Quidway NE40E-M2K FRAME for V8R10C10
                fname8090CX6602(675944),                   --Quidway CX6602 FRAME for V8R10C10
--M2K wwx365872 add end

                fname8031S1720-28GWR-4P-E(537116),            --S1720-28GWR-4P-E           switch for V2R10C00 tr6
                fname8031S1720-28GWR-4X-E(537117),            --S1720-28GWR-4X-E           switch for V2R10C00 tr6
                fname8031S1720-28GWR-PWR-4P-E(537118),        --S1720-28GWR-PWR-4P-E       switch for V2R10C00 tr6
                fname8031S1720-28GWR-PWR-4X-E(537119),        --S1720-28GWR-PWR-4X-E       switch for V2R10C00 tr6
                fname8031S1720-52GWR-4P-E(537120),            --S1720-52GWR-4P-E           switch for V2R10C00 tr6
                fname8031S1720-52GWR-4X-E(537121),            --S1720-52GWR-4X-E           switch for V2R10C00 tr6
                fname8031S1720-52GWR-PWR-4P-E(537122),        --S1720-52GWR-PWR-4P-E       switch for V2R10C00 tr6
                fname8031S1720-52GWR-PWR-4X-E(537123),        --S1720-52GWR-PWR-4X-E       switch for V2R10C00 tr6
                fname8031S1720-28GWR-PWR-4TP-E(537124),       --S1720-28GWR-PWR-4TP-E      switch for V2R10C00 tr6
                fname8031S1720-10GW-2P-E(537125),             --S1720-10GW-2P-E            switch for V2R10C00 tr6
                fname8031S1720-10GW-PWR-2P-E(537126),         --S1720-10GW-PWR-2P-E        switch for V2R10C00 tr6

                fname8031S5720-12X-LI-AC(537127),             --S5720-12X-LI-AC            Metro Service Platform for   V2R*,on 2016.12.24
                fname8031S5320-12X-LI-AC(537128),             --S5320-12X-LI-AC            Metro Service Platform for   V2R*,on 2016.12.24
                fname8031S5720-12X-PWR-LI-AC(537129),         --S5720-12X-PWR-LI-AC        Metro Service Platform for   V2R*,on 2016.12.24
                fname8031S5320-12X-PWR-LI-AC(537130),         --S5320-12X-PWR-LI-AC        Metro Service Platform for V2R11
                fname8031S5320-28TP-LI-AC(537131),            --S5320-28TP-LI-AC           Metro Service Platform for V2R11
                fname8031S5721-28X-SI-24S-AC(537132),         --S5721-28X-SI-24S-AC        Metro Service Platform for V2R11
                fname8031S5320-28X-SI-24S-AC(537133),         --S5320-28X-SI-24S-AC        Metro Service Platform for V2R11
                fname8031S5320-28X-SI-24S-DC(537134),         --S5320-28X-SI-24S-DC        Metro Service Platform for V2R11
                fname8031S2720-12TP-EI(537135),            --S2720-12TP-EI           Metro Service Platform for V2R11, modify name
                fname8031S2320-12TP-EI-AC(537136),            --S2320-12TP-EI-AC           Metro Service Platform for V2R11
                fname8031S2320-12TP-EI-DC(537137),            --S2320-12TP-EI-DC           Metro Service Platform for V2R11
                fname8031S2720-12TP-PWR-EI(537138),        --S2720-12TP-PWR-EI       Metro Service Platform for V2R11, modify name
                fname8031S2320-12TP-PWR-EI-AC(537139),        --S2320-12TP-PWR-EI-AC       Metro Service Platform for V2R11
                fname8031S2720-52TP-EI(537140),            --S2720-52TP-EI           Metro Service Platform for V2R11, modify name
                fname8031S2320-52TP-EI-AC(537141),            --S2320-52TP-EI-AC           Metro Service Platform for V2R11
                fname8031S2720-52TP-PWR-EI(537142),        --S2720-52TP-PWR-EI       Metro Service Platform for V2R11, modify name
                fname8031S2320-52TP-PWR-EI-AC(537143),        --S2320-52TP-PWR-EI-AC       Metro Service Platform for V2R11
                fname8031S2720-28TP-PWR-EI-L(537144),       --S2720-28TP-PWR-EI-L      Metro Service Platform for V2R11, modify name
                fname8031S2720-28TP-EI(537145),         --S2720-28TP-EI       Metro Service Platform for V2R11, modify name, modify name
                fname8031S2320-28TP-EI-AC(537146),            --S2320-28TP-EI-AC           Metro Service Platform for V2R11
                fname8031S2320-28TP-EI-DC(537147),            --S2320-28TP-EI-DC           Metro Service Platform for V2R11
                fname8031S2720-28TP-PWR-EI(537148),        --S2720-28TP-PWR-EI       Metro Service Platform for V2R11, modify name
                fname8031S2320-28TP-PWR-EI-AC(537149),        --S2320-28TP-PWR-EI-AC       Metro Service Platform for V2R11
                fname8031S2320-28P-PWR-EI-ACF(537150),        --S2320-28P-PWR-EI-ACF       Metro Service Platform for V2R11


                fname8031S6720-26Q-LI-24S-AC(537151),         --S6720-26Q-LI-24S-AC        Metro Service Platform for V2R11
                fname8031S6720S-26Q-LI-24S-AC(537152),        --S6720S-26Q-LI-24S-AC       Metro Service Platform for V2R11
                fname8031S6321-26Q-SI-24S-AC(537153),         --S6321-26Q-SI-24S-AC        Metro Service Platform for   V2R*,on 2016.12.24
                fname8031S6320-26Q-SI-24S-AC(537154),         --S6320-26Q-SI-24S-AC        Metro Service Platform for   V2R*,on 2016.12.24
                fname8031S6720S-26Q-SI-24S-AC(537155),        --S6720S-26Q-SI-24S-AC       Metro Service Platform for V2R11
                fname8031S6720-26Q-SI-24S-AC(537156),         --S6720-26Q-SI-24S-AC        Metro Service Platform for V2R11
                fname8031S6720-16X-LI-16S-AC(537157),         --S6720-16X-LI-16S-AC        Metro Service Platform for V2R11
                fname8031S6720S-16X-LI-16S-AC(537158),        --S6720S-16X-LI-16S-AC       Metro Service Platform for V2R11
                fname8031S1720X-16XWR(537159),                --S1720X-16XWR               Metro Service Platform for V2R11
                fname8031S1720X-16XWR-E(537160),              --S1720X-16XWR-E             Metro Service Platform for V2R11
                fname8031S6720-32X-LI-32S-AC(537161),         --S6720-32X-LI-32S-AC        Metro Service Platform for V2R11
                fname8031S6720S-32X-LI-32S-AC(537162),        --S6720S-32X-LI-32S-AC       Metro Service Platform for V2R11
                fname8031S6720-32X-SI-32S-AC(537163),         --S6720-32X-SI-32S-AC        Metro Service Platform for V2R11
                fname8031S6320-32X-SI-32S-AC(537164),         --S6320-32X-SI-32S-AC        Metro Service Platform for   V2R*,on 2016.12.24
                fname8031S1720X-32XWR(537165),                --S1720X-32XWR               Metro Service Platform for V2R11
                fname8031S1720X-32XWR-E(537166),              --S1720X-32XWR-E             Metro Service Platform for V2R11
                fname8031S6720-32C-SI-AC(537167),             --S6720-32C-SI-AC            Metro Service Platform for V2R11
                fname8031S6720-32C-SI-DC(537168),             --S6720-32C-SI-DC            Metro Service Platform for V2R11
                fname8031S6320-32C-SI-AC(537169),             --S6320-32C-SI-AC            Metro Service Platform for   V2R*,on 2016.12.24
                fname8031S6320-32C-SI-DC(537170),             --S6320-32C-SI-DC            Metro Service Platform for   V2R*,on 2016.12.24
                fname8031S6720-32C-PWH-SI-AC(537171),         --S6720-32C-PWH-SI-AC        Metro Service Platform for V2R11
                fname8031S6720-32C-PWH-SI(537172),            --S6720-32C-PWH-SI           Metro Service Platform for V2R11
                fname8031S6320-32C-PWH-SI-AC(537173),         --S6320-32C-PWH-SI-AC        Metro Service Platform for   V2R*,on 2016.12.24
                fname8031S6320-32C-PWH-SI(537174),            --S6320-32C-PWH-SI           Metro Service Platform for   V2R*,on 2016.12.24
                fname8031S6720-56C-PWH-SI-AC(537175),         --S5730-56C-PWH-SI-AC        Metro Service Platform for V2R11 modify from S5730-56C-PWH-SI-AC to S6720-56C-PWH-SI-AC
                fname8031S6720-56C-PWH-SI(537176),            --S5730-56C-PWH-SI           Metro Service Platform for V2R11 modify from S5730-56C-PWH-SI to S6720-56C-PWH-SI
                fname8031S6320-56C-PWH-SI-AC(537177),         --S5330-56C-PWH-SI-AC        Metro Service Platform for   V2R*,on 2016.12.24 modify from S5330-56C-PWH-SI-AC to S6320-56C-PWH-SI-AC
                fname8031S6320-56C-PWH-SI(537178),            --S5330-56C-PWH-SI           Metro Service Platform for   V2R*,on 2016.12.24 modify from S5330-56C-PWH-SI to S6320-56C-PWH-SI

                fname8031S6720-48Q-SI-48S-AC(537179),        --S6720-48Q-SI-48S-AC        Metro Service Platform for V2R11,delete
                fname8031S6720S-48Q-SI-48S-AC(537180),       --S6720S-48Q-SI-48S-AC       Metro Service Platform for V2R11,delete
                fname8031S6320-48Q-SI-48S-AC(537181),        --S6320-48Q-SI-48S-AC        Metro Service Platform for   V2R*,on 2016.12.24
                fname8031S5730-48C-SI-AC(537182),            --S5730-48C-SI-AC            Metro Service Platform for V2R11
                fname8031S5330-48C-SI-AC(537183),            --S5330-48C-SI-AC            Metro Service Platform for   V2R*,on 2016.12.24
                fname8031S5730-48C-PWR-SI-AC(537184),        --S5730-48C-PWR-SI-AC        Metro Service Platform for V2R11
                fname8031S5730-68C-SI-AC(537185),            --S5730-68C-SI-AC            Metro Service Platform for V2R11
                fname8031S5330-68C-SI-AC(537186),            --S5330-68C-SI-AC            Metro Service Platform for V2R11
                fname8031S5730-68C-PWR-SI-AC(537187),        --S5730-68C-PWR-SI-AC        Metro Service Platform for V2R11
                fname8031S6720-52X-PWH-SI-ACF(537188),       --S6720-52X-PWH-SI-ACF       Metro Service Platform for V2R11
                fname8031S6720-52X-PWH-SI(537189),           --S6720-52X-PWH-SI           Metro Service Platform for V2R11
                fname8031S6320-52X-PWH-SI-ACF(537190),       --S6320-52X-PWH-SI-ACF       Metro Service Platform for   V2R*,on 2016.12.24
                fname8031S6320-52X-PWH-SI(537191),           --S6320-52X-PWH-SI           Metro Service Platform for   V2R*,on 2016.12.24

                fname8031S5720-28P-LI-AC-SEA(537192),        -- Real name S5720-28P-LI-AC     for LSW V2R11 support license for oversea
                fname8031S5720-28P-PWR-LI-AC-SEA(537193),    -- Real name S5720-28P-PWR-LI-AC for LSW V2R11 support license for oversea
                fname8031S5320-28P-LI-AC-SEA(537194),        -- Real name S5320-28P-LI-AC     for LSW V2R11 support license for oversea
                fname8031S5320-28P-PWR-LI-AC-SEA(537195),    -- Real name S5320-28P-PWR-LI-AC for LSW V2R11 support license for oversea
                fname8031S5720-52P-LI-AC-SEA(537196),        -- Real name S5720-52P-LI-AC     for LSW V2R11 support license for oversea
                fname8031S5320-52P-LI-AC-SEA(537197),        -- Real name S5320-52P-LI-AC     for LSW V2R11 support license for oversea
                fname8031S5720-52P-PWR-LI-AC-SEA(537198),    -- Real name S5720-52P-PWR-LI-AC for LSW V2R11 support license for oversea
                fname8031S5320-52P-PWR-LI-AC-SEA(537199),    -- Real name S5320-52P-PWR-LI-AC for LSW V2R11 support license for oversea

                fname8031S5320-12P-LI-BAT(537200),           --S5320-12P-LI-BAT  add for LSW V2R11C10
                fname8031S5330-68C-SI(537201),               --S5330-68C-SI      add for LSW V2R11C10
                fname8031S5730-68C-PWR-SI(537202),           --S5730-68C-PWR-SI  add for LSW V2R11C10

                fname8031S5730-52X-PWH-SI-ACF(537203),       --98010786	S5730-52X-PWH-SI-ACF add for lsw v2r11c10
                fname8031S5730-56C-PWH-SI-AC(537204),        --98010785	S5730-56C-PWH-SI-AC  add for lsw v2r11c10
                fname8031S5730-32C-PWH-SI-AC(537205),        --98010787	S5730-32C-PWH-SI-AC  add for lsw v2r11c10

                fname8031S2320-52TP-EI-DC(537206),      --98010788 S2320-52TP-EI-DC   for lsw v2r11c10
                fname8031S5330-68C-SI-DC(537207),       --98010789 S5330-68C-SI-DC    for lsw  v2r11c10
                fname8031S5730S-48C-EI-AC(537208),      --98010790 S5730S-48C-EI-AC   for lsw  v2r11c10
                fname8031S5730S-48C-PWR-EI(537209),     --98010791 S5730S-48C-PWR-EI  for lsw  v2r11c10
                fname8031S5730S-68C-EI-AC(537210),      --98010792 S5730S-68C-EI-AC   for lsw  v2r11c10
                fname8031S5730S-68C-PWR-EI(537211),     --98010793 S5730S-68C-PWR-EI  for lsw  v2r11c10


                fname8031S5330-36C-HI(537216),          --02351MQK S5330-36C-HI     for lsw  v2r11c50
                fname8031S5730-36C-HI(537217),          --02351MQJ S5730-36C-HI     for lsw  v2r11c50
                fname8031S5730-44C-HI(537218),          --02351MQG S5730-44C-HI     for  lsw v2r11c50
                fname8031S5330-36C-PWH-HI(537219),      --02351MQM S5330-36C-PWH-HI for lsw  v2r11c50
                fname8031S5730-36C-PWH-HI(537220),      --02351MQN S5730-36C-PWH-HI for  lsw v2r11c50
                fname8031S5730-44C-PWH-HI(537221),      --02351LKB S5730-44C-PWH-HI for lsw  v2r11c50
                fname8031S5330-60C-HI(537222),          --02351MQP S5330-60C-HI     for  lsw v2r11c50
                fname8031S5730-60C-HI(537223),          --02351MQR S5730-60C-HI     for  lsw v2r11c50
                fname8031S5730-68C-HI(537224),          --02351MQT S5730-68C-HI     for  lsw v2r11c50
                fname8031S5730-60C-PWH-HI(537225),      --02351MQV S5730-60C-PWH-HI for  lsw v2r11c50
                fname8031S5730-68C-PWH-HI(537226),      --02351LKE S5730-68C-PWH-HI for  lsw v2r11c50
                fname8031S6720-50L-HI-48S(537227),      --02351MXN S6720-50L-HI-48S for  lsw v2r11c50
                fname8031S6320-50L-HI-48S(537228),      --02351MXP S6320-50L-HI-48S for  lsw v2r11c50
                fname8031S6720-30L-HI-24S(537229),      --02351MXR S6720-30L-HI-24S for  lsw v2r11c50
                fname8031S6320-30L-HI-24S(537230),      --02351MXS S6320-30L-HI-24S for  lsw v2r11c50

                fname8031S5720I-12X-SI-AC(537231),             --98010794 S5720I-12X-SI-AC for lsw v2r12c00
                fname8031S5720I-12X-PWH-SI-DC(537232),   --98010795 S5720I-12X-PWH-SI-DC for lsw v2r12c00
                fname8031S5720I-28X-SI-AC(537233),             --98010796 S5720I-28X-SI-AC for lsw v2r12c00
                fname8031S5720I-28X-PWH-SI-AC(537234),   --98010797 S5720I-28X-PWH-SI-AC for lsw v2r12c00
                fname8031S5320-52X-SI-AC-V1(537235),        -- Real name S5320-52X-SI-AC for LSW V2R11C10 from S5320-52X-LI-AC
                fname8031S5320-52X-SI-DC-V1(537236),        -- Real name S5320-52X-SI-DC for LSW V2R11C10 from S5320-52X-LI-DC
                fname8031S5320-52P-SI-AC-V1(537237),        -- Real name S5320-52P-SI-AC for LSW V2R11C10 from S5320-52P-LI-AC
                fname8031S5320-52P-SI-DC-V1(537238),        -- Real name S5320-52P-SI-DC for LSW V2R11C10 from S5320-52P-LI-AC
                fname8031S5300-52P-LI-DC-V1(537239),        -- Real name S5300-52P-LI-DC for LSW V2R11C10 from S5320-52P-LI-AC
                fname8031S5320-36C-EI-28S-AC-V1(537240),    -- Real name S5320-36C-EI-28S-AC for LSW V2R11C10 from S5320-28X-LI-24S-AC
                fname8031S5320-36C-EI-28S-DC-V1(537241),    -- Real name S5320-36C-EI-28S-DC for LSW V2R11C10 from S5320-28X-LI-24S-DC
                fname8031S5730-44C-HI-24S(537242),          --02351XFR S5730-44C-HI-24S     for lsw v2r13c00
                fname8031S5730-60C-HI-48S(537243),          --02351XFS S5730-60C-HI-48S     for lsw v2r13c00
                fname8031S5730-68C-HI-48S(537244),          --02351XFT S5730-68C-HI-48S     for lsw v2r13c00
                fname8031S5730-36C-HI-24S(537245),          --02351XFQ S5730-36C-HI-24S     for lsw v2r13c00
                fname8031S5720I-12X-PWH-SI-AC(537246),      --98010811 S5720I-12X-PWH-SI-AC for lsw v2r13c00
                fname8031S5720I-10X-PWH-SI-AC(537247),      --S5720I-10X-PWH-SI-AC for lsw v2r13c00

                fname8031S1600-8(537248),                   --S1600-8 for lsw V2R12C10
                fname8031S1600-16(537249),                  --S1600-16 for lsw V2R12C10
                fname8031S1600-24(537250),                  --S1600-24 for lsw V2R12C10
                fname8031S2600-10P(537251),                 --S2600-10P for lsw V2R12C10
                fname8031S2600-10P-PWR(537252),             --S2600-10P-PWR for lsw V2R12C10
                fname8031S2600-28P(537253),                 --S2600-28P for lsw V2R12C10
                fname8031S2600-28P-PWR(537254),             --S2600-28P-PWR for lsw V2R12C10
                fname8031S3600-28P(537255),                 --S3600-28P for lsw V2R12C10
                fname8031S3600-28P-PWR(537256),             --S3600-28P-PWR for lsw V2R12C10
                fname8031S3600-52P(537257),                 --S3600-52P for lsw V2R12C10
                fname8031S3600-52P-PWR(537258),             --S3600-52P-PWR for lsw V2R12C10
                fname8031S1700-16-AC(537259),               --S1700-16-AC for lsw V2R12C10
                fname8031S1700-24R(537260),                 --S1700-24R for lsw V2R12C10
                fname8031S5330-60C-HI-48S(537261),          --S5330-60C-HI-48S for lsw V2R13C00
                fname8031S5330-36C-HI-24S(537262),          --S5330-36C-HI-24S for lsw V2R13C00
                fname8031S5720-52X-LI-48S-AC(537263),       --S5720-52X-LI-48S-AC for lsw V2R13C00
                fname8031S5320-52X-LI-48S-AC(537264),       --S5320-52X-LI-48S-AC for lsw V2R13C00
                fname8031S5320-52X-LI-48S-DC(537265),       --S5320-52X-LI-48S-DC for lsw V2R13C00
                fname8031S5320-52X-SI-48S(537266),          --S5320-52X-SI-48S for lsw V2R13C00
                fname8031S5720-52X-SI-48S(537267),          --S5720-52X-SI-48S for lsw V2R13C00
                fname8031S6320-26Q-LI-24S(537268),          --S6320-26Q-LI-24S for lsw V2R12C00
                fname8031S5720I-10X-PWH-SI-AC-Sea(537269),     --S5720I-10X-PWH-SI-AC oversea for V2R13C00
                fname8031S5720I-6X-PWH-SI-AC(537270),              --S5720I-6X-PWH-SI-AC for V2R13C00

                fname8031S1820EC-8G(537271),                --S1820EC-8G           for LSW V2R12C20
                fname8031S1820EC-24G(537272),               --S1820EC-24G          for LSW V2R12C20
                fname8031S5820EC-10P(537273),               --S5820EC-10P          for LSW V2R12C20
                fname8031S5820EC-10P-PWR(537274),           --S5820EC-10P-PWR      for LSW V2R12C20
                fname8031S5820EC-28P(537275),               --S5820EC-28P          for LSW V2R12C20
                fname8031S5820EC-28P-PWR(537276),           --S5820EC-28P-PWR      for LSW V2R12C20
                fname8031S1720-10GF-2P(537277),             --S1720-10GF-2P        for LSW V2R12C20
                fname8031S1720-10GF-PWR-2P(537278),         --S1720-10GF-PWR-2P    for LSW V2R12C20
                fname8031S1720-28GFR-4P(537279),            --S1720-28GFR-4P       for LSW V2R12C20
                fname8031S1720-28GFR-PWR-4P(537280),        --S1720-28GFR-PWR-4P   for LSW V2R12C20
                fname8031S1720-52GFR-4P(537281),            --S1720-52GFR-4P       for LSW V2R12C20
                fname8031S1720-52GFR-PWR-4P(537282),        --S1720-52GFR-PWR-4P   for LSW V2R12C20
                fname8031S5720SV2-28P-LI-AC(537283),        --S5720SV2-28P-LI-AC   for LSW V2R12C20
                fname8031S5720SV2-52P-LI-AC(537284),        --S5720SV2-52P-LI-AC   for LSW V2R12C20
                fname8031S6730-H48X6C(537285),           --S6730-H48X6C for LSW V2R19C00
                fname8031S6330-H48X6C(537286),           --S6330-H48X6C for LSW V2R19C00
                fname8031S6730-H24X6C(537287),           --S6730-H24X6C for LSW V2R19C00
                fname8031S6330-H24X6C(537288),            --S6330-H24X6C for LSW V2R19C00
                fname8031S5720-28X-PWR-LI-ACF-740(537289),       --S5720-28X-PWR-LI-ACF(740W) for LSW V2R13C00
                --fname8031S6750-36L-HI-36S(537290),         S6750-36L-HI-36S for V2R19C00
                --fname8031S6350-36L-HI-36S(537291),         S6350-36L-HI-36S for V2R19C00
                --fname8031S2720S-12TP-EI-AC(537292),         S2720S-12TP-EI-AC for V2R19C00
                --fname8031S2720S-12TP-PWR-EI-AC(537293),     S2720S-12TP-PWR-EI-AC for V2R19C00
                --fname8031S2720S-52TP-EI-AC(537294),         S2720S-52TP-EI-AC for V2R19C00
                --fname8031S2720S-52TP-PWR-EI-AC(537295),     S2720S-52TP-PWR-EI-AC for V2R19C00
                --fname8031S2720S-28TP-PWR-EI-L-AC(537296),   S2720S-28TP-PWR-EI-L-AC for V2R19C00
                --fname8031S2720S-28TP-PWR-EI-AC(537297),     S2720S-28TP-PWR-EI-AC for V2R19C00
                --fname8031S2720S-28TP-EI-AC(537298),         S2720S-28TP-EI-AC for V2R19C00
                --fname8031S5730-32C-PWH-SI(537299),         S5730-32C-PWH-SI for V2R19C00
                fname8031S5731-H24T4XC(537300),                 --S5731-H24T4XC for v2r19c00
                fname8031S5731-H48T4XC(537301),                 --S5731-H48T4XC for v2r19c00
                fname8031S5731-H24P4XC(537302),                 --S5731-H24P4XC for v2r19c00
                fname8031S5731-H48P4XC(537303),                --S5731-H48P4XC for v2r19c00
                fname8031S5720I-S4T2S-A(537304),                --S5720I-S4T2S-A for v2r19c00
                fname8031S5720I-S8U2X-A(537305),               --S5720I-S8U2X-A for v2r19c00
                fname8031S5720I-S8U2X-A1(537306),             --S5720I-S8U2X-A1 for v2r19c00
                fname8031S5731-S24T4X(537307),                  --S5731-S24T4X(24*10/100/1000BASE-T ports,4*10GE SFP+ ports,without power module) for v2r19c00
                fname8031S5731S-S24T4X-A(537308),            --S5731S-S24T4X-A(24*10/100/1000BASE-T ports,4*10GE SFP+ ports,1*600W AC power) for v2r19c00
                fname8031S5331-H24T4XC(537309),               --S5331-H24T4XC(24*10/100/1000BASE-T ports,4*10GE SFP+ ports,1*expansion slot,without power module)  for v2r19c00
                fname8031S5731-S24P4X(537310),                 --S5731-S24P4X(24*10/100/1000BASE-T ports,4*10GE SFP+ ports,1*expansion slot,PoE+, without power module)  for v2r19c00
                fname8031S5731S-S24P4X-A(537311),           --S5731S-S24P4X-AA (24*10/100/1000BASE-T ports,4*10GE SFP+ ports,1*expansion slot,PoE+,1*1000W PoE AC power) for v2r19c00
                fname8031S5331-H24P4XC(537312),              --S5331-H24P4XC(24*10/100/1000BASE-T ports,4*10GE SFP+ ports,1*expansion slot,PoE+,without power module)  for v2r19c00
                fname8031S5731-S48T4X(537313),                 --S5731-S48T4X(48*10/100/1000BASE-T ports,4*10GE SFP+ ports,1*expansion slot,without power module)  for v2r19c00
                fname8031S5731S-S48T4X-A(537314),           --S5731S-S48T4X-A(48*10/100/1000BASE-T ports,4*10GE SFP+ ports,1*expansion slot,1*600W AC power)   for v2r19c00
                fname8031S5331-H48T4XC(537315),              --S5331-H48T4XC(48*10/100/1000BASE-T ports,4*10GE SFP+ ports,1*expansion slot,without power module)  for v2r19c00
                fname8031S5731-S48P4X(537316),                 --S5731-S48P4X (48*10/100/1000BASE-T ports,4*10GE SFP+ ports,1*expansion slot,PoE+,without power module)
                fname8031S5731S-S48P4X-A(537317),           --S5731S-S48P4X-A(48*10/100/1000BASE-T ports,4*10GE SFP+ ports,1*expansion slot,PoE+,1*1000W PoE AC power)
                fname8031S5331-H48P4XC(537318),              --S5331-H48P4XC(48*10/100/1000BASE-T ports,4*10GE SFP+ ports,1*expansion slot,PoE+,without power module)
                fname8031S5732-H24S6Q(537319),                --5732-H24S6Q (20*GE SFP ports,4*10GE SFP+ ports,6*40GE QSFP ports,without power module)
                fname8031S5332-H24S6Q(537320),                --S5332-H24S6Q (20*GE SFP ports,4*10GE SFP+ ports,6*40GE QSFP ports,without power module)
                fname8031S5732-H48S6Q(537321),                --S5732-H48S6Q (44*GE SFP ports,4*10GE SFP+ ports,6*40GE QSFP ports,without power module)
                fname8031S5332-H48S6Q(537322),                --S5332-H48S6Q (44*GE SFP ports,4*10GE SFP+ ports,6*40GE QSFP ports,without power module)
                fname8031S6730-S24X6Q(537323),                --S6730-S24X6Q (24*10GE SFP+ ports,6*40GE QSFP ports,without power module)
                fname8031S6730S-S24X6Q-A(537324),          --S6730S-S24X6Q-A (24*10GE SFP+ ports,6*40GE QSFP ports,without power module)
                fname8031S5731S-H24T4XC-A(537325),       --S5731S-H24T4XC-A (24*10/100/1000BASE-T ports,4*10GE SFP+ ports,1*expansion slot,1*600W AC power)
                fname8031S5731S-H48T4XC-A(537326),       --S5731S-H48T4XC-A (48*10/100/1000BASE-T ports,4*10GE SFP+ ports,1*expansion slot,1*600W AC power)
           
                fname8031S5735-L24T4S-A(537327),                  --S5735-L24T4S-A(24*10/100/1000BASE-T ports,4*GE SFP ports,AC 110/220V)
                fname8031S5735S-L24T4S-A(537328),                --S5735S-L24T4S-A(24*10/100/1000BASE-T ports,4*GE SFP ports,AC 110/220V)
                fname8031S1730S-S24T4S-A(537330),                --S1730S-S24T4S-A(24*10/100/1000BASE-T ports,4*GE SFP ports,AC 110/220V)
                fname8031S5735S-L24T4S-MA(537329),             --S5735S-L24T4S-MA (24*10/100/1000BASE-T ports,4*GE SFP ports,AC 110/220V)
                fname8031S5735S-L24FT4S-A(537331),             --S5735S-L24FT4S-A(12 Ethernet 10/100 ports,12 Ethernet 10/100/1000 ports,4*GE SFP ports,AC 110/220V)
                fname8031S5735-L12T4S-A(537332),                  --S5735-L12T4S-A(12*10/100/1000BASE-T ports,4*GE SFP ports,AC 110/220V)
                fname8031S5735S-L12T4S-A(537333),                --S5735S-L12T4S-A(12*10/100/1000BASE-T ports,4*GE SFP ports,AC 110/220V)
                fname8031S5335-L12T4S-A(537334),                  --S5335-L12T4S-A(12*10/100/1000BASE-T ports,4*GE SFP ports,AC 110/220V)
                fname8031S5735-L24T4X-A(537335),                  --S5735-L24T4X-A(24*10/100/1000BASE-T ports,4*10GE SFP+ ports,AC 110/220V)
                fname8031S5735S-L24T4X-A(537336),               --S5735S-L24T4X-A(24*10/100/1000BASE-T ports,4*10GE SFP+ ports,AC 110/220V)
                fname8031S5335-L24T4X-A(537337),                  --S5335-L24T4X-A(24*10/100/1000BASE-T ports,4*10GE SFP+ ports4,AC power support,front access)
                fname8031S5735-L12P4S-A(537338),                  --S5735-L12P4S-A(12*10/100/1000BASE-T ports,4*GE SFP ports,PoE+,AC 110/220V)
                fname8031S5735S-L12P4S-A(537339),               --S5735S-L12P4S-A(12*10/100/1000BASE-T ports,4*GE SFP ports,PoE+,AC 110/220V)
                fname8031S5335-L12P4S-A(537340),                  --S5335-L12P4S-A(12*10/100/1000BASE-T ports,4*GE SFP ports,PoE+,AC 110/220V)
                fname8031S5735-L24P4S-A(537341),                  --S5735-L24P4S-A(24*10/100/1000BASE-T ports,4*GE SFP ports,PoE+,AC 110/220V)
                fname8031S5735S-L24P4S-A(537342),               --S5735S-L24P4S-A(24*10/100/1000BASE-T ports,4*GE SFP ports,PoE+,AC 110/220V)
                fname8031S1730S-S24P4S-A(537344),               --S1730S-S24P4S-A(24*10/100/1000BASE-T ports,4*GE SFP ports,PoE+,AC 110/220V)
                fname8031S5735S-L24P4S-MA(537343),             --S5735S-L24P4S-MA(24*10/100/1000BASE-T ports,4*GE SFP ports,PoE+,AC 110/220V)
                fname8031S5735-L24P4X-A(537345),                  --S5735-L24P4X-A(24*10/100/1000BASE-T ports,4*10GE SFP+ ports,PoE+,AC 110/220V)
                fname8031S5735S-L24P4X-A(537346),               --S5735S-L24P4X-A(24*10/100/1000BASE-T ports,4*10GE SFP+ ports,PoE+,AC 110/220V)
                fname8031S5335-L24P4X-A(537347),                  --S5335-L24P4X-A(24*10/100/1000BASE-T ports,4*10GE SFP+ ports,PoE+,AC 110/220V)
                fname8031S5335-L32ST4X-A(537348),               --S5335-L32ST4X-A(24*GE SFP ports,8*10/100/1000BASE-T ports,4*10GE SFP+ ports,AC power support,front access)
                fname8031S5735-L32ST4X-A(537349),               --S5735-L32ST4X-A(24*GE SFP ports,8*10/100/1000BASE-T ports,4*10GE SFP+ ports,AC 110/220V)
                fname8031S5735S-L32ST4X-A(537350),             --S5735S-L32ST4X-A(24*GE SFP ports,8*10/100/1000BASE-T ports,4*10GE SFP+ ports,AC 110/220V)
                fname8031S5735-S32ST4X(537351),                   --S5735-S32ST4X(24*GE SFP ports,8*10/100/1000BASE-T ports,4*10GE SFP+ ports,without power module)
                fname8031S5735S-S32ST4X-A(537353),              --S5735-S32ST4X(24*GE SFP ports,8*10/100/1000BASE-T ports,4*10GE SFP+ ports,without power module)
                fname8031S5335-S32ST4X(537352),                   --S5335-S32ST4X(24*GE SFP ports,8*10/100/1000BASE-T ports,4*10GE SFP+ ports,without power module)
                fname8031S5735-L48T4S-A(537354),                  --S5735-L48T4S-A(48*10/100/1000BASE-T ports,4*GE SFP ports,AC 110/220V)
                fname8031S5735S-L48T4S-A(537355),               --S5735S-L48T4S-A(12 Ethernet 10/100 ports,12 Ethernet 10/100/1000 ports,4*GE SFP ports,AC 110/220V)
                fname8031S1730S-S48T4S-A(537356),               --S1730S-S48T4S-A(48*10/100/1000BASE-T ports,4*GE SFP ports,AC 110/220V)
                fname8031S5735S-L48FT4S-A(537357),             --S5735S-L48FT4S-A(24 Ethernet 10/100 ports,24 Ethernet 10/100/1000 ports,4*GE SFP ports,AC 110/220V)
                fname8031S5735-L48T4X-A(537358),                 --S5735-L48T4X-A(24*10/100/1000BASE-T ports,(24*10/100BASE-T ports,4*10GE SFP+ ports,AC 110/220V)
                fname8031S5735S-L48T4X-A(537359),               --S5735S-L48T4X-A(48*10/100/1000BASE-T ports,4*10GE SFP+ ports,AC 110/220V)
                fname8031S5735-S24T4X(537360),                    --S5735-S24T4X(24*10/100/1000BASE-T ports,4*10GE SFP+ ports,without power module)
                fname8031S5335-S24T4X(537361),                    --S5335-S24T4X(24*10/100/1000BASE-T ports,4*10GE SFP+ ports,without power module)
                fname8031S5735S-S24T4S-A(537362),               --S5735S-S24T4S-A(24*10/100/1000BASE-T ports,4*10GE SFP+ ports,1*60W AC power)
                fname8031S5735-S24P4X(537363),                    --S5735-S24P4X(24*10/100/1000BASE-T ports,4*GE SFP ports, PoE+,without power module)
                fname8031S5335-S24P4X(537364),                    --S5335-S24P4X(24*10/100/1000BASE-T ports,4*10GE SFP+ ports,PoE+,without power module)
                fname8031S5735-S48T4X(537365),                    --S5735-S48T4X(48*10/100/1000BASE-T ports,4*10GE SFP+ ports,without power module)
                fname8031S5335-S48T4X(537366),                     --S5335-S48T4X(48*10/100/1000BASE-T ports,4*10GE SFP+ ports,without power module)
                fname8031S5735S-S48T4S-A(537367),               --S5735S-S48T4S-A(48*10/100/1000BASE-T ports,4*GE SFP ports,1*60W AC power)
                fname8031S5735-S48P4X(537368),                     --S5735-S48P4X(48*10/100/1000BASE-T ports,4*GE SFP ports,PoE+,without power module)
                fname8031S5335-S48P4X(537369),                    --S5335-S48P4X(48*10/100/1000BASE-T ports,4*10GE SFP+ ports,PoE+,without power module)
                fname8031S5735-L48P4X-A(537370),                 --S5735-L48P4X-A(48*10/100/1000BASE-T ports,4*10GE SFP+ ports,PoE+,1*1000W PoE AC power)
                fname8031S5735S-L48P4X-A(537371),               --S5735S-L48P4X-A(48*10/100/1000BASE-T ports,4*10GE SFP+ ports,PoE+,1*1000W PoE AC power)
                fname8031S5735S-L48P4S-A(537372),               --S5735S-L48P4S-A(48*10/100/1000BASE-T ports,4*GE SFP ports,PoE+,1*1000W PoE AC power)
                fname8031S5735-S48S4X(537373),                     --S5735-S48S4X(48*GE SFP ports,,4*10GE SFP+ ports,PoE+,without power module)
                fname8031S5335-S48S4X(537374),                      --S5335-S48S4X(48*GE SFP ports,,4*10GE SFP+ ports,PoE+,without power module)
                fname8031S5735-S4T2X-IA150G1(537375),           --S5735-S4T2X-IA150G1 (4*10/100/1000BASE-T ports, 2*10GE SFP+ ports, AC power supply)
                fname8031S5735-S8P2X-IA200G1(537376),           --S5735-S8P2X-IA200G1 (8*10/100/1000BASE-T ports, 2*10GE SFP+ ports, PoE+, AC power supply)
                fname8031S5735-S8P2X-IA200H1(537377),           --S5735-S8P2X-IA200H1 (8*10/100/1000BASE-T ports, 2*10GE SFP+ ports, PoE+, support for solar power, AC power supply)
                fname8031S5731S-H24T4S-A(537378),                  --S5731S-H24T4S-A(24*10/100/1000BASE-T ports,4*GE SFP ports,1*150W AC power)
                fname8031S5731S-H48T4S-A(537379),                  --S5731S-H48T4S-A(48*10/100/1000BASE-T ports,4*GE SFP ports,1*150W AC power)
                fname8031S1700-8-AC(537380),                             -- S1700-8-AC  for V2R19C00
                fname8031S5731S-H24T4X-A(537381),                 --S5731S-H24T4X-A(24*10/100/1000BASE-T ports,4*10GE SFP+ ports,1*150W AC power)
                fname8031S5731S-H48T4X-A(537382),                  --S5731S-H48T4X-A(48*10/100/1000BASE-T ports,4*10GE SFP+ ports,1*150W AC power)
                fname8031S6730S-H24X6C-A(537383),                 --S6730S-H24X6C-A(24*10GE SFP+ ports,6*100GE QSFP28 ports,1*600W AC power)
                fname8031S1730S-H24T4S-A(537384),                 --S1730S-H24T4S-A(24*10/100/1000BASE-T ports, 4*GE SFP ports, AC 110/220V)
                fname8031S1730S-S24T4X-A(537385),                 --S1730S-S24T4X-A(24*10/100/1000BASE-T ports, 4*10GE SFP+ ports, AC 110/220V)
                fname8031S1730S-H48T4S-A(537386),                 --S1730S-H48T4S-A(48*10/100/1000BASE-T ports, 4*GE SFP ports, AC 110/220V)
                fname8031S5335-L48T4X-A(537387),                    --S5335-L48T4X-A(48*10/100/1000BASE-T ports, 4*10GE SFP+ ports, AC 110/220V)
                fname8031S1730S-S48P4S-A(537388),                 --S1730S-S48P4S-A(48*10/100/1000BASE-T ports,4*GE SFP ports,PoE+,1*1000W PoE AC power)
                fname8031S6730-H48X6C-K(537389),                 --S6730-H48X6C-K (48*10GE SFP+ ports, 6*40GE QSFP28 ports, optional license for upgrade to 6*100GE QSFP28, without power module) for V2R19C!0
                fname8031S6730-H24X6C-K(537390),                 --S6730-H24X6C-K (24*10GE SFP+ ports, 6*100GE QSFP28 ports, without power module) for V2R19C!0
                fname8031S5731-H48P4XC-K(537391),               --S5731-H48P4XC-K(48*10/100/1000BASE-T ports, 4*10GE SFP+ ports, 1*expansion slot, PoE+, without power module) for V2R19C!0
                fname8031S5731-H24T4XC-K(537392),               --S5731-H24T4XC-K (24*10/100/1000BASE-T ports, 4*10GE SFP+ ports, 1*expansion slot, without power module) for V2R19C!0
                fname8031S5731-H24P4XC-K(537393),               --S5731-H24P4XC-K (24*10/100/1000BASE-T ports, 4*10GE SFP+ ports, 1*expansion slot, PoE+, without power module) for V2R19C!0
                fname8031S5732-H24S6Q-K(537394),                 --S5732-H24S6Q-K (20*GE SFP ports,4*10GE SFP+ ports,6*40GE QSFP ports,with Pluggable dual power module) for V2R19C!0
                fname8031S5732-H48S6Q-K(537395),                 --S5732-H48S6Q-K (44*GE SFP ports,4*10GE SFP+ ports,6*40GE QSFP ports,with pluggable dual power module) for V2R19C!0
                fname8031S5732-H48UM2CC(537396),                 --S5732-H48UM2CC(48 Ethernet 100M/1/2.5/5/10G ports, 4*25GE SFP28 ports + 2*40GE or 2*100GE QSFP28 ports, 1*expansion slot, PoE++, without power module) for V2R19C20
                fname8031S5732-H24UM2CC(537397),                 --S5732-H24UM2CC(24 Ethernet 100M/1/2.5/5/10G ports, 4*25GE SFP28 ports + 2*40GE or 2*100GE QSFP28 ports, 1*expansion slot, PoE++, without power module) for V2R19C20
                fname8031S5332-H24UM2CC(537398),                 --S5332-H24UM2CC (24*100M/1G/2.5G/5G/10G Ethernet ports, 4*25GE SFP28 + 2*40GE ports or 2*100GE QSFP28 ports, 1*expansion slot, PoE++, without power module) for V2R19C20
                fname8031S5732-H48XUM2CC(537399),                 --S5732-H48XUM2CC (24*100M/1G/2.5G/5G/10G Ethernet ports, 24*10GE SFP+ ports, 4*25GE SFP28 + 2*40GE ports or 2*100GE QSFP28 ports, 1*expansion slot, PoE++, without power module) for V2R19C20
                fname8031S5735-S24T4X-I(537400),                    --S5735-S24T4X-I (24*10/100/1000BASE-T ports, 4*10GE SFP+ ports, without power module) for V2R19C20
                fname8031S5735S-S24T4X-A(537415),                    --S5735S-S24T4X-A (24*10/100/1000BASE-T ports, 4*10GE SFP+ ports, 1*60W AC power module) for V2R19C20
                fname8031S5735S-S48T4X-A(537416),                    --S5735S-S48T4X-A (48*10/100/1000BASE-T ports, 4*10GE SFP+ ports, 1*60W AC power module) for V2R19C20
                fname8031S5735S-S24P4X-A(537417),                    --S5735S-S24P4X-A (24*10/100/1000BASE-T ports, 4*10GE SFP+ ports, PoE+, one AC power module) for V2R19C20
                fname8031S5735S-S48P4X-A(537418),                    --S5735S-S48P4X-A (48*10/100/1000BASE-T ports, 4*10GE SFP+ ports, PoE+, one AC power module) for V2R19C20
                fname8031S5735S-L48T4S-MA(537419),                    --S5735S-L48T4S-MA (48*10/100/1000BASE-T ports, 4*GE SFP ports, AC power) for V2R19C20
                fname8031S1730S-S24T4S-MA(537420),                    --S1730S-S24T4S-MA (24*10/100/1000BASE-T ports, 4*GE SFP ports, AC power) for V2R19C20
                fname8031S1730S-S24P4S-MA(537421),                    --S1730S-S24P4S-MA (24*10/100/1000BASE-T ports, 4*GE SFP ports, PoE+, AC power) for V2R19C20
                fname8031S6730-H28Y4C(537401),                                            --S6730-H28Y4C (28*25GE SFP28 ports, 4*100GE QSFP28 ports, without power module) for V2R20C00
                fname8031S6330-H28Y4C(537402),                                            --S6330-H28Y4C (28*25GE SFP28 ports, 4*100GE QSFP28 ports, without power module) for V2R20C00
                fname8031S6730-H24X4Y4C(537403),                                        --S6730-H24X4Y4C (24*10GE SFP+ ports, 4*25GE SFP28 ports, 4*100GE QSFP28 ports, without power module) for V2R20C00
                fname8031S6330-H24X4Y4C(537404),                                        --S6330-H24X4Y4C (24*10GE SFP+ ports, 4*25GE SFP28 ports, 4*100GE QSFP28 ports, without power module) for V2R20C00
                fname8031S6730S-H24X4Y4C-A(537405),                                  --S6730S-H24X4Y4 bundle (24*10GE SFP+ ports, 4*25GE SFP28 ports, 4*100GE QSFP28 ports, 1*300W AC power module) for V2R20C00
                fname8031S6730S-S24X4Y4Q-A(537406),                                 --S6730S-S24X4Y4Q bundle (24*10GE SFP+ ports, 4*25GE SFP28 ports, 4*40GE QSFP+ ports, 1*300W AC power module) for V2R20C00
                fname8031S5732-H24S4Y4Q(537407),                                        --S5732-H24S4Y4Q (24*GE SFP ports, 4*25GE SFP28 ports, 4*40GE QSFP+ ports, without power module) for V2R20C00
                fname8031S5332-H24S4Y4Q(537408),                                        --S5232-H24S4Y4Q (24*GE SFP ports, 4*25GE SFP28 ports, 4*40GE QSFP+ ports, without power module) for V2R20C00
                fname8031S5735-L24T4X-D(537409),                                          --S5735-L24T4X-D (24*10/100/1000BASE-T ports, 4*10GE SFP+ ports, DC power) for V2R20C00
                fname8031S5335-L24T4X-D(537410),                                          --S5335-L24T4X-D (24*10/100/1000BASE-T ports, 4*10GE SFP+ ports, DC power, front access) for V2R20C00
                fname8031S5735-L12T4S-D(537411),                                          --S5735-L12T4S-D (12*10/100/1000BASE-T ports, 4*GE SFP ports, DC power) for V2R20C00
                fname8031S5335-L12T4S-D(537412),                                          --S5335-L12T4S-D (12*10/100/1000BASE-T ports, 4*GE SFP ports, DC power) for V2R20C00
                fname8031S5735-L32ST4X-D(537413),                                        --S5735-L32ST4X-D (24*GE SFP ports, 8*10/100/1000BASE-T ports, 4*10GE SFP+ ports, DC power) for V2R20C00
                fname8031S5335-L32ST4X-D(537414),                                        --S5335-L32ST4X-D (24*GE SFP ports, 8*10/100/1000BASE-T ports, 4*10GE SFP+ ports, DC power, front access) for V2R20C00
                fname8031S6730-H28Y4C-K(537426),                                          --S6730-H28Y4C-K (24*GE SFP ports, 4*25GE SFP28 ports, 4*40GE QSFP+ ports, without power module) for V2R20C00	        
                fname8031S5732-H24UM2C-K(537427),                                       --S5732-H24UM2C-K 2.5G Bundle(24*100M/1G/2.5G Ethernet ports, Optional RTU upgrade to 5/10G, 4*25GE SFP28 + 2*40GE or 2*100GE QSFP28 ports, 1*expansion slot, PoE++, 1*1000W AC power) for V2R20C00	  
                fname8031S5732-H48UM2C-K(537428),                                       --S5732-H48UM2C-K 2.5G Bundle(48*100M/1G/2.5G Ethernet ports, Optional RTU upgrade to 5/10G, 4*25GE SFP28 + 2*40GE or 2*100GE QSFP28 ports, 1*expansion slot, PoE++, 1*1000W AC power) for V2R20C00

                fname8031S5736-S24UM4XC(537429), --S5736-S24UM4XC Base(24*100M/1G Ethernet ports,Optional RTU upgrade to 2.5/5/10G, 4*10GE SFP+ ports, 1*expansion slot, PoE++, without power module) for V2R20C00
                fname8031S5336-S24UM4XC(537430), --S5336-S24UM4XC Base(24*100M/1G Ethernet ports,Optional RTU upgrade to 2.5/5/10G, 4*10GE SFP+ ports, 1*expansion slot, PoE++, without power module) for V2R20C00
                fname8031S5736-S24T4XC(537431), --S5736-S24T4XC (24*10/100/1000BASE-T ports, 4*10GE SFP+ ports, 1*expansion slot, without power module) for V2R20C00
                fname8031S5336-S24T4XC(537432), --S5336-S24T4XC (24*10/100/1000BASE-T ports, 4*10GE SFP+ ports, 1*expansion slot, without power module) for V2R20C00
                fname8031S5735S-H24T4XC-A(537433), --S5735S-H24T4XC bundle(24*10/100/1000BASE-T ports, 4*10GE SFP+ ports, 1*expansion slot, one AC power module) for V2R20C00
                fname8031S5736-S48T4XC(537434), --S5736-S48T4XC (48*10/100/1000BASE-T ports, 4*10GE SFP+ ports, 1*expansion slot, without power module) for V2R20C00
                fname8031S5336-S48T4XC(537435), --S5336-S48T4XC (48*10/100/1000BASE-T ports, 4*10GE SFP+ ports, 1*expansion slot, without power module) for V2R20C00
                fnameS5735S-H48T4XC-A(537436), --S5735S-H48T4XC bundle(48*10/100/1000BASE-T ports, 4*10GE SFP+ ports, 1*expansion slot, one AC power module) for V2R20C00
                fname8031S5736-S24U4XC(537437), --S5736-S24U4XC (24*10/100/1000BASE-T ports, 4*10GE SFP+ ports, 1*expansion slot, PoE++, without power module) for V2R20C00
                fname8031S5336-S24U4XC(537438), --S5336-S24U4XC (24*10/100/1000BASE-T ports, 4*10GE SFP+ ports, 1*expansion slot, PoE++, without power module) for V2R20C00
                fname8031S5735S-H24U4XC-A(537439), --S5735S-H24U4XC bundle(24*10/100/1000BASE-T ports, 4*10GE SFP+ ports, 1*expansion slot, PoE++, one AC power module) for V2R20C00
                fname8031S5736-S48U4XC(537440), --S5736-S48U4XC (48*10/100/1000BASE-T ports, 4*10GE SFP+ ports, 1*expansion slot, PoE++, without power module) for V2R20C00
                fname8031S5336-S48U4XC(537441), --S5336-S48U4XC (48*10/100/1000BASE-T ports, 4*10GE SFP+ ports, 1*expansion slot, PoE++, without power module) for V2R20C00
                fname8031S5735S-H48U4XC-A(537442), --S5735S-H48U4XC bundle(48*10/100/1000BASE-T ports, 4*10GE SFP+ ports, 1*expansion slot, PoE++, one AC power module) for V2R20C00
                fname8031S5736-S24S4XC(537443), --S5736-S24S4XC (24*GE SFP ports, 4*10GE SFP+ ports, 1*expansion slot, without power module) for V2R20C00
                fname8031S5336-S24S4XC(537444), --S5336-S24S4XC (24*GE SFP ports, 4*10GE SFP+ ports, 1*expansion slot, without power module) for V2R20C00
                fname8031S5735S-H24S4XC-A(537445), --S5735S-H24S4XC bundle(24*GE SFP ports, 4*10GE SFP+ ports, 1*expansion slot, one AC power module) for V2R20C00
                fname8031S5736-S48S4XC(537446), --S5736-S48S4XC (48*GE SFP ports, 4*10GE SFP+ ports, 1*expansion slot, without power module) for V2R20C00
                fname8031S5336-S48S4XC(537447), --S5336-S48S4XC (48*GE SFP ports, 4*10GE SFP+ ports, 1*expansion slot, without power module) for V2R20C00
                fname8031S5336-S48S4X-A(537448), --S5336-S48S4X-A Base(48*GE SFP ports,Optional RTU upgrade to 10G, 4*10GE SFP+ ports, AC power, front access) for V2R20C00
                fname8031S5336-S48S4X-D(537449), --S5336-S48S4X-D Base(48*GE SFP ports,Optional RTU upgrade to 10G, 4*10GE SFP+ ports, DC power, front access) for V2R20C00
                fname8031S6720S-S52X-A(537450), --S6720S-S52X-A(52*10GE SFP+ ports, AC power, front access) for V2R20C00
                fname8031S6720S-S24S28X-A(537451), --S6720S-S24S28X-A(24*GE SFP ports,28*10GE SFP+ ports, AC power, front access) for V2R20C00
                fname8031S5720-52X-LI-48S-AC1(537452), --S5720-52X-LI-48S-AC1 (46*GE SFP ports, 2 of which are 10/100/1000BASE-T + SFP combo ports, 4*10GE SFP+ ports, AC power supply) for V2R20C00
                fname8031S5720-52X-LI-48S-DC1(537453), --S5720-52X-LI-48S-DC1 (46*GE SFP ports, 2 of which are 10/100/1000BASE-T + SFP combo ports, 4*10GE SFP+ ports, DC power supply) for V2R20C00
                fname8031S5720-52X-LI-24S-AC1(537454), --S5720-52X-LI-24S-AC1 (24*FE SFP ports,22*GE SFP ports, 2 of which are 10/100/1000BASE-T + SFP combo ports, 4*10GE SFP+ ports, AC power supply) for V2R20C00
                fname8031S5720S-52X-LI-24S-AC1(537455), --S5720S-52X-LI-24S-AC1 (24*FE SFP ports,22*GE SFP ports, 2 of which are 10/100/1000BASE-T + SFP combo ports, 4*10GE SFP+ ports, AC power supply) for V2R20C00
                fname8031S5320-52X-LI-48S-AC1(537456), --S5320-52X-LI-48S-AC1 (46*GE SFP ports, 2 of which are 10/100/1000BASE-T + SFP combo ports, 4*10GE SFP+ ports, AC power supply) for V2R20C00
                fname8031S5320-52X-LI-48S-DC1(537457), --S5320-52X-LI-48S-DC1 (46*GE SFP ports, 2 of which are 10/100/1000BASE-T + SFP combo ports, 4*10GE SFP+ ports, DC power supply) for V2R20C00
                fname8031S5320-52X-LI-24S-AC1(537458), --S5320-52X-LI-24S-AC1 (24*FE SFP ports,22*GE SFP ports, 2 of which are 10/100/1000BASE-T + SFP combo ports, 4*10GE SFP+ ports, AC power supply) for V2R20C00

                fname8031S5735-L8T4X-A1(537460), --S5735-L8T4X-A1 (8*10/100/1000BASE-T ports, 4*10GE SFP+ ports, AC power) for V2R20C10
                fname8031S5335-L8T4X-A1(537461), --S5335-L8T4X-A1 (8*10/100/1000BASE-T ports, 4*10GE SFP+ ports, AC power) for V2R20C10
                fname8031S5735-L8T4S-A1(537462), --S5735-L8T4S-A1 (8*10/100/1000BASE-T ports, 4*GE SFP ports, AC power) for V2R20C10
                fname8031S5735S-L8T4S-A1(537463), --S5735S-L8T4S-A1 (8*10/100/1000BASE-T ports, 4*GE SFP ports, AC power) for V2R20C10
                fname8031S1730S-S8T4S-A1(537464), --S1730S-S8T4S-A1 (8*10/100/1000BASE-T ports, 4*GE SFP ports, AC power) for V2R20C10
                fname8031S2730S-S8FT4S-A(537465), --S2730S-S8FT4S-A (4*10/100BASE-TX ports, 4*10/100/1000BASE-T ports, 4*GE SFP ports, AC power) for V2R20C10
                fname8031S500-8T4S(537466), --S500-8T4S (8*10/100/1000BASE-T ports, 4*GE SFP ports, AC power) for V2R20C10
                fname8031S300-8T4S(537467), --S300-8T4S (8*10/100/1000BASE-T ports, 4*GE SFP ports, AC power) for V2R20C10
                fname8031S200-8T4S(537468), --S200-8T4S (8*10/100/1000BASE-T ports, 4*GE SFP ports, AC power) for V2R20C10
                fname8031S5735-L8P4X-A1(537469), --S5735-L8P4X-A1 (8*10/100/1000BASE-T ports, 4*10GE SFP+ ports, PoE+, AC power) for V2R20C10
                fname8031S5735-L8T4X-D1(537470), --S5735-L8T4X-D1 (8*10/100/1000BASE-T ports, 4*10GE SFP+ ports, DC power) for V2R20C10
                fname8031S5335-L8P4X-A1(537471), --S5335-L8P4X-A1 (8*10/100/1000BASE-T ports, 4*10GE SFP+ ports, PoE+, AC power) for V2R20C10
                fname8031S5335-L8T4X-D1(537472), --S5335-L8T4X-D1 (8*10/100/1000BASE-T ports, 4*10GE SFP+ ports, DC power) for V2R20C10
                fname8031S5735-L8P4S-A1(537473), --S5735-L8P4S-A1 (8*10/100/1000BASE-T ports, 4*GE SFP ports, PoE+, AC power) for V2R20C10
                fname8031S5735S-L8P4S-A1(537474), --S5735S-L8P4S-A1 (8*10/100/1000BASE-T ports, 4*GE SFP ports, PoE+, AC power) for V2R20C10
                fname8031S1730S-S8P4S-A1(537475), --S1730S-S8P4S-A1 (8*10/100/1000BASE-T ports, 4*GE SFP ports, PoE+, AC power) for V2R20C10
                fname8031S2730S-S8FP4S-A(537476), --S2730S-S8FP4S-A (4*10/100BASE-TX ports, 4*10/100/1000BASE-T ports, 4*GE SFP ports, PoE+, AC power) for V2R20C10
                fname8031S500-8P4S(537477), --S500-8P4S (8*10/100/1000BASE-T ports, 4*GE SFP ports, PoE+, AC power) for V2R20C10
                fname8031S300-8P4S(537478), --S300-8P4S (8*10/100/1000BASE-T ports, 4*GE SFP ports, PoE+, AC power) for V2R20C10
                fname8031S200-8P4S(537479), --S200-8P4S (8*10/100/1000BASE-T ports, 4*GE SFP ports, PoE+, AC power) for V2R20C10
                fname8031S5735-L24T4X-A1(537480), --S5735-L24T4X-A1 (24*10/100/1000BASE-T ports, 4*10GE SFP+ ports, AC power) for V2R20C10
                fname8031S5335-L24T4X-A1(537481), --S5335-L24T4X-A1 (24*10/100/1000BASE-T ports, 4*10GE SFP+ ports, AC power, front access) for V2R20C10
                fname8031S5735-L24T4X-D1(537482), --S5735-L24T4X-D1 (24*10/100/1000BASE-T ports, 4*10GE SFP+ ports, DC power) for V2R20C10
                fname8031S5335-L24T4X-D1(537483), --S5335-L24T4X-D1 (24*10/100/1000BASE-T ports, 4*10GE SFP+ ports, DC power, front access) for V2R20C10
                fname8031S5735-L24T4S-A1(537484), --S5735-L24T4S-A1 (24*10/100/1000BASE-T ports, 4*GE SFP ports, AC power) for V2R20C10
                fname8031S5735S-L24T4S-A1(537485), --S5735S-L24T4S-A1 (24*10/100/1000BASE-T ports, 4*GE SFP ports, AC power) for V2R20C10
                fname8031S1730S-S24T4S-A1(537486), --S1730S-S24T4S-A1 (24*10/100/1000BASE-T ports, 4*GE SFP ports, AC power) for V2R20C10
                fname8031S2730S-S24FT4S-A(537487), --S2730S-S24FT4S-A (12*10/100BASE-TX ports, 12*10/100/1000BASE-T ports, 4*GE SFP ports, AC power) for V2R20C10
                fname8031S5735S-L24T4X-A1(537488), --S5735S-L24T4X-A1 (24*10/100/1000BASE-T ports, 4*XGE SFP+ ports, AC power) for V2R20C10
                fname8031S1730S-S24T4X-A1(537489), --S1730S-S24T4X-A1 (24*10/100/1000BASE-T ports, 4*XGE SFP+ ports, AC power) for V2R20C10
                fname8031S500-24T4S(537490), --S500-24T4S (24*10/100/1000BASE-T ports, 4*GE SFP ports, AC power) for V2R20C10
                fname8031S300-24T4S(537491), --S300-24T4S (24*10/100/1000BASE-T ports, 4*GE SFP ports, AC power) for V2R20C10
                fname8031S200-24T4S(537492), --S200-24T4S (24*10/100/1000BASE-T ports, 4*GE SFP ports, AC power) for V2R20C10
                fname8031S2730S-S16FT4S-A(537493), --S2730S-S16FT4S-A (8*10/100BASE-TX ports, 8*10/100/1000BASE-T ports, 4*GE SFP ports, AC power) for V2R20C10
                fname8031S500-16T4S(537494), --S500-16T4S (16*10/100/1000BASE-T ports, 4*GE SFP ports, AC power) for V2R20C10
                fname8031S300-16T4S(537495), --S300-16T4S (16*10/100/1000BASE-T ports, 4*GE SFP ports, AC power) for V2R20C10
                fname8031S5735-L24P4X-A1(537496), --S5735-L24P4X-A1 (24*10/100/1000BASE-T ports, 4*10GE SFP+ ports, PoE+, AC power) for V2R20C10
                fname8031S5335-L24P4X-A1(537497), --S5335-L24P4X-A1 (24*10/100/1000BASE-T ports, 4*10GE SFP+ ports, PoE+, AC power) for V2R20C10
                fname8031S5735-L24P4S-A1(537498), --S5735-L24P4S-A1 (24*10/100/1000BASE-T ports, 4*GE SFP ports, PoE+, AC power) for V2R20C10
                fname8031S5735S-L24P4S-A1(537499), --S5735S-L24P4S-A1 (24*10/100/1000BASE-T ports, 4*GE SFP ports, PoE+, AC power) for V2R20C10
                fname8031S1730S-S24P4S-A1(537500), --S1730S-S24P4S-A1 (24*10/100/1000BASE-T ports, 4*GE SFP ports, PoE+, AC power) for V2R20C10
                fname8031S2730S-S24FP4S-A(537501), --S2730S-S24FP4S-A (12*10/100BASE-TX ports, 12*10/100/1000BASE-T ports, 4*GE SFP ports, PoE+, AC power) for V2R20C10
                fname8031S500-24P4S(537502), --S500-24P4S (24*10/100/1000BASE-T ports, 4*GE SFP ports, PoE+, AC power) for V2R20C10
                fname8031S300-24P4S(537503), --S300-24P4S (24*10/100/1000BASE-T ports, 4*GE SFP ports, PoE+, AC power) for V2R20C10
                fname8031S200-24P4S(537504), --S200-24P4S (24*10/100/1000BASE-T ports, 4*GE SFP ports, PoE+, AC power) for V2R20C10
                fname8031S5735S-L24P4X-A1(537505), --S5735S-L24P4X-A1 (24*10/100/1000BASE-T ports, 4*10GE SFP+ ports, PoE+, AC power) for V2R20C10
                fname8031S2730S-S16FP4S-A(537506), --S2730S-S16FP4S-A1 (8*10/100BASE-TX ports, 8*10/100/1000BASE-T ports,, 4*GE SFP ports, PoE+, AC power) for V2R20C10
                fname8031S500-16P4S(537507), --S500-16P4S (16*10/100/1000BASE-T ports, 4*GE SFP ports, PoE+, AC power) for V2R20C10
                fname8031S300-16P4S(537508), --S500-16P4S (16*10/100/1000BASE-T ports, 4*GE SFP ports, PoE+, AC power) for V2R20C10
                fname8031S5735-L48T4X-A1(537509), --S5735-L48T4X-A1 (48*10/100/1000BASE-T ports, 4*10GE SFP+ ports, AC power) for V2R20C10
                fname8031S5335-L48T4X-A1(537510), --S5335-L48T4X-A1 (48*10/100/1000BASE-T ports, 4*10GE SFP+ ports, AC power) for V2R20C10
                fname8031S5735-L48T4S-A1(537511), --S5735-L48T4S-A1 (48*10/100/1000BASE-T ports, 4*GE SFP ports, AC power) for V2R20C10
                fname8031S5735S-L48T4S-A1(537512), --S5735S-L48T4S-A1 (48*10/100/1000BASE-T ports, 4*GE SFP ports, AC power) for V2R20C10
                fname8031S1730S-S48T4S-A1(537513), --S1730S-S48T4S-A1 (48*10/100/1000BASE-T ports, 4*GE SFP ports, AC power) for V2R20C10
                fname8031S2730S-S48FT4S-A(537514), --S2730S-S48FT4S-A (24*10/100BASE-TX ports, 24*10/100/1000BASE-T ports, 4*GE SFP ports, AC power) for V2R20C10
                fname8031S5735S-L48T4X-A1(537515), --S5735S-L48T4X-A1 (48*10/100/1000BASE-T ports, 4*10GE SFP+ ports, AC power) for V2R20C10
                fname8031S1730S-S48T4X-A1(537516), --S1730S-S48T4X-A1 (48*10/100/1000BASE-T ports, 4*10GE SFP+ ports, AC power) for V2R20C10
                fname8031S500-48T4S(537517), --S500-48T4S (48*10/100/1000BASE-T ports, 4*GE SFP ports, AC power) for V2R20C10
                fname8031S300-48T4S(537518), --S300-48T4S (48*10/100/1000BASE-T ports, 4*GE SFP ports, AC power) for V2R20C10
                fname8031S200-48T4S(537519), --S200-48T4S (48*10/100/1000BASE-T ports, 4*GE SFP ports, AC power) for V2R20C10
                fname8031S5735-L48P4X-A1(537520), --S5735-L48P4X-A1 (48*10/100/1000BASE-T ports, 4*10GE SFP+ ports, PoE+, AC power) for V2R20C10
                fname8031S5335-L48P4X-A1(537521), --S5335-L48P4X-A1 (48*10/100/1000BASE-T ports, 4*10GE SFP+ ports, PoE+, AC power) for V2R20C10
                fname8031S5735-L48P4S-A1(537522), --S5735-L48P4S-A1 (48*10/100/1000BASE-T ports, 4*GE SFP ports, PoE+, AC power) for V2R20C10
                fname8031S5735S-L48P4S-A1(537523), --S5735S-L48P4S-A1 (48*10/100/1000BASE-T ports, 4*GE SFP ports, PoE+, AC power) for V2R20C10
                fname8031S5735S-L48P4X-A1(537524), --S5735S-L48P4X-A1 (48*10/100/1000BASE-T ports, 4*10GE SFP+ ports, PoE+, AC power) for V2R20C10
                fname8031S1730S-S48P4S-A1(537525), --S1730S-S48P4S-A1 (48*10/100/1000BASE-T ports, 4*GE SFP ports, PoE+, AC power) for V2R20C10
                fname8031S2730S-S48FP4S-A(537526), --S2730S-S48FP4S-A (24*10/100BASE-TX ports, 24*10/100/1000BASE-T ports, 4*GE SFP ports, PoE+, AC power) for V2R20C10	
                fname8031S5336-S24S4X-A(537527), --S5336-S24S4X-A base (24*GE SFP ports, optional RTU upgrade to 10G, 4*10GE SFP+ ports, AC power supply, front access) for V2R20C10
                fname8031S5336-S24S4X-D(537528), --S5336-S24S4X-D base (24*GE SFP ports, optional RTU upgrade to 10G, 4*10GE SFP+ ports, AC power supply, front access) for V2R20C10
                fname8031S5735-L32ST4X-A1(537531), --S5735-L32ST4X-A1 (24*GE SFP ports, 8*10/100/1000BASE-T ports, 4*10GE SFP+ ports, AC power) for V2R20C10
                fname8031S5335-L32ST4X-A1(537532), --S5335-L32ST4X-A1 (24*GE SFP ports, 8*10/100/1000BASE-T ports, 4*10GE SFP+ ports, AC power, front access) for V2R20C10
                fname8031S5735S-L32ST4X-A1(537533), --S5735S-L32ST4X-A1 (24*GE SFP ports, 8*10/100/1000BASE-T ports, 4*10GE SFP+ ports, AC power) for V2R20C10
                fname8031S500-32ST4X(537534), --S500-32ST4X (24*GE SFP ports, 8*10/100/1000BASE-T ports, 4*10GE SFP+ ports, AC power) for V2R20C10
                fname8031S5735-L32ST4X-D1(537535), --S5735-L32ST4X-V2 (24*GE SFP ports, 8*10/100/1000BASE-T ports, 4*10GE SFP+ ports, DC power) for V2R20C10
                fname8031S5335-L32ST4X-D1(537536), --S5335-L32ST4X-V2 (24*GE SFP ports, 8*10/100/1000BASE-T ports, 4*10GE SFP+ ports, DC power, front access) for V2R20C10
                fname8031S5700W-H24T4XC1(537529), --S5700W-H24T4XC1 (24*10/100/1000BASE-T ports, 4*10GE SFP+ ports, 1*expansion slot, without power module) for V2R20C10
                fname8031S5700W-H48T4XC1(537530), --S5700W-H48T4XC1 (48*10/100/1000BASE-T ports, 4*10GE SFP+ ports, 1*expansion slot, without power module) for V2R20C10
                fname8031S5735S-H24T4X-A(537542), --S5735S-H24T4X bundle(24*10/100/1000BASE-T ports, 4*10GE SFP+ ports, 1*AC power module) for V2R20C30
                fname8031S5735S-H48T4X-A(537543), --S5735S-H48T4X bundle (48*10/100/1000BASE-T ports, 4*10GE SFP+ ports, 1*AC power module) for V2R20C30
                fname8031S5735S-H24U4X-A(537544), --S5735S-H24U4X bundle (24*10/100/1000BASE-T ports, 4*10GE SFP+ ports, PoE++, 1*AC power module) for V2R20C30
                fname8031S5735S-H48U4X-A(537545), --S5735S-H48U4X bundle (48*10/100/1000BASE-T ports, 4*10GE SFP+ ports, PoE++, 1*AC power module) for V2R20C30
                fname8031S5735S-H24S4X-A(537546), --S5735S-H24S4X bundle (24*GE SFP ports, 4*10GE SFP+ ports, 1*AC power module) for V2R20C30
                fname8031S5735S-H48S4X-A(537547), --S5735S-H48S4X bundle (48*GE SFP ports, 4*10GE SFP+ ports, 1*AC power module) for V2R20C30
                fname8031S5735S-H48S4XC-A(537548), --S5735S-H48S4XC bundle (48*GE SFP ports, 4*10GE SFP+ ports, 1*expansion slot, 1*AC power module) for V2R20C30
                fname8031S5735R-8P4S(537549), --S5735R-8P4S (8*10/100/1000BASE-T ports, 4*GE SFP ports, PoE+, AC power) for V2R20C30
                fname8031S5735R-24T4X(537550), --S5735R-24T4X (24*10/100/1000BASE-T ports, 4*10GE SFP+ ports, AC power) for V2R20C30
                fname8031S5735R-24T4S(537551), --S5735R-24T4S (24*10/100/1000BASE-T ports, 4*GE SFP ports, AC power) for V2R20C30
                fname8031S5735R-24P4X(537552), --S5735R-24P4X (24*10/100/1000BASE-T ports, 4*10GE SFP+ ports, PoE+, AC power) for V2R20C30
                fname8031S5735R-24P4S(537553), --S5735R-24P4S (24*10/100/1000BASE-T ports, 4*GE SFP ports, PoE+, AC power) for V2R20C30
                fname8031S5735R-48T4S(537554), --S5735R-48T4S (48*10/100/1000BASE-T ports, 4*GE SFP ports, AC power) for V2R20C30
                fname8031S5736-S48S4X-A(537555), --S5736-S48S4X-A base (48*GE SFP ports, optional RTU upgrade to 10G, 4*10GE SFP+ ports, AC power supply, front access) for V2R20C30
                fname8031S5736-S48S4X-D(537556), --S5736-S48S4X-D base (48*GE SFP ports, optional RTU upgrade to 10G, 4*10GE SFP+ ports, DC power supply, front access) for V2R20C30
                fname8031S6730-H48X6C-V2(537540), --S6730-H48X6C-V2(48*10GE SFP+ ports, 6*40GE QSFP28 ports, optional license for upgrade to 6*100GE QSFP28, without power module) for V6R21C00
                fname8031S6730-H24X6C-V2(537541), --S6730-H24X6C-V2(24*10GE SFP+ ports, 6*40GE QSFP28 ports, optional license for upgrade to 6*100GE QSFP28, without power module) for V6R21C00
                fname8031S5735-L8T4X-IA1(537557), --S5735-L8T4X-IA1 (8*10/100/1000BASE-T ports, 4*10GE SFP+ ports, AC power) for V2R21C00				
                fname8031S5735-L8P4X-IA1(537558), --S5735-L8P4X-IA1 (8*10/100/1000BASE-T ports, 4*10GE SFP+ ports, PoE+, AC power) for V2R21C00
                fname8031S5735-L24T4X-IA1(537559), --S5735-L24T4X-IA1 (24*10/100/1000BASE-T ports, 4*10GE SFP+ ports, AC power) for V2R21C00
                fname8031S5735-L8T4S-QA1(537560), --S5735-L8T4S-QA1 (8*10/100/1000BASE-T ports, 4*GE SFP ports, AC power, Fanless) for V2R21C00
                fname8031S5735-L24T4X-QA1(537561), --S5735-L24T4X-QA1 (24*10/100/1000BASE-T ports, 4*10GE SFP+ ports, AC power, Fanless) for V2R21C00
                fname8031S5735-L24T4S-QA1(537562), --S5735-L24T4S-QA1 (24*10/100/1000BASE-T ports, 4*GE SFP ports, AC power, Fanless) for V2R21C00
                fname8031S6730-H48X6C-TV2(537563), --S6730-H48X6C-TV2(48*10GE SFP+ ports, 6*40GE QSFP28 ports, optional license for upgrade to 6*100GE QSFP28, without power module) for V6R21C10(TPM)
                fname8031S6730-H24X6C-TV2(537564), --S6730-H24X6C-TV2(24*10GE SFP+ ports, 6*40GE QSFP28 ports, optional license for upgrade to 6*100GE QSFP28, without power module) for V6R21C10(TPM)
                fname8031S6730-H48Y6C-V2(537565),  --S6730-H48Y6C-V2(48*25GE SFP28 ports, 6*100GE QSFP28 ports, without power module) for V6R21C10
                fname8031S6730-H48Y6C-TV2(537566), --S6730-H48Y6C-TV2(48*25GE SFP28 ports, 6*100GE QSFP28 ports, without power module) for V6R21C10(TPM)
                fname8031S5735-L8P4S-QA1(537567), --S5735-L8P4S-QA1 (8*10/100/1000BASE-T ports, 4*GE SFP ports, PoE+, AC power, Fanless) for V2R21C00
				
				fname8031S5735-S24U4X(537780),  --  S5735-S24U4X (24*10/100/1000BASE-T ports, 4*10GE SFP+ ports, PoE++, without power module)
				fname8031S5735-S48U4X(537781),  --  S5735-S48U4X (48*10/100/1000BASE-T ports, 4*10GE SFP+ ports, PoE++, without power module) 
				fname8031S5735S-S24S4X-A(537782),  --  S5735S-S24S4X bundle (24*GE SFP ports, 4*10GE SFP+ ports, 1*AC power module) 
				fname8031S5735S-S48S4X-A(537783),  --  S5735S-S48S4X bundle (48*GE SFP ports, 4*10GE SFP+ ports, 1*AC power module) 
				fname8031S6720S-S36S16X-A(537784),  --  S6720S-S36S16X-A (36*GE SFP ports, 16*10GE SFP+ ports, AC power supply, front access) 
				fname8031S5735S-S24T4S-XA(537785),  --  S5735S-S24T4S-X Bundle (24*10/100/1000BASE-T ports, 4*GE SFP ports, 1*AC power)

                fname8031S5735-L8T4S-QA2(537587),   --S5735-L8T4S-QA2 (8*10/100/1000BASE-T ports, 4*GE SFP ports, AC power) for V2R21C01
                fname8031S5735S-L8T4S-QA2(537588),  --S5735S-L8T4S-QA2 (8*10/100/1000BASE-T ports, 4*GE SFP ports, AC power) for V2R21C01
                fname8031S300-8T4S-QA2(537589),     --S300-8T4S-QA2 (8*10/100/1000BASE-T ports, 4*GE SFP ports, AC power) for V2R21C01
                fname8031S5735S-L8T4S-MA2(537590),  --S5735S-L8T4S-MA2 (8*10/100/1000BASE-T ports, 4*GE SFP ports, AC power) for V2R21C01
                fname8031S1730S-S8T4S-QA2(537591),  --S1730S-S8T4S-QA2 (8*10/100/1000BASE-T ports, 4*GE SFP ports, AC power) for V2R21C01
                fname8031S200-8T4S-QA2(537592),     --S200-8T4S-QA2 (8*10/100/1000BASE-T ports, 4*GE SFP ports, AC power) for V2R21C01
                fname8031S5735-L8P4S-QA2(537593),   --S5735-L8P4S-QA2 (8*10/100/1000BASE-T ports, 4*GE SFP ports, PoE+, AC power) for V2R21C01
                fname8031S5735S-L8P4S-QA2(537594),  --S5735S-L8P4S-QA2 (8*10/100/1000BASE-T ports, 4*GE SFP ports, PoE+, AC power) for V2R21C01
                fname8031S300-8P4S-QA2(537595),     --S300-8P4S-QA2 (8*10/100/1000BASE-T ports, 4*GE SFP ports, PoE+, AC power) for V2R21C01
                fname8031S5735S-L8P4S-MA2(537596),  --S5735S-L8P4S-MA2 (8*10/100/1000BASE-T ports, 4*GE SFP ports, PoE+, AC power) for V2R21C01
                fname8031S1730S-S8P4S-QA2(537597),  --S1730S-S8P4S-QA2 (8*10/100/1000BASE-T ports, 4*GE SFP ports, PoE+, AC power) for V2R21C01
                fname8031S200-8P4S-QA2(537598),     --S200-8P4S-QA2 (8*10/100/1000BASE-T ports, 4*GE SFP ports, PoE+, AC power) for V2R21C01
                fname8031S5735-L24T4X-QA2(537599),  --S5735-L24T4X-QA2 (24*10/100/1000BASE-T ports, 4*10GE SFP+ ports, AC power) for V2R21C01
                fname8031S5735S-L24T4X-QA2(537600), --S5735S-L24T4X-QA2 (24*10/100/1000BASE-T ports, 4*10GE SFP+ ports, AC power) for V2R21C01
                fname8031S1730S-S24T4X-QA2(537601), --S1730S-S24T4X-QA2 (24*10/100/1000BASE-T ports, 4*10GE SFP+ ports, AC power) for V2R21C01
                fname8031S5735-L24T4S-QA2(537602),  --S5735-L24T4S-QA2 (24*10/100/1000BASE-T ports, 4*GE SFP ports, AC power) for V2R21C01
                fname8031S5735S-L24T4S-QA2(537603), --S5735S-L24T4S-QA2 (24*10/100/1000BASE-T ports, 4*GE SFP ports, AC power) for V2R21C01
                fname8031S5735S-L24T4S-MA2(537604), --S5735S-L24T4S-MA2 (24*10/100/1000BASE-T ports, 4*GE SFP ports, AC power) for V2R21C01
                fname8031S1730S-S24T4S-QA2(537605), --S1730S-S24T4S-QA2 (24*10/100/1000BASE-T ports, 4*GE SFP ports, AC power) for V2R21C01
                fname8031S300-24T4S-QA2(537606),    --S300-24T4S-QA2 (24*10/100/1000BASE-T ports, 4*GE SFP ports, AC power) for V2R21C01
                fname8031S200-24T4S-QA2(537607),    --S200-24T4S-QA2 (24*10/100/1000BASE-T ports, 4*GE SFP ports, AC power) for V2R21C01
                fname8031S5735-L24P4X-A2(537610),   --S5735-L24P4X-A2 (24*10/100/1000BASE-T ports, 4*10GE SFP+ ports, PoE+, AC power) for V2R21C01
                fname8031S5735S-L24P4X-A2(537611),  --S5735S-L24P4X-A2 (24*10/100/1000BASE-T ports, 4*10GE SFP+ ports, PoE+, AC power) for V2R21C01
                fname8031S1730S-S24P4X-A2(537612),  --S1730S-S24P4X-A2 (24*10/100/1000BASE-T ports, 4*10GE SFP+ ports, PoE+, AC power) for V2R21C01
                fname8031S5735-L24P4S-A2(537613),   --S5735-L24P4S-A2 (24*10/100/1000BASE-T ports, 4*GE SFP ports, PoE+, AC power) for V2R21C01
                fname8031S5735S-L24P4S-A2(537614),  --S5735S-L24P4S-A2 (24*10/100/1000BASE-T ports, 4*GE SFP ports, PoE+, AC power) for V2R21C01
                fname8031S5735S-L24P4S-MA2(537615), --S5735S-L24P4S-MA2 (24*10/100/1000BASE-T ports, 4*GE SFP ports, PoE+, AC power) for V2R21C01
                fname8031S1730S-S24P4S-A2(537616),  --S1730S-S24P4S-A2 (24*10/100/1000BASE-T ports, 4*GE SFP ports, PoE+, AC power) for V2R21C01
                fname8031S300-24P4S-A2(537617),     --S300-24P4S-A2 (24*10/100/1000BASE-T ports, 4*GE SFP ports, PoE+, AC power) for V2R21C01
                fname8031S200-24P4S-A2(537618),     --S200-24P4S-A2 (24*10/100/1000BASE-T ports, 4*GE SFP ports, PoE+, AC power) for V2R21C01
                fname8031S5700W-S24P4X1(537619), --S5700W-S24P4X1 (24*10/100/1000BASE-T ports,4*10GE SFP+ ports,PoE+, without power module) for V2R21C00
                fname8031S5700W-S48P4X1(537620), --S5700W-S48P4X1 (48*10/100/1000BASE-T ports,4*10GE SFP+ ports,PoE+,without power module) for V2R21C00
                fname8031S6700W-S24X6Q1(537621), --S6700W-S24X6Q1 (24*10GE SFP+ ports, 6*40GE QSFP ports, without power module) for V2R21C00
                fname8031S5700W-L24T4X-A1(537622), --S5700W-L24T4X-A1 (24*10/100/1000BASE-T ports, 4*10GE SFP+ ports, AC power) for V2R21C00
                fname8031S5700W-L48T4X-A1(537623), --S5700W-L48T4X-A1 (48*10/100/1000BASE-T ports, 4*10GE SFP+ ports, AC power) for V2R21C00
                fname8031S5735-S24T4X-X(537625),    --S5735-S24T4X-X (24*10/100/1000BASE-T ports, 4*10GE SFP+ ports, without power module) for V2R21C01
                fname8031S5735S-S24T4X-XA(537626),  --S5735S-S24T4X-XA (24*10/100/1000BASE-T ports, 4*10GE SFP+ ports, 1*60W AC power module) for V2R21C01
                fname8031S6735-S48X6C(537583), --S6735-S48X6C(48 10 Gig SFP+,6 100 Gig QSFP28 interface,with 1 interface slot,without power module) for V2R21C01
                fname8031S6735S-S48X6C-A(537584),  --S6735S-S48X6C Bundle(48 10 Gig SFP+,6 100 Gig QSFP28 interface,with 1 interface slot,with 600W AC power supply) for V2R21C01
                fname8031S6735-S24X6C(537585),  --S6735-S24X6C Bundle(48 10 Gig SFP+,2 100 Gig QSFP28 interface,with 1 interface slot,without power module) for V2R21C01
                fname8031S6735S-S24X6C-A(537586),  --S6735S-S24X6C Bundle(24 10 Gig SFP+,6 100 Gig QSFP28 interface,with 1 interface slot,with 600W AC power supply) for V2R21C01
                fname8031S5735S-H24S4X-MA(537627),  --S5735S-H24S4X-M bundle (24*GE SFP ports, 4*10GE SFP+ ports, 1*AC power module) for V2R21C01
                fname8031S5731-S48S4X-A(537568),  --S5731-S48S4X-A(48*GE SFP ports, 4*10GE SFP+ ports, AC power, front access) for V2R21C01
                fname8031S5731S-S48S4X-A1(537569),  --S5731S-S48S4X-A1(48*GE SFP ports, 12*10GE SFP+ ports, AC power, front access) for V2R21C01
                fname8031S5331-S48S4X-A(537570),  --S5331-S48S4X-A(48*GE SFP ports, 4*10GE SFP+ ports, AC power, front access) for V2R21C01
                fname8031S5331-S48S4X-D(537571),  --S5331-S48S4X-D(48*GE SFP ports, 4*10GE SFP+ ports, DC power, front access) for V2R21C01
                fname8031S5731-S48S4X(537572),  --S5731-S48S4X(48*GE SFP ports,  4*10GE SFP+ ports, without power module) for V2R21C01
                fname8031S5731S-S48S4X-A(537573),  --S5731S-S48S4X-A(48*GE SFP ports,  4*10GE SFP+ ports, with AC power supply) for V2R21C01
                fname8031S5331-S48S4X(537574),  --S5331-S48S4X(48*GE SFP ports,  4*10GE SFP+ ports, without power module) for V2R21C01
                fname8031S5731-S32ST4X-A(537575),  --S5731-S32ST4X-A(8*10/100/1000BASE-T ports, 24*GE SFP ports, 4*10GE SFP+ ports, AC power, front access) for V2R21C01
                fname8031S5731S-S32ST4X-A1(537576),  --S5731S-S32ST4X-A1(8*10/100/1000BASE-T ports, 24*GE SFP ports, 4*10GE SFP+ ports, AC power, front access) for V2R21C01
                fname8031S5731-S32ST4X-D(537577),  --S5731-S32ST4X-D(8*10/100/1000BASE-T ports, 24*GE SFP ports, 4*10GE SFP+ ports, DC power, front access) for V2R21C01
                fname8031S5331-S32ST4X-A(537578),  --S5331-S32ST4X-A(8*10/100/1000BASE-T ports, 24*GE SFP ports, 4*10GE SFP+ ports, AC power, front access) for V2R21C01
                fname8031S5331-S32ST4X-D(537579),  --S5331-S32ST4X-D(8*10/100/1000BASE-T ports, 24*GE SFP ports, 4*10GE SFP+ ports, DC power, front access) for V2R21C01
                fname8031S5731-S32ST4X(537580),  --S5731-S32ST4X(8*10/100/1000BASE-T ports, 24*GE SFP ports, 4*10GE SFP+ ports, without power module) for V2R21C01
                fname8031S5731S-S32ST4X-A(537581),  --S5731S-S32ST4X-A(8*10/100/1000BASE-T ports, 24*GE SFP ports, 4*10GE SFP+ ports, with AC power supply) for V2R21C01
                fname8031S5331-S32ST4X(537582),  --S5331-S32ST4X(8*10/100/1000BASE-T ports, 24*GE SFP ports, 4*10GE SFP+ ports, without power module) for V2R21C01
                fname8031S5700W-S32ST4X1(537624),  --S5700W-S32ST4X1 (24*GE SFP ports, 8*10/100/1000BASE-T ports, 4*10GE SFP+ ports, without power module) for V2R21C01
                fname8031S5731-H48HB4XZ(537628), --S5731-H48HB4XZ(44*Hybrid GE SFP ports, 4*Hybrid 10GE SFP+ ports, 4*10GE SFP+ ports, 1*expansion slot, PoE++, without power module) for V2R21C10
                fname8031S5731S-H48HB4XZ-A(537629), --S5731S-H48HB4XZ Bundle(44*Hybrid GE SFP ports, 4*Hybrid 10GE SFP+ ports, 4*10GE SFP+ ports, 1*expansion slot, PoE++, 1*AC power) for V2R21C10
                fname8031S5731-H24HB4XZ(537630), --S5731-H24HB4XZ(20*Hybrid GE SFP ports, 4*Hybrid 10GE SFP+ ports, 4*10GE SFP+ ports, 1*expansion slot, PoE++, without power module) for V2R21C10
                fname8031S5731S-H24HB4XZ-A(537631), --S5731S-H24HB4XZ Bundle(20*Hybrid GE SFP ports, 4*Hybrid 10GE SFP+ ports, 4*10GE SFP+ ports, 1*expansion slot, PoE++, 1*AC power) for V2R21C10 
                fname8031S5731S-S48P4X-A1(537632), --S5731S-S48T4X Bundle(48*10/100/1000BASE-T ports, 4*10GE SFP+ ports, PoE+,single power, 1*AC power)for v2r21c10
                fname8031S5331-S48T4X(537634), --S5331-S48T4X (48*10/100/1000BASE-T ports, 4*10GE SFP+ ports, without power module)for v2r21c10
                fname8031S5331-S24T4X(537637), --S5331-S24T4X (24*10/100/1000BASE-T ports, 4*10GE SFP+ ports, without power module)for v2r21c10
                fname8031S5731-S48T4X-A(537638), --S5731-S48T4X-A (48*10/100/1000BASE-T ports, 4*10GE SFP+ ports, AC power)for v2r21c10
                fname8031S5731S-S48T4X-A1(537639), --S5731S-S48T4X-A1 (48*10/100/1000BASE-T ports, 4*10GE SFP+ ports, AC power)for v2r21c10
                fname8031S5331-S48T4X-A(537640), --S5331-S48T4X-A (48*10/100/1000BASE-T ports, 4*10GE SFP+ ports, AC power)for v2r21c10
                fname8031S5731-S24T4X-A(537641), --S5731-S24T4X-A (24*10/100/1000BASE-T ports, 4*10GE SFP+ ports, AC power)for v2r21c10
                fname8031S5731S-S24T4X-A1(537642), --S5731S-S24T4X-A1 (24*10/100/1000BASE-T ports, 4*10GE SFP+ ports, AC power)for v2r21c10
                fname8031S5731-S24T4X-D(537643), --S5731-S24T4X-D (24*10/100/1000BASE-T ports, 4*10GE SFP+ ports, DC power)for v2r21c10
                fname8031S5331-S24T4X-A(537644), --S5331-S24T4X-A (24*10/100/1000BASE-T ports, 4*10GE SFP+ ports, AC power,front access)for v2r21c10
                fname8031S5331-S24T4X-D(537645), --S5331-S24T4X-D (24*10/100/1000BASE-T ports, 4*10GE SFP+ ports, DC power,front access)for v2r21c10
                fname8031S5731-S48P4X-A(537646), --S5731-S48P4X Bundle(48*10/100/1000BASE-T ports, 4*10GE SFP+ ports, PoE+,single power, 1*AC power)for v2r21c10
                fname8031S5331-S48P4X(537647), --S5331-S48P4X (48*10/100/1000BASE-T ports, 4*10GE SFP+ ports, PoE+, without power module)for v2r21c10
                fname8031S5331-S24P4X(537648), --S5331-S24P4X (24*10/100/1000BASE-T ports, 4*10GE SFP+ ports, PoE+, without power module)for v2r21c10
                fname8031S200-48T4X(537649), --S200-48T4X (48*10/100/1000BASE-T ports, 4*10GE SFP+ ports, AC power) for V2R21C01
                fname8031S200-48P4X(537650), --S200-48P4X (48*10/100/1000BASE-T ports, 4*10GE SFP+ ports, PoE+, AC power) for V2R21C01
                fname8031S200-32ST4X(537651), --S200-32ST4X (24*GE SFP ports, 8*10/100/1000BASE-T ports, 4*10GE SFP+ ports, AC power, front access) for V2R21C01
                fname8031S200-24T4X-QA2(537652), --S200-24T4X-QA2 (24*10/100/1000BASE-T ports, 4*10GE SFP+ ports, AC power) for V2R21C01
                fname8031S200-24P4X-A2(537653), --S200-24P4X-A2 (24*10/100/1000BASE-T ports, 4*10GE SFP+ ports, PoE+, AC power) for V2R21C01
                fname8031S600-S24S28X(537654), --S600-S24S28X (24*GE SFP ports, 28*10GE SFP+ ports, AC power supply, front access) for V2R21C10
                fname8031S6730-H28X6CZ-V2(537667), --S6730-H28X6C-V2 (28*10GE SFP+ ports, 6*100GE QSFP28, 1*expansion slot, without power module) for V6R22C00
                fname8031S6730-H28X6CZ-TV2(537668), --S6730-H28X6C-TV2 (28*10GE SFP+ ports, 6*100GE QSFP28, 1*expansion slot, HTM, without power module) for V6R22C00
                fname8031S5732-H24S4X6QZ-V2(537669), --S5732-H24S4X6QZ-V2 (24*GE SFP ports,4*10GE SFP+ ports,6*40GE QSFP ports, 1*expansion slot, without power module) for V6R22C00
                fname8031S5732-H24S4X6QZ-TV2(537670), --S5732-H24S4X6QZ-TV2 (24*GE SFP ports,4*10GE SFP+ ports,6*40GE QSFP ports, 1*expansion slot, HTM, without power module) for V6R22C00
                fname8031S5732-H48UM4Y2CZ-V2(537671), --S5732-H48UM4Y2CZ-V2 2.5G Bundle(48*100M/1G/2.5G Ethernet ports, Optional RTU upgrade to 5/10G, 4*25GE SFP28, 2*100GE QSFP28 ports, 1*expansion slot, PoE++, with AC power supply) for V6R22C00
                fname8031S5732-H48UM4Y2CZ-TV2(537672), --S5732-H48UM4Y2CZ-TV2 2.5G Bundle(48*100M/1G/2.5G Ethernet ports, Optional RTU upgrade to 5/10G, 4*25GE SFP28, 2*100GE QSFP28 ports, 1*expansion slot, PoE++, HTM, with AC power supply) for V6R22C00
				fname8031S5731-S24N4X2Q-A(537673), --S5731-S24N4X2Q-A(24*100M/1G/2.5G Ethernet ports, 4*10GE SFP+ ports, 2*40GE QSFP ports, AC power, front access)
              	fname8031S5331-S24N4X2Q-A(537674), --S5331-S24N4X2Q-A(24*100M/1G/2.5G Ethernet ports, 4*10GE SFP+ ports, 2*40GE QSFP ports, AC power, front access)
              	fname8031S5731S-S24N4X2Q-A1(537675), --S5731S-S24N4X2Q-A1(24*100M/1G/2.5G Ethernet ports, 4*10GE SFP+ ports, 2*40GE QSFP ports, AC power, front access)
              	fname8031S5731-S24UN4X2Q(537676), --S5731-S24NU4X2Q (24*100M/1G/2.5G Ethernet ports, 4*10GE SFP+ ports, 2*40GE QSFP ports, without power module)
              	fname8031S5731S-S24UN4X2Q(537677), --S5731S-S24NU4X2Q Bundle(24*100M/1G/2.5G/5G Ethernet ports, 4*10GE SFP+ ports or 2*40GE QSFP ports, with AC power supply)
              	fname8031S5731-S24UR2Q(537678), --S5731-S24RU2Q (24*100M/1G/2.5G/5G Ethernet ports, 4*10GE SFP+ ports or 2*40GE QSFP ports, without power module)
              	fname8031S5731S-S24UR2Q(537679), --S5731S-S24NU4X2Q Bundle(24*100M/1G/2.5G Ethernet ports, 4*10GE SFP+ ports, 2*40GE QSFP ports, with AC power supply)
              	fname8031S5731-S8UM16UN2Q(537680), --S5731-S8UM16UN2Q (8*100M/1G/2.5G/5G/10G,16*100M/1G/2.5G Ethernet ports, 2*40GE QSFP ports, switch to 16*100M/1G/2.5G/5G/10G,8*100M/1G Ethernet ports, 4*10GE SFP+ ports, without power module)
              	fname8031S5731S-S8UM16UN2Q(537681), --S5731-S8UM16UN2Q Bundle(8*100M/1G/2.5G/5G/10G,16*100M/1G/2.5G Ethernet ports, 2*40GE QSFP ports, switch to 16*100M/1G/2.5G/5G/10G,8*100M/1G Ethernet ports, 4*10GE SFP+ ports, with AC power supply)

              	fname8031S5732-H48UM4Y2CZ-KV2(537682),  --S5732-H48UM4Y2CZ-KV2  for V6R22C00
                fname8031S5732-H24UM4Y2CZ-V2(537683),   --S5732-H24UM4Y2CZ-V2   for V6R22C00
                fname8031S5732-H24UM4Y2CZ-TV2(537684),  --S5732-H24UM4Y2CZ-TV2  for V6R22C00
                fname8031S5732-H24UM4Y2CZ-KV2(537685),  --S5732-H24UM4Y2CZ-KV2  for V6R22C00
                fname8031S6730-H48X6CZ-V2(537686),      --S6730-H48X6CZ-V2      for V6R22C00
                fname8031S6730-H48X6CZ-TV2(537687),     --S6730-H48X6CZ-TV2     for V6R22C00
                fname8031S5732-H44S4X6QZ-V2(537688),    --S5732-H44S4X6QZ-V2    for V6R22C00
                fname8031S5732-H44S4X6QZ-TV2(537689),   --S5732-H44S4X6QZ-TV2   for V6R22C00
                fname8031S5735-L8T4X-QA-V2(537690),        --S5735-L8T4X-QA-V2    for V6R22C01
                fname8031S5735-L8T4S-A-V2(537691),         --S5735-L8T4S-A-V2     for V6R22C01
                fname8031S5735-L10T4X-A-V2(537692),        --S5735-L10T4X-A-V2    for V6R22C01
                fname8031S5735-L10T4X-TA-V2(537693),       --S5735-L10T4X-TA-V2   for V6R22C01
                fname8031S5335-L10T4X-A-V2(537694),        --S5335-L10T4X-A-V2    for V6R22C01
                fname8031S5735-L8P4X-QA-V2(537696),        --S5735-L8P4X-QA-V2    for V6R22C01
                fname8031S5735-L8P4S-A-V2(537697),         --S5735-L8P4S-A-V2     for V6R22C01
                fname8031S5735-L8P2T4X-A-V2(537698),        --S5735-L8P2T4X-A-V2    for V6R22C01
                fname8031S5735-L8P2T4X-TA-V2(537699),       --S5735-L8P2T4X-TA-V2   for V6R22C01
                fname8031S5335-L8P2T4X-A-V2(537700),        --S5335-L8P2T4X-A-V2    for V6R22C01
                fname8031S5335-L10T4X-D-V2(537701),        --S5335-L10T4X-D-V2    for V6R22C01
                fname8031S5735-L16T4X-QA-V2(537702),       --S5735-L16T4X-QA-V2   for V6R22C01
                fname8031S5735-L16T4S-A-V2(537703),        --S5735-L16T4S-A-V2    for V6R22C01
                fname8031S5335-L16T4X-A-V2(537704),        --S5335-L16T4X-A-V2    for V6R22C01
                fname8031S5735-L24T4X-QA-V2(537705),       --S5735-L24T4X-QA-V2   for V6R22C01
                fname8031S5735-L24T4S-A-V2(537706),        --S5735-L24T4S-A-V2    for V6R22C01
                fname8031S5735-L24T4XE-A-V2(537707),       --S5735-L24T4XE-A-V2   for V6R22C01
                fname8031S5335-L24T4XE-A-V2(537708),       --S5335-L24T4XE-A-V2   for V6R22C01
                fname8031S5735-L24T4XE-D-V2(537709),       --S5735-L24T4XE-D-V2   for V6R22C01
                fname8031S5335-L24T4XE-D-V2(537710),       --S5335-L24T4XE-D-V2   for V6R22C01
                fname8031S5735-L24T4XE-TA-V2(537711),      --S5735-L24T4XE-TA-V2   for V6R22C01
                fname8031S5735-S24T4XE-V2(537712),         --S5735-S24T4XE-V2     for V6R22C01
                fname8031S5335-S24T4XE-V2(537713),         --S5335-S24T4XE-V2     for V6R22C01
                fname8031S5735I-S24T4XE-V2(537714),        --S5735I-S24T4XE-V2    for V6R22C01
                fname8031S5735I-S24T4XE-T-V2(537715),      --S5735I-S24T4XE-T-V2  for V6R22C01
                fname8031S5735-L24P4S-A-V2(537716),        --S5735-L24P4S-A-V2    for V6R22C01
                fname8031S5735-L24P4XE-A-V2(537717),       --S5735-L24P4XE-A-V2   for V6R22C01
                fname8031S5735-L24P4XE-TA-V2(537718),      --S5735-L24P4XE-TA-V2  for V6R22C01
                fname8031S5335-L24P4XE-A-V2(537719),       --S5335-L24P4XE-A-V2   for V6R22C01
                fname8031S5735-S24P4XE-V2(537721),         --S5735-S24P4XE-V2     for V6R22C01
                fname8031S5335-S24P4XE-V2(537722),         --S5335-S24P4XE-V2     for V6R22C01
                fname8031S5735-L48T4S-A-V2(537723),        --S5735-L48T4S-A-V2    for V6R22C01
                fname8031S5735-L48T4XE-A-V2(537724),       --S5735-L48T4XE-A-V2   for V6R22C01
                fname8031S5335-L48T4XE-A-V2(537725),       --S5335-L48T4XE-A-V2   for V6R22C01
                fname8031S5735-L48T4XE-TA-V2(537726),      --S5735-L48T4XE-TA-V2  for V6R22C01
                fname8031S5735-L48T4XE-D-V2(537727),       --S5735-L48T4XE-D-V2   for V6R22C01
                fname8031S5735-S48T4XE-V2(537728),         --S5735-S48T4XE-V2     for V6R22C01
                fname8031S5335-S48T4XE-V2(537729),         --S5335-S48T4XE-V2     for V6R22C01
                fname8031S5735-L48LP4S-A-V2(537730),       --S5735-L48LP4S-A-V2   for V6R22C01
                fname8031S5735-L48LP4XE-A-V2(537731),      --S5735-L48LP4XE-A-V2  for V6R22C01
                fname8031S5735-L48P4XE-A-V2(537732),       --S5735-L48P4XE-A-V2   for V6R22C01
                fname8031S5735-S48P4XE-V2(537733),         --S5735-S48P4XE-V2     for V6R22C01
                fname8031S5335-S48P4XE-V2(537734),         --S5335-S48P4XE-V2     for V6R22C01
                fname8031S5735-S24U4XE-V2(537735),         --S5735-S24U4XE-V2     for V6R22C01
                fname8031S5335-S24U4XE-V2(537736),         --S5335-S24U4XE-V2     for V6R22C01
                fname8031S5735-S48U4XE-V2(537737),         --S5735-S48U4XE-V2     for V6R22C01
                fname8031S5335-S48U4XE-V2(537738),         --S5335-S48U4XE-V2     for V6R22C01
                fname8031S5735I-S24U4XE-V2(537739),        --S5735I-S24U4XE-V2    for V6R22C01
                fname8031S5735I-S24U4XE-T-V2(537740),      --S5735I-S24U4XE-T-V2  for V6R22C01
                fname8031S5735I-S8T4XN-V2(537741),         --S5735I-S8T4XN-V2     for V6R22C01
                fname8031S5735I-S8T4XN-T-V2(537742),       --S5735I-S8T4XN-T-V2   for V6R22C01
                fname8031S5735I-S8T4SN-V2(537743),         --S5735I-S8T4SN-V2     for V6R22C01
                fname8031S5735I-S8U4XN-V2(537744),         --S5735I-S8U4XN-V2     for V6R22C01
                fname8031S5735I-L8P4X-A-V2(537791),        --S5735I-L8P4X-A-V2    for V6R22C10
                fname8031S5735I-L10T4X-A-V2(537792),       --S5735I-L10T4X-A-V2   for V6R22C10
                fname8031S6330-H24X4Y(537793),             --S6330-H24X4Y    for V2R22C10
                fname8031S3710-H24T4S-A(537794),           -- S3710-H24T4S-A     for V6R22C10
                fname8031S3710-H24P4S-A(537795),           -- S3710-H24P4S-A     for V6R22C10
                fname8031S3710-H48T4S-A(537796),           -- S3710-H48T4S-A     for V6R22C10
                fname8031S3710-H48LP4S-A(537797),          -- S3710-H48LP4S-A    for V6R22C10
                fname8031S5331-S24T4X-A-V1(537798),        -- S5331-S24T4X-A-V1  for V6R22C10
                fname8031S5331-H24P4XC-V1(537799),         -- S5331-H24P4XC-V1   for V6R22C10
                fname8031S5331-H48T4XC-V1(537800),         -- S5331-H48T4XC-V1   for V6R22C10
                fname8031S310-24P4S(537801),               -- S310-24P4S         for V6R22C10
                fname8031S310-24T4S(537802),               -- S310-24T4S         for V6R22C10
                fname8031S310-48T4S(537803),               -- S310-48T4S         for V6R22C10
                fname8031S5331-S24S8T4X-A(537804),         --S5331-S24S8T4X-A for V2R22C10
                fname8031S5331-S24S8T4X-D(537805),         --S5331-S24S8T4X-D for V2R22C10
                fname8031S5755-H48T4Y2CZ(537807),          --S5755-H48T4Y2CZ
                fname8031S5755-H48P4Y2CZ(537808),          --S5755-H48P4Y2CZ
                fname8031S5755-H48U4Y2CZ(537809),          --S5755-H48U4Y2CZ
                fname8031S5755-H24T4Y2CZ(537810),          --S5755-H24T4Y2CZ
                fname8031S5755-H24P4Y2CZ(537811),          --S5755-H24P4Y2CZ
                fname8031S5755-H24U4Y2CZ(537812),          --S5755-H24U4Y2CZ
                fname8031S5755-H24UTM4X4Y2C(537813),       --S5755-H24UTM4X4Y2C
                fname8031S5755-H48UTM4X4Y2C(537814),       --S5755-H48UTM4X4Y2C
                fname8031S5755-H24N4Y-A(537815),           --S5755-H24N4Y-A
                fname8031S5355-H24N4Y-A(537816),           --S5355-H24N4Y-A
                fname8031S5755-H48N4Y-A(537817),           --S5755-H48N4Y-A
                fname8031S5355-H48N4Y-A(537818),           --S5355-H48N4Y-A
                fname8031S5755-H24UN4Y2CZ(537819),         --S5755-H24UN4Y2CZ
                fname8031S5755-H48UN4Y2CZ(537820),         --S5755-H48UN4Y2CZ
                fname8031S5735-L24ST4XE-A-V2(537821),      --S5735-L24ST4XE-A-V2
                fname8031S5735-L48S4XE-A-V2(537822),       --S5735-L48S4XE-A-V2
                fname8031S5331-S32ST4X-A-V1(537824),       --S5331-S32ST4X-A-V1
                fname8031S5335-L48S4X-A-V2(537825),        --S5335-L48S4X-A-V2
                fname8031S5735-S48S4XE-V2(537827),         --S5735-S48S4XE-V2
                fname8031S5335-S48S4X-V2(537829),          --S5335-S48S4X-V2
                fname8031S5331-S48S4X-V1(537830),          --S5331-S48S4X-V1
                fname8031S5735-L14P2S-QA-V2(537831),       --S5735-L14P2S-QA-V2
                fname8031S5735-L16LP2X-QA-V2(537832),      --S5735-L16LP2X-QA-V2
                fname8031S5735-L16P2UM2X-QA-V2(537833),    --S5735-L16P2UM2X-QA-V2
                fname8031S5735-L16LP2UM2X-QA-V2(537834),   --S5735-L16LP2UM2X-QA-V2
                fname8031S5335-L16LP2UM2X-QA-V2(537835),   --S5335-L16LP2UM2X-QA-V2
                fname8031S5735-L48P4X-A2(537836),          --S5735-L48P4X-A2 for V2R23C00
                fname8031S5735-L48P4S-A2(537837),          --S5735-L48P4S-A2 for V2R23C00
                fname8031S5735S-L48P4X-A2(537838),         --S5735S-L48P4X-A2 for V2R23C00
                fname8031S5735S-L48P4S-A2(537839),         --S5735S-L48P4S-A2 for V2R23C00
                fname8031S5735-L48T4X-A2(537840),          --S5735-L48T4X-A2 for V2R23C00
                fname8031S5735-L48T4S-A2(537841),          --S5735-L48T4S-A2 for V2R23C00
                fname8031S5735S-L48T4X-A2(537842),         --S5735S-L48T4X-A2 for V2R23C00
                fname8031S5735S-L48T4S-A2(537843),         --S5735S-L48T4S-A2 for V2R23C00
                fname8031S5531-H48HB4XZ(537845),           --S5531-H48HB4XZ for V2R22C10
                fname8031S5531-S32ST4X(537846),            --S5531-S32ST4X  for V2R22C10
                fname8031S5335-L24ST4XE-A-V2(537848),      --S5335-L24ST4XE-A-V2
                fname8031S5735-S24HS4XE-V2(537849),        --S5735-S24HS4XE-V2
                fname8031S5735-S24ST4XE-V2(537850),        --S5735-S24ST4XE-V2
                fname8031S5335-S24ST4XE-V2(537851),        --S5335-S24ST4XE-V2
                fname8031S5735-S48HS4XE-V2(537852),        --S5735-S48HS4XE-V2
                fname8031S5735I-H8T4S2XN-V2(537853),          --S5735I-H8T4S2XN-V2
                fname8031S5755-H24UTM4X4Y2C-T(537854),      --S5755-H24UTM4X4Y2C-T  
                fname8031S5755-H48UTM4X4Y2C-T(537855),      --S5755-H48UTM4X4Y2C-T  
                fname8031S5735-L14P2S-TQA-V2(537856),       --S5735-L14P2S-TQA-V2   
                fname8031S5535-L16LP2UM2X-QA-V2(537857),    --S5535-L16LP2UM2X-QA-V2
                fname8031S5535-L24ST4XE-A-V2(537858),       --S5535-L24ST4XE-A-V2   
                fname8031S5535-S24HS4XE-V2(537859),         --S5535-S24HS4XE-V2     
                fname8031S5335-L8T4X-QA-V2(537860),         --S5335-L8T4X-QA-V2     
                fname8031S5335-L8T4S-A-V2(537861),          --S5335-L8T4S-A-V2      
                fname8031S5335-L8P4X-QA-V2(537862),         --S5335-L8P4X-QA-V2     
                fname8031S5335-L24T4X-QA-V2(537863),        --S5335-L24T4X-QA-V2       
                fname8031S5735-L48S4X-A-V2(537864),         --S5735-L48S4X-A-V2
                fname8031S6730S-S48X6Q-A1(538027),          --S6730S-S48X6Q-A1
                fname8031S6730S-H48X6C-A1(538028),          --S6730S-H48X6C-A1
				
                fname8031eKitEngineS5735S-L48P4X-A1(537873), --S5735S-L48P4X-A1 for V2R23C00
                fname8031eKitEngineS5735S-L48P4S-A1(537874), --S5735S-L48P4S-A1 for V2R23C00
                fname8031eKitEngineS5735S-L48T4X-A1(537875), --S5735S-L48T4X-A1 for V2R23C00
                fname8031eKitEngineS5735S-L48T4S-A1(537876), --S5735S-L48T4S-A1 for V2R23C00
                fname8031S5735R-48T4S-A2(537867),           --S5735R-48T4S-A2 for V2R23C00
                fname8031S5735R-8P4S-QA2(537868),           --S5735R-8P4S-QA2 for V2R23C00
                fname8031S5735R-24T4X-QA2(537869),          --5735R-24T4X-QA2 for V2R23C00
                fname8031S5735R-24T4S-QA2(537870),          --S5735R-24T4S-QA2 for V2R23C00
                fname8031S5735R-24P4X-A2(537871),           --S5735R-24P4X-A2 for V2R23C00
                fname8031S5735R-24P4S-A2(537872),           --S5735R-24P4S-A2 for V2R23C00
                fname8031S220-24T4X(537877),                --S220-24T4X
                fname8031S220-24P4X(537878),                --S220-24P4X
                fname8031S220-48T4X(537879),                --S220-48T4X
                fname8031S220-48P4X(537880),                --S220-48P4X
                fname8031S220-48P4S(537881),                --S220-48P4S
                fname8031S220-48T4S(537882),                --S220-48T4S
                fname8031S310-24T4X(537883),                --S310-24T4X
                fname8031S310-24P4X(537884),                --S310-24P4X
                fname8031S310-48T4X(537885),                --S310-48T4X
                fname8031S310-48P4S(537886),                --S310-48P4S
                fname8031S310-48P4X(537887),                --S310-48P4X 
                fname8031S5735I-H24U8S4XE-QA-V2(537888),    --S5735I-H24U8S4XE-QA-V2
                fname8031S5735I-S24T8S4XE-QA-V2(537889),    --S5735I-S24T8S4XE-QA-V2
                fname8031S5735I-S16T8S4XE-QD-V2(537890),    --S5735I-S16T8S4XE-QD-V2
                fname8031S6730-S48X6Q(537891),              --S6730-S48X6Q for V2R23C10
                fname8031S6330-S48X6Q(537900),              --S6330-S48X6Q for V2R23C10
                fname8031S6750-H48Y8C(537865),              --S6750-H48Y8C          
                fname8031S6750-H36C(537866),                --S6750-H36C            
                fname8031S5735-L48LPN4XE-A-V2(537892),      --S5735-L48LPN4XE-A-V2  
                fname8031S5735-L24PN4XE-A-V2(537893),       --S5735-L24PN4XE-A-V2   
                fname8031S5735-S48PN4XE-V2(537894),         --S5735-S48PN4XE-V2     
                fname8031S5735-S24PN4XE-V2(537895),         --S5735-S24PN4XE-V2     
                fname8031S5735-L24LU8S4XE-QA-V2(537896),    --S5735-L24LU8S4XE-QA-V2
                fname8031S5335-L24ST4XE-D-V2(537897),       --S5335-L24ST4XE-D-V2   
                fname8031S5735-S48T4XE-C-V2(537898),        --S5735-S48T4XE-C-V2    
                fname8031S5735-S24T4XE-C-V2(537899),        --S5735-S24T4XE-C-V2    
                fname8031S6750-S16X8YZ(537901),             --S6750-S16X8YZ
                fname8031S6750-S24T16X8Y2CZ(537902),        --S6750-S24T16X8Y2CZ
                fname8031S6750-S16X10Y2CZ(537903),           --S6750-S16X10Y2CZ
                fname8031S5755-H24HB2Y2CZ(537904),          --S5755-H24HB2Y2CZ
                fname8031S6730-H6FX4Y2CZ-V2(537905),        --S6730-H6FX4Y2CZ-V2
                fname8031S5735-L24T8J4XE-A-V2(537906),      --S5735-L24T8J4XE-A-V2
                fname8031S5735-S24T8J4XE-XA-V2(537907),     --S5735-S24T8J4XE-XA-V2
                fname8031S5735-S24T4XEZ-V2(537908),         --S5735-S24T4XEZ-V2
                fname8031S5735-S24T8J4XEZ-V2(537909),       --S5735-S24T8J4XEZ-V2
                fname8031S5735-S24P4XEZ-V2(537910),         --S5735-S24P4XEZ-V2
                fname8031S5735-S24P8J4XEZ-V2(537911),       --S5735-S24P8J4XEZ-V2
                fname8031S5735-S48T4XE-XA-V2(537912),       --S5735-S48T4XE-XA-V2
                fname8031S5735-S48T4XEZ-V2(537913),         --S5735-S48T4XEZ-V2
                fname8031S5735-S48P4XEZ-V2(537914),         --S5735-S48P4XEZ-V2
                fname8031S5535-S48HS4XE-V2(537915),         --S5535-S48HS4XE-V2
                fname8031S5335-L24T4S-A-V2(537916),         --S5335-L24T4S-A-V2
                fname8031S5335-L24P4S-A-V2(537917),         --S5335-L24P4S-A-V2
                fname8031S5755-H48T4Y2CZ-B(537918),         --S5755-H48T4Y2CZ-B
                fname8031S5535-S48PN4XE-V2(537919),         --S5535-S48PN4XE-V2
                fname8031S5535-S24PN4XE-V2(537920),         --S5535-S24PN4XE-V2
                fname8031S6780-H4Z(537921),                 --S6780-H4Z
                fname8031S5735I-S8T8P2S4XN-V2(537950),      --S5735I-S8T8P2S4XN-V2
                fname8031S5735I-S16T2S4XN-V2(537951),       --S5735I-S16T2S4XN-V2     
                fname8031S310-24ST4X(537941),               --S310-24ST4X
                fname8031S310-24PN4X(537942),               --S310-24PN4X
                fname8031S5735S-L24ST4X-A3(537944),         --S5735S-L24ST4X-A3
                fname8031S5735S-L48S4X-A3(537945),          --S5735S-L48S4X-A3
                fname8031S1730S-S48T4S-A3(537948),          --S1730S-S48T4S-A3
                fname8031S1730S-S48P4S-A3(537949),          --S1730S-S48P4S-A3
                fname8031S220-8T4S(537952),                 --S220-8T4S
                fname8031S220-8P4S(537953),                 --S220-8P4S
                fname8031S530-24T4XE(537954),               --S530-24T4XE
                fname8031S530-24ST4XE(537955),              --S530-24ST4XE
                fname8031S530-48S4XE(537956),               --S530-48S4XE
                fname8031S220S-8T2J(537922),                --S220S-8T2J
                fname8031S220S-8T2X(537923),                --S220S-8T2X
                fname8031S310S-8T2X(537924),                --S310S-8T2X
                fname8031S220S-8P4J(537925),                --S220S-8P4J
                fname8031S220S-8P4JX(537926),               --S220S-8P4JX
                fname8031S220S-10PN4JX(537927),             --S220S-10PN4JX
                fname8031S310S-8P4JX(537928),               --S310S-8P4JX
                fname8031S310S-10PN4JX(537929),             --S310S-10PN4JX
                fname8031S220S-24T4J(537930),               --S220S-24T4J
                fname8031S220S-24T4JX(537931),              --S220S-24T4JX
                fname8031S310S-24T4J(537932),               --S310S-24T4J
                fname8031S310S-24T4JX(537933),              --S310S-24T4JX
                fname8031S220S-24P4J(537934),               --S220S-24P4J
                fname8031S220S-24P4JX(537935),              --S220S-24P4JX
                fname8031S220S-24LP4JX(537936),             --S220S-24LP4JX
                fname8031S220S-26PN4JX(537937),             --S220S-26PN4JX
                fname8031S310S-24P4J(537938),               --S310S-24P4J
                fname8031S310S-24P4JX(537939),              --S310S-24P4JX
                fname8031S310S-26PN4JX(537940),             --S310S-26PN4JX
                fname8031S620-24T16X8Y2CZ(537943),          --S620-24T16X8Y2CZ
                fname8031S5735S-S24P4X-A3(537946),          --S5735S-S24P4X-A3
                fname8031S5735S-S48P4X-A3(537947),          --S5735S-S48P4X-A3           
                fname8031S5731I-L8T2SN(537976),             --S5731I-L8T2SN
                fname8031S5731I-L8T2S2XN(537977),           --S5731I-L8T2S2XN
                fname8031S5731I-L8P2S2XN(537978),           --S5731I-L8P2S2XN
                fname8031S5731I-L16T2S2XN(537979),          --S5731I-L16T2S2XN
                fname8031S5735-L48PN4XE-A-V2(537957),       --S5735-L48PN4XE-A-V2    
                fname8031S5735R-L8T4S-A-V2(537958),         --S5735R-L8T4S-A-V2      
                fname8031S5735R-L8T4X-QA-V2(537959),        --S5735R-L8T4X-QA-V2     
                fname8031S5735R-L8P4S-A-V2(537960),         --S5735R-L8P4S-A-V2      
                fname8031S5735R-L8P4X-QA-V2(537961),        --S5735R-L8P4X-QA-V2     
                fname8031S5735R-L16LP2S-QA-V2(537962),      --S5735R-L16LP2S-QA-V2   
                fname8031S5735R-L16LP2X-QA-V2(537963),      --S5735R-L16LP2X-QA-V2   
                fname8031S5735R-L16LP2UM2X-QA-V2(537964),   --S5735R-L16LP2UM2X-QA-V2
                fname8031S5735R-L16T4S-A-V2(537965),        --S5735R-L16T4S-A-V2     
                fname8031S5735R-L16T4X-QA-V2(537966),       --S5735R-L16T4X-QA-V2    
                fname8031S5735R-L24T4S-A-V2(537967),        --S5735R-L24T4S-A-V2     
                fname8031S5735R-L24T4X-QA-V2(537968),       --S5735R-L24T4X-QA-V2    
                fname8031S5735R-L24P4S-A-V2(537969),        --S5735R-L24P4S-A-V2     
                fname8031S5735R-L24P4X-A-V2(537970),        --S5735R-L24P4X-A-V2     
                fname8031S5735R-L48T4S-A-V2(537971),        --S5735R-L48T4S-A-V2     
                fname8031S5735R-L48T4X-A-V2(537972),        --S5735R-L48T4X-A-V2     
                fname8031S5735R-L48LP4S-A-V2(537973),       --S5735R-L48LP4S-A-V2    
                fname8031S5735R-L48LP4X-A-V2(537974),       --S5735R-L48LP4X-A-V2    
                fname8031S5735R-L48P4X-A-V2(537975),        --S5735R-L48P4X-A-V2
                fname8031S5735I-H8T2XN-V2(537980),          --S5735I-H8T2XN-V2
                fname8031S5735I-H8U2XN-V2(537981),          --S5735I-H8U2XN-V2
                fname8031S5735I-S8U2XN-V2(537982),          --S5735I-S8U2XN-V2
                fname8031S5735I-S48T4XE-V2(538049),         --S5735I-S48T4XE-V2
                fname8031S5755-S24T8J8YZ(537983),           --S5755-S24T8J8YZ      
                fname8031S5755-S24T8Y(537984),              --S5755-S24T8Y         
                fname8031S5755-S24P8J8YZ(537985),           --S5755-S24P8J8YZ      
                fname8031S5755-S24P8Y(537986),              --S5755-S24P8Y         
                fname8031S5755-S24U8J8YZ(537987),           --S5755-S24U8J8YZ      
                fname8031S5755-S24U8Y(537988),              --S5755-S24U8Y         
                fname8031S5755-S48T8YZ(537989),             --S5755-S48T8YZ        
                fname8031S5755-S48T8Y(537990),              --S5755-S48T8Y         
                fname8031S5755-S48P8YZ(537999),             --S5755-S48P8YZ        
                fname8031S5755-S48P8Y(538000),              --S5755-S48P8Y         
                fname8031S5755-S48U8YZ(538001),             --S5755-S48U8YZ        
                fname8031S5755-S48U8Y(538002),              --S5755-S48U8Y         
                fname8031S5755-H24UM4Y2CZ(538003),          --S5755-H24UM4Y2CZ     
                fname8031S5755-H24UM4Y2CZ-T(538004),        --S5755-H24UM4Y2CZ-T   
                fname8031S5755-H48UM4Y2CZ(538005),          --S5755-H48UM4Y2CZ     
                fname8031S5755-H48UM4Y2CZ-T(538006),        --S5755-H48UM4Y2CZ-T   
                fname8031S5751R-L8T2X-QA(538007),           --S5751R-L8T2X-QA      
                fname8031S5751R-L8T2J-QA(538008),           --S5751R-L8T2J-QA      
                fname8031S5751R-L8P2X-QA(538009),           --S5751R-L8P2X-QA      
                fname8031S5751R-L8P2J-QA(538010),           --S5751R-L8P2J-QA      
                fname8031S5751R-L8P2PN2X-QA(538011),        --S5751R-L8P2PN2X-QA   
                fname8031S5751R-L24T4J-QA(538012),          --S5751R-L24T4J-QA     
                fname8031S5751R-L24T2J2X-QA(538013),        --S5751R-L24T2J2X-QA   
                fname8031S5751R-L24P4J-A(538014),           --S5751R-L24P4J-A      
                fname8031S5751R-L24P2J2X-A(538015),         --S5751R-L24P2J2X-A    
                fname8031S5751R-L24P2PN2J2X-A(538016),      --S5751R-L24P2PN2J2X-A 
                fname8031S5735R-S24T8J4X-XA-V2(538017),     --S5735R-S24T8J4X-XA-V2
                fname8031S5735R-S48T4X-XA-V2(538018),       --S5735R-S48T4X-XA-V2  
                fname8031S5735R-S24P4X-V2(538019),          --S5735R-S24P4X-V2     
                fname8031S5735R-S48P4X-V2(538020),          --S5735R-S48P4X-V2     
                fname8031S3510-S8P2PN2X-A(538021),          --S3510-S8P2PN2X-A     
                fname8031S310-48S4X(538050),                --S310-48S4X           
                fname8031S310-48HP4X(538051),               --S310-48HP4X          
                fname8031S310-48PN4X(538024),               --S310-48PN4X          
                fname8031S310-24T8J4X(538025),              --S310-24T8J4X         
                fname8031S620-16X8YZ(538026),               --S620-16X8YZ          
                fname8031S5735S-L8T4X-QA3(538029),          --S5735S-L8T4X-QA3     
                fname8031S5735S-L8P4X-QA3(538030),          --S5735S-L8P4X-QA3     
                fname8031S5735S-L24T4S-QA3(538031),         --S5735S-L24T4S-QA3    
                fname8031S5735S-L24T4X-QA3(538032),         --S5735S-L24T4X-QA3    
                fname8031S5735S-L24T8J4XE-A3(538033),       --S5735S-L24T8J4XE-A3  
                fname8031S5735S-L24P4S-A3(538034),          --S5735S-L24P4S-A3     
                fname8031S5735S-L24P4XE-A3(538035),         --S5735S-L24P4XE-A3    
                fname8031S5735S-L48T4S-A3(538036),          --S5735S-L48T4S-A3     
                fname8031S5735S-L48T4XE-A3(538037),         --S5735S-L48T4XE-A3    
                fname8031S5735S-L48P4S-A3(538038),          --S5735S-L48P4S-A3     
                fname8031S5735S-L48P4XE-A3(538039),         --S5735S-L48P4XE-A3    
                fname8031S5735S-L24PN4XE-A3(538040),        --S5735S-L24PN4XE-A3   
                fname8031S5735S-L48PN4XE-A3(538041),        --S5735S-L48PN4XE-A3   
                fname8031S1730S-S8T4X-QA3(538042),          --S1730S-S8T4X-QA3     
                fname8031S1730S-S8P4X-QA3(538043),          --S1730S-S8P4X-QA3     
                fname8031S1730S-S24T4S-QA3(538044),         --S1730S-S24T4S-QA3    
                fname8031S1730S-S24T4X-QA3(538045),         --S1730S-S24T4X-QA3    
                fname8031S1730S-S24P4S-A3(538046),          --S1730S-S24P4S-A3     
                fname8031S1730S-S24P4X-A3(538047),          --S1730S-S24P4X-A3     
                fname8031S1730S-S48T4X-A3(538048),          --S1730S-S48T4X-A3
                fname8031S5735-L24P4XE-A-V2-BJEX(538085),   --S5735-L24P4XE-A-V2-BJEX
                fname8031S5735-L24P4XE-A-V2-SHEX(538086),   --S5735-L24P4XE-A-V2-SHEX
                fname8031S5735-L24P4XE-A-V2-GDEX(538052),   --S5735-L24P4XE-A-V2-GDEX
                fname8031S5735-L24P4XE-A-V2-JSEX(538053),   --S5735-L24P4XE-A-V2-JSEX
                fname8031S5735-L24P4XE-A-V2-ZJEX(538054),   --S5735-L24P4XE-A-V2-ZJEX
                fname8031S5735-L48T4XE-A-V2-BJEX(538055),   --S5735-L48T4XE-A-V2-BJEX
                fname8031S5735-L48T4XE-A-V2-SHEX(538056),   --S5735-L48T4XE-A-V2-SHEX
                fname8031S5735-L48T4XE-A-V2-GDEX(538057),   --S5735-L48T4XE-A-V2-GDEX
                fname8031S5735-L48T4XE-A-V2-JSEX(538058),   --S5735-L48T4XE-A-V2-JSEX
                fname8031S5735-L48T4XE-A-V2-ZJEX(538059),   --S5735-L48T4XE-A-V2-ZJEX
                fname8031S5735E-L8T4X-QA-V2(538060),        --S5735E-L8T4X-QA-V2     
                fname8031S5735E-L8P4X-QA-V2(538061),        --S5735E-L8P4X-QA-V2     
                fname8031S5735E-L24T4XE-A-V2(538062),       --S5735E-L24T4XE-A-V2    
                fname8031S5735E-L24P4S-A-V2(538063),        --S5735E-L24P4S-A-V2     
                fname8031S5735E-L24P4XE-A-V2(538064),       --S5735E-L24P4XE-A-V2    
                fname8031S5735E-L48T4XE-A-V2(538065),       --S5735E-L48T4XE-A-V2    
                fname8031S5735E-L48LP4S-A-V2(538066),       --S5735E-L48LP4S-A-V2    
                fname8031S5735E-L48LP4XE-A-V2(538067),      --S5735E-L48LP4XE-A-V2   
                fname8031S5735E-S24HS4XE-V2(538068),        --S5735E-S24HS4XE-V2     
                fname8031S5735E-L24ST4XE-A-V2(538069),      --S5735E-L24ST4XE-A-V2   
                fname8031S5735E-S48HS4XE-V2(538070),        --S5735E-S48HS4XE-V2     
                fname8031S5735E-L48S4XE-A-V2(538071),       --S5735E-L48S4XE-A-V2    
                fname8031S5735E-L16LP2X-QA-V2(538072),      --S5735E-L16LP2X-QA-V2   
                fname8031S5735E-L16LP2UM2X-QA-V2(538073),   --S5735E-L16LP2UM2X-QA-V2
                fname8031S6750E-S24T16X8Y2CZ(538074),       --S6750E-S24T16X8Y2CZ    
                fname8031S6750E-S16X10Y2CZ(538075),         --S6750E-S16X10Y2CZ      
                fname8031S5755E-H24HB2Y2CZ(538076),         --S5755E-H24HB2Y2CZ      
                fname8031S6730E-H6FX4Y2CZ-V2(538077),       --S6730E-H6FX4Y2CZ-V2    
                fname8031S310-24U4X(538078),                --S310-24U4X             
                fname8031S530-24T8J4XE(538079),             --S530-24T8J4XE                    
                fname8031S530-48T4XE(538080),               --S530-48T4XE            
                fname8031S550-24T8J8YZ(538081),             --S550-24T8J8YZ          
                fname8031S550-24T8Y(538082),                --S550-24T8Y             
                fname8031S550-48T8YZ(538083),               --S550-48T8YZ            
                fname8031S550-48T8Y(538084),                --S550-48T8Y  
                fname8031S5755-S24UN8YZ(538087),                    --S5755-S24UN8YZ
                fname8031S5755-S24N8YZ(538088),                     --S5755-S24N8YZ
                fname8031S5755-S48UN8YZ(538089),                    --S5755-S48UN8YZ
                fname8031S5755-S48N8YZ(538090),                     --S5755-S48N8YZ
                fname8031S5735-L24HJ4XE-A-V2(538091),               --S5735-L24HJ4XE-A-V2
                fname8031S5735E-L24HJ4XE-A-V2(538092),              --S5735E-L24HJ4XE-A-V2
                fname8031S5735-S24HJ4XE-V2(538093),                 --S5735-S24HJ4XE-V2
                fname8031S5735E-S24HJ4XE-V2(538094),                --S5735E-S24HJ4XE-V2
                fname8031S5735-S48HJ4XE-V2(538095),                 --S5735-S48HJ4XE-V2
                fname8031S5735E-S48HJ4XE-V2(538096),                --S5735E-S48HJ4XE-V2
                fname8031S5735-L24J4X-A-V2(538097),                 --S5735-L24J4X-A-V2
                fname8031S5735-L24J4X-D-V2(538098),                 --S5735-L24J4X-D-V2
                fname8031S5735-L48J4X-A-V2(538100),                 --S5735-L48J4X-A-V2
                fname8031S5735-L48J4X-D-V2(538101),                 --S5735-L48J4X-D-V2
                fname8031S5735-S24J4XE-V2(538103),                  --S5735-S24J4XE-V2
                fname8031S5735E-S24J4XE-V2(538104),                 --S5735E-S24J4XE-V2
                fname8031S5735-S48J4XE-V2(538106),                  --S5735-S48J4XE-V2
                fname8031S5735E-S48J4XE-V2(538107),                 --S5735E-S48J4XE-V2
                fname8031S6730-S24X6Q-V2(538109),                   --S6730-S24X6Q-V2
                fname8031S6730-S48X6Q-V2(538110),                   --S6730-S48X6Q-V2
                fname8031S6330-H24X6C-V2(538111),                   --S6330-H24X6C-V2
                fname8031S6330-H48X6C-V2(538112),                   --S6330-H48X6C-V2
                fname8031S6750-H48X8C(538113),                      --S6750-H48X8C 
                fname8031S5735-L24T4S-A-V2-BJEX(538114),            --S5735-L24T4S-A-V2-BJEX
                fname8031S5735-L24T4S-A-V2-SHEX(538115),            --S5735-L24T4S-A-V2-SHEX
                fname8031S5735-L24T4S-A-V2-GDEX(538116),            --S5735-L24T4S-A-V2-GDEX
                fname8031S5735-L24T4S-A-V2-JSEX(538117),            --S5735-L24T4S-A-V2-JSEX
                fname8031S5735-L24T4S-A-V2-ZJEX(538118),            --S5735-L24T4S-A-V2-ZJEX
                fname8031S5735-L24T4XE-A-V2-BJEX(538119),           --S5735-L24T4XE-A-V2-BJE
                fname8031S5735-L24T4XE-A-V2-SHEX(538120),           --S5735-L24T4XE-A-V2-SHE
                fname8031S5735-L24T4XE-A-V2-GDEX(538121),           --S5735-L24T4XE-A-V2-GDE
                fname8031S5735-L24T4XE-A-V2-JSEX(538122),           --S5735-L24T4XE-A-V2-JSE
                fname8031S5735-L24T4XE-A-V2-ZJEX(538123),           --S5735-L24T4XE-A-V2-ZJE
                fname8031S5735-L24P4S-A-V2-BJEX(538124),            --S5735-L24P4S-A-V2-BJEX
                fname8031S5735-L24P4S-A-V2-SHEX(538125),            --S5735-L24P4S-A-V2-SHEX
                fname8031S5735-L24P4S-A-V2-GDEX(538126),            --S5735-L24P4S-A-V2-GDEX
                fname8031S5735-L24P4S-A-V2-JSEX(538127),            --S5735-L24P4S-A-V2-JSEX
                fname8031S5735-L24P4S-A-V2-ZJEX(538128),            --S5735-L24P4S-A-V2-ZJEX
                fname8031S6750-S24T16X8Y2CZ-BJEX(538129),           --S6750-S24T16X8Y2CZ-BJEX
                fname8031S6750-S24T16X8Y2CZ-SHEX(538130),           --S6750-S24T16X8Y2CZ-SHEX
                fname8031S6750-S24T16X8Y2CZ-GDEX(538131),           --S6750-S24T16X8Y2CZ-GDEX
                fname8031S6750-S24T16X8Y2CZ-JSEX(538132),           --S6750-S24T16X8Y2CZ-JSEX
                fname8031S6750-S24T16X8Y2CZ-ZJEX(538133),           --S6750-S24T16X8Y2CZ-ZJEX
                fname8031S210-24T4JX(538134),                       --S210-24T4JX   
                fname8031S210-24P2J(538135),                        --S210-24P2J   
                fname8031S210-24P4JX(538136),                       --S210-24P4JX   
                fname8031S210I-8T4SX(538137),                       --S210I-8T4SX   
                fname8031S210I-8P4SX(538138),                       --S210I-8P4SX   
                fname8031S210-8T(538140),                           --S210-8T   
                fname8031S210-8T2J(538141),                         --S210-8T2J   
                fname8031S210-8LP2J(538142),                        --S210-8LP2J   
                fname8031S210-8P2J(538143),                         --S210-8P2J   
                fname8031S210-24T2J(538144),                        --S210-24T2J   
                fname8031S5735S-S24T4SE-A3(538145),                 --S5735S-S24T4SE-A3
                fname8031S5735S-S24T4XE-A3(538146),                 --S5735S-S24T4XE-A3
                fname8031S5735S-S24T8J4XE-XA3(538147),              --S5735S-S24T8J4XE-XA3
                fname8031S5735S-S48T4SE-A3(538148),                 --S5735S-S48T4SE-A3
                fname8031S5735S-S48T4XE-A3(538149),                 --S5735S-S48T4XE-A3
                fname8031S5735S-S24ST4XE-A3(538150),                --S5735S-S24ST4XE-A3
                fname8031S5735S-S48S4XE-A3(538151),                 --S5735S-S48S4XE-A3
                fname8031S5751-L16T2X-RUA(538152),                  --S5751-L16T2X-RUA
                fname8031S5751R-L16T2X-QA(538153),                  --S5751R-L16T2X-QA
                fname8031S5751-L16T2J-RUA(538154),                  --S5751-L16T2J-RUA
                fname8031S5751R-L16T2J-QA(538155),                  --S5751R-L16T2J-QA
                fname8031S5751-L16LP2X-RUA(538156),                 --S5751-L16LP2X-RUA
                fname8031S5751R-L16LP2X-QA(538157),                 --S5751R-L16LP2X-QA
                fname8031S5751-L16LP2J-RUA(538158),                 --S5751-L16LP2J-RUA
                fname8031S5751R-L16LP2J-QA(538159),                 --S5751R-L16LP2J-QA
                fname8031S5751-L16LP4UN2X-RUA(538160),              --S5751-L16LP4UN2X-RUA
                fname8031S5751R-L16LP4UN2X-QA(538161),              --S5751R-L16LP4UN2X-QA
                fname8031S5751-L8LP4UN2X-RUA(538162),               --S5751-L8LP4UN2X-RUA
                fname8031S5751R-L8LP4UN2X-QA(538163),               --S5751R-L8LP4UN2X-QA
                fname8031S310S-8P4UN2X(538164),                     --S310S-8P4UN2X
                fname8031S5751-L4LP8UN2X-RUA(538167),               --S5751-L4LP8UN2X-RUA 
                fname8031S5751R-L4LP8UN2X-QA(538168),               --S5751R-L4LP8UN2X-QA
                fname8031S310S-4P8UN2X(538169),                     --S310S-4P8UN2X
                fname8031S5751-L24T2J-RUA(538172),                  --S5751-L24T2J-RUA
                fname8031S5751-L24T2X-RUA(538173),                  --S5751-L24T2X-RUA
                fname8031S5751-L24P2J-RUA(538174),                  --S5751-L24P2J-RUA
                fname8031S5751-L24P2X-RUA(538175),                  --S5751-L24P2X-RUA
                fname8031S5751-L24P2PN2X-RUA(538176),               --S5751-L24P2PN2X-RUA
                fname8031S5755-S48T8YZ-B(538177),                   --S5755-S48T8YZ-B
                fname8031S5755-H24J8T4Y2CZ(538178),                 --S5755-H24J8T4Y2CZ 
                fname8031S5755-H48J4Y2CZ(538179),                   --S5755-H48J4Y2CZ
                fname8031S5755-S48T4X4Y-HT(538180),                 --S5755-S48T4X4Y-HT
                fname8031S5755-S48P4X4Y-HT(538181),                 --S5755-S48P4X4Y-HT
                fname8031S5751-L8LP4JN-RUA(538182),                 --S5751-L8LP4JN-RUA
                fname8031S5751-L8LP4XN-RUA(538183),                 --S5751-L8LP4XN-RUA
                fname8031S5735-S24T4XE-Q-V2(538184),                --S5735-S24T4XE-Q-V2
                fname8031S6750-H48Y8C-B(538185),                    --S6750-H48Y8C-B
                fname8031S5735I-S24F2T2XN-SPE-V2(538186),           --S5735I-S24F2T2XN-SPE-V2
                fname8031S110E-24T(538187),                         --S110E-24T   
                fname8031S110E-24T2J(538188),                       --S110E-24T2J 
                fname8031S110E-24LP2J(538189),                      --S110E-24LP2J
                fname8031S110E-24P2J(538190),                       --S110E-24P2J 
                fname8031S210-4P8UN2X(538191),                      --S210-4P8UN2X
                fname8031S110E-24T-SEA(538192),                     --S110E-24T oversea for V6R25C10
                fname8031S110E-24T2J-SEA(538193),                   --S110E-24T2J oversea for V6R25C10
                fname8031S110E-24LP2J-SEA(538194),                  --S110E-24LP2J oversea for V6R25C10
                fname8031S110E-24P2J-SEA(538195),                   --S110E-24P2J oversea for V6R25C10 
 
-- 8090:
                fname8090Unknown(561152),            -- Quidway unknown FRAME,
                fname8090Whole(561153),              -- Quidway NE80E FRAME, NE5000E FRAME,
                fname8090Half(561154),              -- Quidway NE40E FRAME,
                fname8090HalfLow(561155),            -- Quidway Ne40E FRAME low ,40E
                fname8090BTBMaster(561156),          -- Quidwy NE5000E BTB MASTER FRAME
                fname8090BTBSlave(561157),           -- Quidwy NE5000E BTB Slave FRAME
                fname8090ClusterCentral(561158),     -- Quidwy NE5000E Cluster Central FRAME
                fname8090ClusterLine(561159),        -- Quidwy NE5000E Cluster Line  FRAME
                fname8090Quarter(561160),            -- Quidwy Ne40E-4 FRAME
                fname8090NE40E3DC(561161),          -- Quidwy Ne40E-3 FRAME
                fname8090NE40E3AC(561162),          -- Quidwy Ne40E-3 FRAME
                fname8090HalfX(561163),              -- Quidway NE40E-X8 FRAME,
                fname8090WholeX(561164),             -- Quidway NE80E-X16 FRAME,
                fname8090NE5000EX(561165),          --Quidway NE5000E-X16 FRAME,
                fname8090NE5000E-20(561105),        --Quidway NE5000E-20 FRAME,
                fname8090NE40EX1(561166),           --Quidway NE40E-X1 FRAME,
                fname8090NE40EX2(561167),           --Quidway NE40E-X2 FRAME,
                fname8090NE5000EX-VB(561168),       --Quidway NE5000E-X16VB FRAME,
                fname8090NE40E-X2-M8(561169),       --Quidway CX600-X2-M8 FRAME,ne40e,AC. compatitable with old panel, no "AC" in name
                fname8090NE40E-X1-M4(561170),       -- Quidway CX600-X1-M4 FRAME, ne40e
                fname8090NE40E-X2-M16(561171),      --Quidway CX600-X2-M16 FRAME, ne40e
                fname8090CX600-X2(561172),          --Quidway CX600-X2 FRAME,
                fname8090NE5000EX16A(561173),        --Quidway NE5000E-X16A FRAME,
                fname8090NE5000EX16B(561816),        --Quidway NE5000E-X16B FRAME,
                fname8090NE5000ENGCCC(561174),      --Quidway NE5000E-NGCCC FRAME,
                fname8090NE40E-X16A-AC(561175),        --Quidway NE40E-X16A-AC FRAME
                fname8090NE40E-X2-M8-DC(561176),       --Quidway CX600-X2-M8 FRAME,ne40e,DC
                fname8090NE40E-X8A-AC(561177),          --Quidway NE40E-X8A-AC FRAME,
                fname8090NE5000E-X8A(561178),        --Quidway NE5000E-X8A FRAME,
                fname8090NE40E-X8A-DC(561179),         --Quidway NE40E-X8A-DC FRAME,
    fname8090NE40E-X16A-DC(561180),        --Quidway NE40E-X16A-DC FRAME,
                fname8090NE40E-X8C-DC(562103),         --Quidway NE40E-X8C-DC FRAME,
                fname8090NE40E-X16C-DC(562101),        --Quidway NE40E-X16C-DC FRAME,
                fnameSIG9800-X8A(562200),        --Quidway SIG9800-X8A FRAME,
                fnameSIG9800-X8A-DC(562201),        --Quidway SIG9800-X8A-DC FRAME,
                fnameSIG9800-X8A-HVDC(562202),        --Quidway SIG9800-X8A-HVDC FRAME,
                fnameSIG9800-X16A(562203),        --Quidway SIG9800-X16A FRAME,
                fnameSIG9800-X16A-DC(562204),        --Quidway SIG9800-X16A-DC FRAME,
                fnameSIG9800-X16A-HVDC(562205),        --Quidway SIG9800-X16A-HVDC FRAME,
                fname8090NE40E-X8C(562106),            --Quidway NE40E-X8C FRAME,
                fname8090NE40E-X16C(562105),           --Quidway NE40E-X16C FRAME,
                fname8090NE40E-X8AK(562107),            --Quidway NE40E-X8AK FRAME,
                fname8090NE40E-X8AK-DC(562108),         --Quidway NE40E-X8AK-DC FRAME,
                fname8090NE40E-X8AK-HVDC(562109),       --Quidway NE40E-X8AK-HVDC FRAME,
                fname8090NE40E-X4A(562111),             --Quidway NE40E-X4A FRAME,
                fname8090NE5000E-X8(562031),       --Quidway NE5000E-X8 FRAME,
                fname8090NE40E-M2E(562032),       --Quidway NE40E-M2E FRAME,
                fname8090NE40E-M2F(562033),       --Quidway NE40E-M2F FRAME,
                fname8090NE40E-X3A(562034),          -- Quidwy Ne40E-3A FRAME,
                fname8090NE40E-X2-M8A(562035),          -- Quidwy CX600-X2-M8A FRAME, ne40e
                fname8090NE40E-X2-M8A-DC(562036),       -- Quidwy CX600-X2-M8A-DC  FRAME, ne40e
                fname8090NE40E-X2-M16A(562037),         -- Quidwy CX600-X2-M16A FRAME, ne40e
                fname8090NE9000-20(562038),       --Quidway NE9000-20 FRAME
                fname8090NE40E-M2H(562039),       --Quidway NE40E-M2H FRAME
                fname8090NE9000-8(562054),       --Quidway NE9000-8 FRAME
                fname8090CX6620(562055),       --Quidway CX6620 FRAME
                fname8090CX6608(562056),       --Quidway CX6608 FRAME
                fname8090NE40E-X16A-LS(570076),      --Quidway NE40E-X16A-LS FRAME
                fname8090NE40E-X8A-LS(570075),       --Quidway NE40E-X8A-LS FRAME
                fname8090NE9000-20-LS(570072),       --Quidway NE9000-20-LS FRAME
                fname8090NE9000-8-LS(570071),        --Quidway NE9000-8-LS FRAME

--MA5611S  R015C10
                frameMA5611SAE08(561221),      -- Virtual frame MA5611S-AE08 of MA5611S(sd5130) FTTS device.
                fnameMA5611SAE08PD8VDSL(561575),        --Virtual Frame MA5611S-AE08 of the MA5611S-AE08 8VDSL pd device.
                fnameMA5611SAE16PD16VDSL(561576),       --Virtual Frame MA5611S-AE16 of the MA5611S-AE16 16VDSL pd device.
-- NE40E:
                subbname8090DEVCR5D08DMD1M01(561610),   -- Bidirectional 1-Channel CWDM Optical Add/Drop Multiplexing (1471nm) Physical Interface Card(PIC)
                subbname8090DEVCR5D08DMD1M02(561611),   -- Bidirectional 1-Channel CWDM Optical Add/Drop Multiplexing (1491nm) Physical Interface Card(PIC)
                subbname8090DEVCR5D08DMD1M03(561612),   -- Bidirectional 1-Channel CWDM Optical Add/Drop Multiplexing (1511nm) Physical Interface Card(PIC)
                subbname8090DEVCR5D08DMD1M04(561613),   -- Bidirectional 1-Channel CWDM Optical Add/Drop Multiplexing (1531nm) Physical Interface Card(PIC)
                subbname8090DEVCR5D08DMD1M05(561614),   -- Bidirectional 1-Channel CWDM Optical Add/Drop Multiplexing (1551nm) Physical Interface Card(PIC)
                subbname8090DEVCR5D08DMD1M06(561615),   -- Bidirectional 1-Channel CWDM Optical Add/Drop Multiplexing (1571nm) Physical Interface Card(PIC)
                subbname8090DEVCR5D08DMD1M07(561616),   -- Bidirectional 1-Channel CWDM Optical Add/Drop Multiplexing (1591nm) Physical Interface Card(PIC)
                subbname8090DEVCR5D08DMD1M08(561617),   -- Bidirectional 1-Channel CWDM Optical Add/Drop Multiplexing (1611nm) Physical Interface Card(PIC)
                subbname8090DEVCR5D08DMD2M01(561618),   -- Bidirectional 2-Channel CWDM Optical Add/Drop Multiplexing (1471/1491nm) Physical Interface Card(PIC)
                subbname8090DEVCR5D08DMD2M02(561619),   -- Bidirectional 2-Channel CWDM Optical Add/Drop Multiplexing (1511/1531nm) Physical Interface Card(PIC)
                subbname8090DEVCR5D08DMD2M03(561620),   -- Bidirectional 2-Channel CWDM Optical Add/Drop Multiplexing (1551/1571nm) Physical Interface Card(PIC)
                subbname8090DEVCR5D08DMD2M04(561621),   -- Bidirectional 2-Channel CWDM Optical Add/Drop Multiplexing (1591/1611nm) Physical Interface Card(PIC)
               subbname8090DEVMEOM0E2NCE70(561627),   -- 2-Port 100GBase-CFP2 Flexible Card(BP480-E)
                subbname8090DEVMEOM0LEXFE70(561628),   -- 20-Port 10GBase LAN/WAN-SFP+ Flexible Card(BP480-E)
                subbname8090DEVCR5D0L5XFH71(561629),   -- 5-Port 10GBase LAN/WAN-SFP+ Flexible Card H(P51-H, Occupy two sub-slots)
                subbname8090DEVME0D0L5XXH7F(561630),   -- 5-Port 10GBase LAN/WAN-SFP+ Flexible Card H(BP51-H,occupy 2 sub-slot)
                subbname8090DEVBGWD0L5XFH71(561631),   -- 5-Port 10GBase LAN/WAN-SFP+ Flexible Card(BP100)
                subbname8090DEVCX68LGXF0(561632),   -- 28-Port 10GBase-X-SFP+ + 16-Port 100/1000Base-X-SFP
--M2K-B
                subbname8090DEVCX6PM2KBAS92(561830),   --CX600-M2K Basic Configuration (Includes M2K Chassis, Fixed Interface(4*100GE+12*10GE+10*GE)/2*DC Power/Fan Box,without Software and Document)
 --V8R11C00 NE5000
                subbname8090DEVCR5D00N8NC60(561828), --8-Port 100G OTN/ETH QSFP28 Flexible Card CM(CP1T6,Occupy 1 sub-slot)
                subbname8090DEVCR5D00N8NC61(561829), --8-Port 100G OTN/ETH QSFP28 Flexible Card(CP1T6,Occupy 1 sub-slot)
             --V8R11C00 NE5000E 1.6T
                subbname8090DEVCR59LJXFC(561783),   -- 36-Port 10GBase LAN/WAN-SFP+ Flexible Card(CP1T6,Occupy 1 sub-slot)
                subbname8090DEVCR59E8NBE(561784),   -- 8-Port 100G QSFP28 Flexible Card(CP1T6,Occupy 1 sub-slot)
                subbname8090DEVCR59E2KCA1(561785),  -- 2-Port 400G CFP8 Flexible Card(CP1T6,Occupy 1 sub-slot)

                --V8R11C10 NE5000E 1.6T
                subbname8090DEVCR59T8NBB(561786),  -- 8-Port 100G OTN/ETH QSFP28 Flexible Card(CP1T6,Occupy 1 sub-slot)
                subbname8090DEVCR59E2KBA(561787),  -- 2-Port 400G CFP8 Flexible Card(CP1T6,Occupy 1 sub-slot)

                --V8R11C10 NE9000E 1.6T
                subbname8090DEVCR58E8NBE(561788),   -- 8-Port 100G QSFP28 Flexible Card(CP1T6,Occupy 1 sub-slot)
                subbname8090DEVCR58E4KE4NB0(225725),    --4-Port 400GBase QSFPDD + 4-Port 100GBase QSFP28 Fixed Card
                subbname8090DEVCR9D00D8NC81(225726),    --8-Port 100G-CFP2 Flexible Card CM
                subbname8090DEVME0DE4NE8V70(225727),    --4-Port 100G/8-Port 50GBase-QSFP28 Flexible Card E(P1T-E)
				subbname8090DEVCR5DE4NE8V70(225728),    --8-Port 50G/4-Port 100GBase-QSFP28 Flexible Card E(P1T-E)
				subbname8090DEVCX6DE4NE8V10(225729),    --8-Port 50G/4-Port 100GBase-QSFP28 FlexE/MACsec Flexible Card(S1T)
				subbname8090DEVCX6D0EDYFA10(225730),    --16-Port 25GBase-SFP28 MACsec Flexible Card(S1T)
              subbname8090DEVCR58EENBD0(225731),      --20-Port 100GE-QSFP28 FlexE/MACSec Integrated Line Process Unit CM(LPUI-2T-CM)
              subbname8090DEVCR5D0E5XMF93(225733),      --2-Port 50GBase/1-Port 100GBase-QSFP28 FlexE MACsec Physical Interface Card CM(PIC)(Default Enable 1*50GE)
              subbname8090DEVCR5D0E5XMF94(225769),      --2-Port 50GBase/1-Port 100GBase-QSFP28 FlexE MACsec Physical Interface Card(PIC)
              subbname8090DEVCR5DE2NE4X13(225734),      --2-Port 100GBase-QSFP28 FlexE MACsec Interface Card(Default Enable 1*100GE Enabled)
             subbname8090DEVCR5DE2NE4X14(225770),      --2-Port 100GBase/50GBase-QSFP28 FlexE MACsec Interface Card(PIC)
              subbname8090DEVANKD001EV202(225732),      --2 Channels 50G/1 Channel 100G Base QSFP28 High Speed Interface Board(1*50GE enable by default)
              subbname8090DEVANKD001EV103(225735),      --1 Channel 50G Base QSFP28 High Speed Interface Board
              subbname8090DEVCR2D0E5XMF91(225736),      --2-Port 50GBase/1-Port 100GBase-QSFP28 FlexE MACsec Physical Interface Card CM(PIC)(Default Enable 1*50GE)
              subbname8090DEVCR2D00E4XM25(225737),      --4-Port 25GE(SFP28)/10GE(SFP+) MACsec Physical Interface  Card (PIC)
              subbname8090DEVCR2D00E8XM25(225738),      --8-Port 25GE(SFP28)/10GE(SFP+) MACsec Physical Interface  Card (PIC)
              subbname8090DEVCR2D00E4XF20(225739),      --4-Port 10GBase-SFP+MACsec Interface Card
              subbname8090DEVCR2D00E1NB20(225740),      --1-Port 100GBase-QSFP28+MACsec Interface Card
              subbname8090DEVCR2DE2NE4X10(225741),      --2-Port 100GBase-QSFP28/1-Port100GBase-QSFP28+4-Port 10GBase-SFP+MACsec Interface Card
              subbname8090DEVCR2D00LAXF91(225742),      --10-Port 10GBase LAN/WAN-SFP+ MACsec Physical Interface Card(PIC)
              subbname8090DEVANKD001EV104(225743),      --1 Channel 50G Base QSFP28 High Speed Interface Board CM(30GE enable by default)
              subbname8090DEVANKD001EV105(225744),      --1 Channel 50G Base QSFP28 High Speed Interface Board
              subbname8090DEVCR5D00EDYB70(225748),    --16-Port 25GBase-SFP28 Flexible Card E(P1T-E)
              subbname8090DEVCR57E8YFA0(225750),        --8-Port 25GBase-SFP28 Integrated Integrated Service Unit (ISUI-201)
              subbname8090DEVCR57LKXFB0(225745),        --40-Port 10GBase-SFP+ Integrated Line Process Unit(NE40E LPU400A))
              subbname8090DEVCR58LPXFA0(225746),        --60-Port 10GBase LAN/WAN-SFP+ MACSec Integrated Line Process Unit(NE9000 LPUI-1T)
              subbname8090DEVCR56LFXFB3(225749),        --24-Port 10GBase LAN/WAN SFP+ Flexible Card(CP1T,Occupy 1 sub-slot)
              subbname8090DEVCR57EENBC1(225753),        --20-Port 100GBase QSFP28 Integrated Line Process Unit(LPUI-2TA)
              subbname8090DEVCX62E2NBD0(225751),        --2-Port 100GBase-QSFP28 FlexE/MACsec Integrated Integrated Service Unit (ISUI-201)
              subbname8090DEVCX62E4NBC0(225752),        --4-Port 100GBase-QSFP28 FlexE/MACsec Integrated Integrated Service Unit(ISUI-401)
              subbname8090DEVCR57LKXFB1(225754),        --40-Port 10Gase LAN/WAN-SFP+ MACsec Integrated Line Processing Unit (LPUI-400A)
              subbname8090DEVCR57E4NBC1(225755),        --4-Port 100GBase-QSFP28 FlexE/MACsec Integrated Line Processing Unit-A
              subbname8090DEVCR57LFXFF0(225756),        --24-Port 10GBase LAN/WAN-SFP+ MACsec Integrated Line Processing Unit
              subbname8090DEVCR57LFXFF1(225757),        --24-Port 10GBase LAN/WAN-SFP+ MACsec Integrated Line Processing Unit-A
              subbname8090DEVCR57E8YFA1(225758),        --8-Port 25GBase-SFP28 MACsec Integrated Line Processing Unit A
			  subbname8090DEVCR5D0LFXFM20(482067),   -- 20-Port 10GBase LAN/WAN-SFP+ Flexible Card(P483)
			  subbname8090DEVCR5D0LEXFM20(483067),   -- 20-Port 10GBase LAN/WAN-SFP+ Flexible Card(P483)
              subbname8090DEVME0M0LEXFB76(108199),   -- 20-Port 10GBase LAN/WAN-SFP+ Flexible Card(P483)
              subbname8090DEVCR8D00E4XFD0(998318),   -- 4-Port 10GE-SFP+ FlexE MACsec Physical Interface Card(PIC)
              subbname8090DEVGPLI36YS10CQES1(582391),   -- 36-Port 25GE(SFP28)/10GE(SFP+)/GE(SFP) 10-Port 100GBase QSFP28 Integrated Line Process Unit
              subbname8090DEVCR8D00E4XFC4(694693),   -- 4-Port 10GE-SFP+ FlexE MACsec Physical Interface Card(PIC)
              subbname8090DEVGPLI72YSE8(778133),   -- 72-Port 25GE(SFP28)/10GE(SFP+)/GE(SFP) Integrated Line Processing Unit
              subbname8090DEVGPLI72YSES7(464797),   -- 72-Port 25GE(SFP28)/10GE(SFP+)/GE(SFP) Integrated Line Processing Unit
              subbname8090DEVCR8D00E4XFC5(582390),   -- 4-Port 10GE-SFP+ FlexE MACsec Physical Interface Card(PIC)
              subbname8090DEVDPE1E4NBIYF(258024),   -- 4-Port 100GBase-QSFP28 or 16-Port 25GBase-SFP28 Combo + 16-Port 25GBase-SFP28
              subbname8090DEVDPE1E4NBIYFS(258023),   -- 4-Port 100GBase-QSFP28 or 16-Port 25GBase-SFP28 Combo + 16-Port 25GBase-SFP28
              subbname8090DEVCR5D00E8GF80(215300),   -- 8 Channels GE/FE Optical Interface Board
              subbname8090DEVCR5D0L6XFA71(591763),   -- 6-Port 10GBase LAN/WAN-SFP+ Flexible Card A(P120-A)
              subbname8090DEVCR5DE4NE8V73(513209),   -- 4-Port 100GBase-QSFP28 FlexE Flexible Card(P1T)
			  subbname8090DEVCX6DE4NE8VA0(229729),   -- 4-Port 100GBase-QSFP28 FlexE Flexible Card(S1T)
              subbname8090DEVCR5DE2NBFM72(973460),   -- 2-Port 100GBase-QSFP28 Flexible Card(P483)
              subbname8090DEVANKD00EX4S01(225762),      --4 Channels 10GE Optical Interface Board(SFP+)
              subbname8090DEVANKD00EX2S01(225763),      --2 Channels 10GE Optical Interface Board(SFP+)
              subbname8090DEVANDD0EM10F00(225764),      --10 Channels GE/FE Optical Interface Board
              subbname8090DEVCR57E2NLEXB1(225765),      --2-Port 100GBase-QSFP28 + 20-Port 10GBase LAN/WAN-SFP+ Integrated Line Processing Unit
              subbname8090DEVANKD001EV203(225767),      --2 Channels 50G/1 Channel 100G Base QSFP28 High Speed Interface Board
              subbname8090DEVANKD001EV204(225768),      --2 Channels 50G/1 Channel 100G Base QSFP28 High Speed Interface Board
              subbname8090DEVCR2D0E5XMF93(225771),      --2-Port 50GBase/1-Port 100GBase-QSFP28 FlexE MACsec Physical Interface Card (PIC)(Enable 2*50GE)
              subbname8090DEVCR5D00EAGF96(225772),      --10-port 100/1000Base-X-SFP MACsec Physical Interface Card(PIC)
              subbname8090DEVCR5D00L4XF91(225773),      --4-Port 10GE(SFP+)/GE(SFP) MACsec Physical Interface Card(PIC)
              subbname8090DEVCR59LPXFA0(225761),        --60-Port 10GBase LAN/WAN-SFP+ MACSec Integrated Line Process Unit
              subbname8090DEVCR59EENBD0(225766),        --20-Port 100GE-QSFP28 FlexE/MACSec Integrated Line Process Unit
			  subbname8090DEVANND001EN100(934629),   -- 1-Port 100GE CFP2 Physical Interface Card
			  subbname8090DEVCR5D00E1KB74(452214),   -- 1-Port 400GBase-QSFP-DD + 2-Port External OA Flexible Card(P1T)
			  subbname8090DEVCR5D00E1KB75(541988),   -- 1-Port 400GBase-QSFP-DD + 2-Port External OA Flexible Card(P1T-CM, 100G Enabled by Default)
			  subbname8090DEVIG2D00E1KB72(443624),   -- 1-Port 400GBase-QSFP-DD + 2-Port External OA Flexible Card(P1T)
			  subbname8090DEVCR57EENBD0(887788),   -- 20-Port 100GBase-QSFP28 FlexE/MACsec Integrated Line Processing Unit
			  subbname8090DEVCR57EENBDS0(198210),   -- 20-Port 100GBase-QSFP28 FlexE/MACsec Integrated Line Processing Unit
			  subbname8090DEVGPLI36YS10CQE2(582392),   -- 36-Port 25GE(SFP28)/10GE(SFP+)/GE(SFP) 10-Port 100GBase QSFP28 Integrated Line Process Unit
			  subbname8090DEVGPLI8KQ8CQES4(824727),   -- 8-Port 400GBase QSFPDD 8-Port 100GBase QSFP28 Integrated Line Process Unit
			  subbname8090DEVGPLI8KQ8CQE5(806150),   -- 8-Port 400GBase QSFPDD 8-Port 100GBase QSFP28 Integrated Line Process Unit
			  subbname8090DEVGPI2KFE1(675384),   -- 20-Port 100GBase-QSFP28 FlexE/MACsec Integrated Line Processing Unit
              subbname8090DEVCR2D0LBXFME0(784745),   -- 12-Port 10GBase LAN/WAN-SFP+ MACsec Flexible Card(P243G)
              subbname8090DEVCR2DE1NBFME0(784746),   -- 2-Port 50GBase/1-Port 100GBase-QSFP28 MACsec Flexible Card (P243G)
			  subbname8090DEVCR5D0LFXFM76(303393),   -- 24-Port 10GBase LAN/WAN-SFP+ MACsec Flexible Card(P483D)
              subbname8090DEVCR5DE1NBFM76(656681),   -- 2-Port 50GBase/1-Port 100GBase-QSFP28 FlexE/MACsec Flexible Card(P243D)
              subbname8090DEVCR5D0LBXFM76(878564),   -- 12-Port 10GBase LAN/WAN-SFP+ MACsec Flexible Card (P243D)
              subbname8090DEVCR5D0EFGFM76(945736),   -- 24-Port 100/1000Base-X-SFP MACsec Flexible Card (P53D)
			  subbname8090DEVCR57L8XEDI0(295993),    --8-Port GE-SFP/10GE-SFP+ and 16-Port GE-SFP Unflexible Card(P243)
			  subbname8090DEVGPLI10CQ36XSES1(582393),   -- 36-Port 10GE(SFP+)/GE(SFP) 10-Port 100GBase QSFP28 Integrated Line Process Unit
              subbname8090DEVGPLI10CQ36XSE2(582394),   -- 36-Port 10GE(SFP+)/GE(SFP) 10-Port 100GBase QSFP28 Integrated Line Process Unit
			  subbname8090DEVGFL72GSFB(548674),      -- 72-port GE MACsec Physical Interface Card(PIC)
			  subbname8090DEVCR8DERGF00F1(548774),   -- NetEngine 8000 F 2T Switch Routing Unit(SRU-2T-A)
			  subbname8090DEVME0D00E1KB71(542988),   -- 1-Port 400GBase-QSFP-DD + 2-Port External OA Flexible Card(BP1T)
			  subbname8090DEVGPR8CQ20YSD(650885),   -- 8-Port 100GBase-QSFP28 + 20-Port 25GBase-Y-SFP+
              subbname8090DEVTNR1E4NBIYFS(258025),   -- 4-Port 100GBase-QSFP28 or 16-Port 25GBase-SFP28 Combo + 16-Port 25GBase-SFP28
              subbname8090DEVCR81E4NBIYFS(258026),   -- 4-Port 100GBase-QSFP28 or 16-Port 25GBase-SFP28 Combo + 16-Port 25GBase-SFP28
              subbname8090DEVCR81E4NBIYF(258027),    -- 4-Port 100GBase-QSFP28 or 16-Port 25GBase-SFP28 Combo + 16-Port 25GBase-SFP28
			  subbname8090DEVGPLI72XSE1(778134),   -- 72-Port 25GE(SFP28)/10GE(SFP+)/GE(SFP) Integrated Line Processing Unit
			  subbname8090DEVCR8DE4YBMSF0(998319),      --4-Port 25GE(SFP28)/10GE(SFP+) MACsec Physical Interface Card (PIC)
			  subbname8090DEVCR8D0LJXXCCP(513217),   -- 36-Port 10GBase LAN/WAN-SFP+ MACsec Flexible Card CM(P1T-CM)
              subbname8090DEVCR8D0LJXX0CP(513214),   -- 36-Port 10GBase LAN/WAN-SFP Flexible Card CM(P1T-CM)
              subbname8090DEVCR8D0LJXXCDP(513215),   -- 36-Port 10GBase LAN/WAN-SFP+ MACsec Flexible Card CM(P1T-E-CM)
              subbname8090DEVCR8D0E5NBCCP(513218),   -- 5-Port 100GBase-QSFP28 FlexE MACsec Flexible Card CM(P1T-CM)
              subbname8090DEVCR8D0E5NBCDP(513216),   -- 5-Port 100GBase-QSFP28 FlexE MACsec Flexible Card CM(P1T-E-CM)
              subbname8090DEVCR8DEANBFECP(513220),   -- 10-Port 100GBase-QSFP28 FlexE MACsec Flexible Card CM(P2T-CM)
              subbname8090DEVCR8DE2KE2NCP(513219),   -- 2-Port 400GBase-QSFP-DD + 2-Port 100GBase-QSFP28 FlexE MACsec Flexible Card CM(P2T-CM)
		      subbname8090DEVCR5DE2NBFM77(513210),   -- 2-Port 100GBase-QSFP28 Flexible Card A(P486-A)
              subbname8090DEVCR5DE2NBFM78(513211),   -- 2-Port 100GBase-QSFP28 Flexible Card A(P486-A)
              subbname8090DEVCR5DE2NBFM79(513212),   -- 2-Port 100GBase-QSFP28 Flexible Card A(P486-A)
              subbname8090DEVME0M0E2NFB7B(513213),   -- 2-Port 100GBase-QSFP28 Flexible Card A(BP486-A)
		      subbname8090DEVGFL72XSGB(548676),      -- 72-port 10GE MACsec Physical Interface Card(PIC)
              subbname8090DEVCR8DERXFMSF0(548776),   -- 72-port 10GE-SFP+ FlexE MACsec Combined Line Processing Unit(LPUC-800-CM)
			  subbname8090DEVCR810LJXX0CP(513221),   -- 36-Port 10GBase LAN/WAN-SFP Flexible Card CM(P1T-CM)
			  subbname8090DEVCR8DEKNBXFF0(548775),   -- 4-Port 100GBase-QSFP28 + 40-port 10GE/GE LAN/WAN-SFP+ Combined Line Processing Unit(LPUC-800-CM)
			  subbname8090DEVGFL4CQ40XSG(548677),   -- 4-Port 100GBase-QSFP28 + 40-port 10GE/GE LAN/WAN-SFP+ Interface Card(PIC)
			  subbname8090DEVCR8DE1KB00F0(548778),   -- 1-Port 400GBase-QSFP-DD Combined Line Processing Unit CM Basic Setup Bundle(Including LPUC-400-CM, default enable 100G)
              subbname8090DEVCR8DE8NB00F0(548779),   -- 8-Port 100GBase-QSFP28 Combined Line Processing Unit(LPUC-800-CM)
              subbname8090DEVGFL1KQG(548679),        -- 1-Port 400GBase-QSFP-DD Interface Card(PIC)
              subbname8090DEVGFL8CQG(548678),        -- 8-Port 100GBase-QSFP28 Interface Card(PIC)
              subbname8090DEVCR8DE1N8XFM0(548680),   -- 1-Port 100GBase-QSFP28 FlexE MACsec + 8-Port 10GBase-SPF+ MACsec Physical Interface Card(PIC)
              subbname8090DEVCR5DE1N8XFM0(548681),   -- 1-Port 100GBase/50GBase-QSFP28 FlexE MACsec or 8-port 10GE(SFP+)/GE(SFP) MACsec Physical Interface Card(PIC)
			  subbname8090DEVCR59EDNBE(709794),         -- 16-Port 100GBase QSFP28
              subbname8090DEVCR59E4KBC(709795),         -- 4-Port 400GBase QSFP-DD
              subbname8090DEVCR59E2EBA(709825),         -- 2-Port 800GBase QSFP-DD
              subbname8090DEVGPR8CQ20YSC1(548684),    -- 8-Port 100GBase-QSFP28 + 20-Port 25GBase-Y-SFP+
              subbname8090DEVCR59E8NBH(709796),       -- 16-Port 100GBase QSFP28 Integrated Line Process Unit C(NE5000E LPUI-1T6-H)
			  subbname8090DEVNetEngine-A812E-S(115923),   --CARD NetEngine A812E-S
		      subbname8090DEVGFL24XS48GSF(548682),            -- 24-Port 10GE/GE LAN/WAN-SFP+ MACsec + 48-port GE(100/1000Base-X-SFP) MACsec Physical Interface Card(PIC)
			  subbname8090DEVGFL2KQG(548783),            -- 2-Port 400GBase-QSFP-DD Interface Card(PIC)
              subbname8090DEVCR8D8E5NBCC0(513222),   -- 5-Port 100GBase-QSFP28 FlexE MACsec Flexible Card CM(P1T-CM)
              subbname8090DEVCR8D8E5NBCL0(513223),   -- 5-Port 100GBase-QSFP28 FlexE MACsec Flexible Card L CM(P1T-L-CM)
              subbname8090DEVCR8D8LJXXCC0(513224),   -- 36-Port 10GBase LAN/WAN-SFP+ MACsec Flexible Card CM(P1T-CM)
              subbname8090DEVCR8D8LJXXCL0(513225),   -- 36-Port 10GBase LAN/WAN-SFP+ MACsec Flexible Card L CM(P1T-L-CM)
              subbname8090DEVCR8D82KE2NC0(513226),   -- 2-Port 400GBase-QSFP-DD FlexE + 2-Port 100GBase-QSFP28 Flexible Card CM(P2T-CM)
              subbname8090DEVCR8D82KE2NL0(513227),   -- 2-Port 400GBase-QSFP-DD FlexE + 2-Port 100GBase-QSFP28 Flexible Card L CM(P2T-L-CM)
              subbname8090DEVCR8D8ANBFEC0(513228),   -- 10-Port 100GBase-QSFP28 FlexE MACsec Flexible Card CM(P2T-CM)
              subbname8090DEVCR8D8ANBFEL0(513229),   -- 10-Port 100GBase-QSFP28 FlexE MACsec Flexible Card L CM(P2T-L-CM)
              subbname8090DEVCR8D8E5NBCE0(513230),   -- 5-Port 100GBase-QSFP28 FlexE MACsec Flexible Card E CM(P1T-E-CM)
              subbname8090DEVCR8D8LJXXCE0(513231),   -- 36-Port 10GBase LAN/WAN-SFP+ MACsec Flexible Card E CM(P1T-E-CM)
			  subbname8090DEVCR8DE2NB00M0(548690),   -- 2-Port 100GBase/50GBase-QSFP28 Interface Card(PIC)
              subbname8090DEVCR8DE2NBMSF0(548691),   -- 2-Port 100GBase/50GBase-QSFP28 Interface Card(PIC)
              subbname8090DEVCR8DE2NBMSF1(548692),   -- 2-Port 100GBase/50GBase-QSFP28 Interface Card(PIC)
              subbname8090DEVCR8DE2NB00M1(548699),   -- 2-Port 100GBase/50GBase-QSFP28 Interface Card(PIC)
	     subbname8090DEVGPI6EQ36KQES0(513327),   -- 6-port 800GBase QSFPDD800-36-Port 400GBase QSFPDD Integrated Line Process Unit
              subbname8090DEVCR8DE1KB00M3(548683),   -- 1-Port 400GBase-QSFP-DD Single-layer Physical Interface Card(PIC)
              subbname8090DEVCR8DE1KB00M1(548685),   -- 1-Port 400GBase-QSFP-DD Single-layer Physical Interface Card(PIC)
              subbname8090DEVCR8DE1KB00M4(548686),   -- 1-Port 400GBase-QSFP-DD Single-layer Physical Interface Card CM(Enable 1*100G)(PIC)
              subbname8090DEVCR8DE1KB00M2(548687),   -- 1-Port 400GBase-QSFP-DD Single-layer Physical Interface Card CM(Enable 1*100G)(PIC)
              subbname8090DEVCR8DE4NB00M3(548693),    -- 4-Port 100GBase/50GBase-QSFP28 Physical Interface Card(PIC)
              subbname8090DEVCR8DE4NB00M1(548694),    -- 4-Port 100GBase/50GBase-QSFP28 Physical Interface Card(PIC)
              subbname8090DEVCR8DE4NB00M2(548695),    -- 4-Port 100GBase/50GBase-QSFP28 Physical Interface Card CM(Enable 2*100GE by default)(PIC)
              subbname8090DEVCR8DPMUF00X1(513250),    -- V8R23C10 for CR8DPMUF00X1(SBOM) 16-Port 10GE(SFP+)/GE(SFP) + 16-Port 155M/16-Port 622M/8-Port 2.5G/2-Port 10GPOS Flexible Card CM(P1T-CM)
              subbname8090DEVCR8DPMUF00XA(513251),    -- V8R23C10 for CR8DPMUF00XA(SBOM) 16-Port 10GE(SFP+)/GE(SFP) + 16-Port 155M/16-Port 622M/8-Port 2.5G/2-Port 10GPOS Flexible Card CM(P1T-CM)
              subbname8090DEVCR8DPMUF00XB(513252),    -- V8R23C10 for CR8DPMUF00XB(SBOM) 16-Port 10GE(SFP+)/GE(SFP) + 16-Port 155M/16-Port 622M/8-Port 2.5G/2-Port 10GPOS Flexible Card CM(P1T-CM)
              subbname8090DEVCR8DPMUF00XC(513253),    -- V8R23C10 for CR8DPMUF00XC(SBOM) 16-Port 10GE(SFP+)/GE(SFP) + 16-Port 155M/16-Port 622M/8-Port 2.5G/2-Port 10GPOS Flexible Card CM(P1T-CM)
              subbname8090DEVCR8D8MUF00L1(513254),    -- V8R23C10 for CR8D8MUF00L1(SBOM) 16-Port 10GE(SFP+)/GE(SFP) + 16-Port 155M/16-Port 622M/8-Port 2.5G/2-Port 10GPOS Flexible Card L CM (P1T-L-CM)
              subbname8090DEVCR8D8MUF00X1(513255),    -- V8R23C10 for CR8D8MUF00X1(SBOM) 16-Port 10GE(SFP+)/GE(SFP) + 16-Port 155M/16-Port 622M/8-Port 2.5G/2-Port 10GPOS Flexible Card (P1T-CM)
              subbname8090DEVCR8DPMUF00X1-(513256),    -- V8R23C10 for CR8DPMUF00X1(SBOM) 16-Port 10GE(SFP+)/GE(SFP) + 16-Port 155M/16-Port 622M/8-Port 2.5G/2-Port 10GPOS Flexible Card CM(P1T-CM)
              subbname8090DEVCR8DPMUF00XA-(513257),    -- V8R23C10 for CR8DPMUF00XA(SBOM) 16-Port 10GE(SFP+)/GE(SFP) + 16-Port 155M/16-Port 622M/8-Port 2.5G/2-Port 10GPOS Flexible Card CM(P1T-CM)
              subbname8090DEVCR8DPMUF00XB-(513258),    -- V8R23C10 for CR8DPMUF00XB(SBOM) 16-Port 10GE(SFP+)/GE(SFP) + 16-Port 155M/16-Port 622M/8-Port 2.5G/2-Port 10GPOS Flexible Card CM(P1T-CM)
              subbname8090DEVCR8DPMUF00XC-(513259),    -- V8R23C10 for CR8DPMUF00XC(SBOM) 16-Port 10GE(SFP+)/GE(SFP) + 16-Port 155M/16-Port 622M/8-Port 2.5G/2-Port 10GPOS Flexible Card CM(P1T-CM)
              subbname8090DEVCR8D8MUF00L1-(513260),    -- V8R23C10 for CR8D8MUF00L1(SBOM) 16-Port 10GE(SFP+)/GE(SFP) + 16-Port 155M/16-Port 622M/8-Port 2.5G/2-Port 10GPOS Flexible Card L CM (P1T-L-CM)
              subbname8090DEVCR8D8MUF00X1-(513261),    -- V8R23C10 for CR8D8MUF00X1(SBOM) 16-Port 10GE(SFP+)/GE(SFP) + 16-Port 155M/16-Port 622M/8-Port 2.5G/2-Port 10GPOS Flexible Card (P1T-CM)
			  subbname8090DEVCR59LJXFD(709799),      -- 36-Port 10GBase LAN/WAN-SFP+ Fixed Daughter Card
              subbname8090DEVCR8DFA0E00M1(548790),      -- 4-Port FXS/FXO + 2-Port E&M + 2-Port RS232 + 2-Port RS485 Physical Interface Card(PIC)
              subbname8090DEVCR8DFA0E00M2(548791),      -- 4-Port FXS/FXO + 2-Port E&M + 2-Port RS232 + 2-Port RS485 Physical Interface Card(PIC)
              subbname8090DEVCR5D00E1ND7A(513232),   -- 1-Port 100GBase-QSFP28 Flexible Card A(P246-A)
              subbname8090DEVCR5D00E1ND7B(513234),   -- 1-Port 100GBase-QSFP28 Flexible Card A(P246-A)
              subbname8090DEVCR5D00E1ND7C(513235),   -- 1-Port 100GBase-QSFP28 Flexible Card A(P246-A)
              subbname8090DEVME03E1NBJ0(513236),     -- 1-Port 100GBase-QSFP28 Flexible Card A(BP246-A)
              subbname8090DEVGPR16KQ56CQS(226960),     -- 16-Port 400GBase-QSFPDD + 56-Port 100GBase-QSFP28
              subbname8090DEVCR8DE4KEDNL0(709810),     -- 4-Port 400GBase-QSFP-DD + 16-Port 100GBase-QSFP28 FlexE Flexible Card L CM(P6T4-L-CM,400GE Port Enabled with 100GE by default)
              subbname8090DEVCR8DE4KEDND0(709811),     -- 4-Port 400GBase-QSFP-DD + 16-Port 100GBase-QSFP28 FlexE Flexible Card CM(P6T4-CM,400GE Port Enabled with 100GE by default)
              subbname8090DEVCR8DE4KEDNE0(709812),     -- 4-Port 400GBase-QSFP-DD + 16-Port 100GBase-QSFP28 FlexE Flexible Card E CM(P6T4-E-CM,400GE Port Enabled with 100GE by default)
              subbname8090DEVCR8D84KEDNL0(709813),     -- 4-Port 400GBase-QSFP-DD + 16-Port 100GBase-QSFP28 FlexE Flexible Card L CM(P6T4-L-CM,400GE Port Enabled with 100GE by default)
              subbname8090DEVCR8D84KEDNC0(709814),     -- 4-Port 400GBase-QSFP-DD + 16-Port 100GBase-QSFP28 FlexE Flexible Card CM(P6T4-CM,400GE Port Enabled with 100GE by default)
              subbname8090DEVCR8D84KEDNE0(709815),     -- 4-Port 400GBase-QSFP-DD + 16-Port 100GBase-QSFP28 FlexE Flexible Card E CM(P6T4-E-CM,400GE Port Enabled with 100GE by default)
              subbname8090DEVCR8DE4KEDND1(709816),     -- 4-Port 400GBase-QSFP-DD + 16-Port 100GBase-QSFP28 FlexE Flexible Card CM(P6T4-CM,400GE Port Enabled with 100GE by default)
              subbname8090DEVCR8DE4KEDND9(709817),     -- 4-Port 400GBase-QSFP-DD + 16-Port 100GBase-QSFP28 FlexE Flexible Card CM(P6T4-CM,400GE Port Enabled with 100GE by default)
              subbname8090DEVCR59EFNBA0(709800),     --  24-Port 100GBase QSFP28
              subbname8090DEVCR59EFNBA1(709801),     --  24-Port 100GBase QSFP28
              subbname8090DEVCR59EAKBA0(709802),     --  10-Port 400GBase QSFP-DD
              subbname8090DEVCR59EAKBA1(709803),     --  10-Port 400GBase QSFP-DD
              subbname8090DEVCR5D0LAXFE7P(513240),   -- 10-Port 10GBase LAN/WAN-SFP+ MACsec Flexible Card(P246-A)
              subbname8090DEVCR5D0LAXFE7Q(513241),   -- 10-Port 10GBase LAN/WAN-SFP+ MACsec Flexible Card(P246-A)
              subbname8090DEVCR5D0LAXFE7R(513242),   -- 10-Port 10GBase LAN/WAN-SFP+ MACsec Flexible Card(P246-A)
              subbname8090DEVME0D0LAXFH7K(513243),   -- 10-Port 10GBase LAN/WAN-SFP+ MACsec Flexible Card(P246-A)
			  virent8090DEVCR8DE1KB00F1(548784),            -- 1-Port 400GBase-QSFP-DD Combined Line Processing Unit CM Basic Setup Bundle(Including LPUC-400-CM, default enable 100G)
              virent8090DEVCR8DE8NB00F1(548785),            -- 8-Port 100GBase-QSFP28 Combined Line Processing Unit(LPUC-800-CM)
              virent8090DEVCR8DEKNBXFF1(548786),            -- 4-Port 100GBase-QSFP28 + 40-port 10GE/GE LAN/WAN-SFP+ Combined Line Processing Unit(LPUC-800-CM)
              virent8090DEVCR8DE2KB00F1(548787),            -- 2-Port 400GBase-QSFP-DD Combined Line Processing Unit(LPUC-800-CM)
              virent8090DEVCR8DERXFMSF1(548788),            -- 72-port 10GE/GE LAN/WAN-SFP+ MACsec Combined Line Processing Unit(LPUC-800-CM)
              subbname8090DEVME0D00L1NB7K(548789),            -- 1-Port 100GBase-QSFP28 Flexible Card A(BP246-A)
              subbname8090DEVCR8DE8YF0026(513244),            -- 8-Port 25GE(SFP28)/10GE(SFP+)  Physical Interface Card (PIC)
              subbname8090DEVCR8DE8EFFEC2(513245),            -- 8-Port 10GE-SFP+ FlexE Physical Interface Card(PIC)
              subbname8090DEVCR8DE8YF0025(513246),            -- 8-Port 10GE-SFP+ FlexE Physical Interface Card(PIC)
              subbname8090DEVCR8DE8EFFEC1(513247),            -- 8-Port 10GE-SFP+ FlexE Physical Interface Card(PIC)
			  subbname8090DEVCR8DE8YBMSF0(549693),     --  8-Port 25GE(SFP28)/10GE(SFP+) MACsec Physical Interface Card (PIC)
              subbname8090DEVCR8DE8YBMSF1(549694),     --  8-Port 25GE(SFP28)/10GE(SFP+) MACsec Physical Interface Card (PIC)
			  subbname8090DEVCR8DL8EFFEC1(549696),     --  8-Port 10GE LAN/WAN-SFP+ FlexE MACsec Physical Interface Card(PIC)
              subbname8090DEVCR8D00L8XFD1(549698),     --  8-Port 10GE LAN/WAN-SFP+ FlexE MACsec Physical Interface Card(PIC)
              subbname8090DEVCR8D00L8XFD0(549697),     --  8-Port 10GE LAN/WAN-SFP+ FlexE MACsec Physical Interface Card(PIC)
			  subbname8090DEVGFL1KQGA(549679),        -- 1-Port 400GBase-QSFP-DD Interface Card(PIC)
              subbname8090DEVGFL8CQGA(549678),        -- 8-Port 100GBase-QSFP28 Interface Card(PIC)
              subbname8090DEVGFL4CQ40XSGA(549677),   -- 4-Port 100GBase-QSFP28 + 40-port 10GE/GE LAN/WAN-SFP+ Interface Card(PIC)
              subbname8090DEVGFL2KQGA(549783),            -- 2-Port 400GBase-QSFP-DD Interface Card(PIC)
              subbname8090DEVGFL72XSGBA(549676),      -- 72-port 10GE MACsec Physical Interface Card(PIC)
              subbname8090DEVCR8DG80E00M1(513248),            -- 10-Port C37.94 Physical Interface Card(PIC)
              subbname8090DEVCR8DG80E00M2(513249),            -- 10-Port C37.94 Physical Interface Card(PIC)
              subbname8090DEVCR8DE6LEJKXA(709804),            -- 6-Port 800GBase-QSFP-DD + 36-Port 400GBase-QSFP-DD Integrated Line Processing Unit CM(LPUIA-19T2-CM,Enable 6*400GE + 36*100GE by default)
              subbname8090DEVCR8D800E8KE1(709866),            -- 8-Port 400GBase-QSFP-DD FlexE MACsec Flexible Card E CM(P6T4-E-CM,400GE Port Enabled with 100GE by default)
              subbname8090DEVCR8D800E8KL1(709867),            -- 8-Port 400GBase-QSFP-DD FlexE MACsec Flexible Card L CM(P6T4-L-CM,400GE Port Enabled with 100GE by default)
              subbname8090DEVCR8D800E8KC1(709868),            -- 8-Port 400GBase-QSFP-DD FlexE MACsec Flexible Card CM(P6T4-CM,400GE Port Enabled with 100GE by default)
              subbname8090DEVCR8DE4KBFECP(709840),            -- 4-Port 400GBase-QSFP-DD FlexE MACsec Flexible Card CM(P3T2-CM,400GE Port Enabled with 100GE by default)
              subbname8090DEVCR8DE4KBFEEP(709841),            -- 4-Port 400GBase-QSFP-DD FlexE MACsec Flexible Card E CM(P3T2-E-CM,400GE Port Enabled with 100GE by default)
              subbname8090DEVCR8DE4KBFELP(709842),            -- 4-Port 400GBase-QSFP-DD FlexE MACsec Flexible Card L CM(P3T2-L-CM,400GE Port Enabled with 100GE by default)
              subbname8090DEVCR8D84KBFECP(709843),            -- 4-Port 400GBase-QSFP-DD FlexE MACsec Flexible Card CM(P3T2-CM,400GE Port Enabled with 100GE by default)
              subbname8090DEVCR8D84KBFEEP(709844),            -- 4-Port 400GBase-QSFP-DD FlexE MACsec Flexible Card E CM(P3T2-E-CM,400GE Port Enabled with 100GE by default)
              subbname8090DEVCR8D84KBFELP(709845),            -- 4-Port 400GBase-QSFP-DD FlexE MACsec Flexible Card L CM(P3T2-L-CM,400GE Port Enabled with 100GE by default)
              subbname8090DEVCR8DEDNBFECP(709850),            -- 16-Port 100GBase-QSFP28 FlexE MACsec Flexible Card CM(P3T2-CM)
              subbname8090DEVCR8DEDNBFEEP(709851),            -- 16-Port 100GBase-QSFP28 FlexE MACsec Flexible Card E CM(P3T2-E-CM)
              subbname8090DEVCR8DEDNBFELP(709852),            -- 16-Port 100GBase-QSFP28 FlexE MACsec Flexible Card L CM(P3T2-L-CM)
              subbname8090DEVCR8D8DNBFECP(709853),            -- 16-Port 100GBase-QSFP28 FlexE MACsec Flexible Card CM(P3T2-CM)
              subbname8090DEVCR8D8DNBFEEP(709854),            -- 16-Port 100GBase-QSFP28 FlexE MACsec Flexible Card E CM(P3T2-E-CM)
              subbname8090DEVCR8D8DNBFELP(709855),            -- 16-Port 100GBase-QSFP28 FlexE MACsec Flexible Card L CM(P3T2-L-CM)
              subbname8090DEVCR8DEDNBFECR(709856),            -- 16-Port 100GBase-QSFP28 FlexE MACsec Flexible Card CM(P3T2-CM)
              subbname8090DEVCR8DE4KBFECR(709846),            -- 4-Port 400GBase-QSFP-DD FlexE MACsec Flexible Card CM(P3T2-CM,400GE Port Enabled with 100GE by default)
              subbname8090DEVCR8DEFNBFCC0(709831),            -- 24-Port 100GBase-QSFP28 FlexE MACsec Flexible Card CM(P6T4-CM)
              subbname8090DEVCR8DEFNBFCE0(709832),            -- 24-Port 100GBase-QSFP28 FlexE MACsec Flexible Card E CM(P6T4-E-CM)
              subbname8090DEVCR8DEFNBFCL0(709833),            -- 24-Port 100GBase-QSFP28 FlexE MACsec Flexible Card L CM(P6T4-L-CM)
              subbname8090DEVCR8D8EFNBFC0(709834),            -- 24-Port 100GBase-QSFP28 FlexE MACsec Flexible Card CM(P6T4-CM)
              subbname8090DEVCR8D8FNBFCE0(709835),            -- 24-Port 100GBase-QSFP28 FlexE MACsec Flexible Card E CM(P6T4-E-CM)
              subbname8090DEVCR8D8EFNBFL0(709836),            -- 24-Port 100GBase-QSFP28 FlexE MACsec Flexible Card L CM(P6T4-L-CM)
              subbname8090DEVCR8D000600C0(709837),            -- 6 Channes E&M Interface Board
              subbname8090DEVCR8DE1KE1NCP(709820),            -- 1-Port 400GBase-QSFP-DD FlexE + 1-Port 100GBase-QSFP28 Flexible Card CM(P1T-CM,400GE Port Enabled with 100GE by default)
              subbname8090DEVCR8DE1KE1NEP(709821),            -- 1-Port 400GBase-QSFP-DD FlexE + 1-Port 100GBase-QSFP28 Flexible Card E CM(P1T-E-CM,400GE Port Enabled with 100GE by default)
              subbname8090DEVCR8D8E1K1NCP(709822),            -- 1-Port 400GBase-QSFP-DD FlexE + 1-Port 100GBase-QSFP28 Flexible Card CM(P1T-CM,400GE Port Enabled with 100GE by default)
              subbname8090DEVCR8D8E1K1NEP(709823),            -- 1-Port 400GBase-QSFP-DD FlexE + 1-Port 100GBase-QSFP28 Flexible Card E CM(P1T-E-CM,400GE Port Enabled with 100GE by default)
              subbname8090DEVCR8D8E1K1NLP(709824),            -- 1-Port 400GBase-QSFP-DD FlexE + 1-Port 100GBase-QSFP28 Flexible Card L CM(P1T-L-CM,400GE Port Enabled with 100GE by default)
              subbname8090DEVCR8DE00E8KN0(709860),            -- 8-Port 400GBase-QSFP-DD FlexE MACsec Flexible Card CM(P6T4-CM,400GE Port Enabled with 100GE by default)
              subbname8090DEVCR8DE00E8KE0(709861),            -- 8-Port 400GBase-QSFP-DD FlexE MACsec Flexible Card E CM(P6T4-E-CM,400GE Port Enabled with 100GE by default)
              subbname8090DEVCR8DE00E8KL0(709862),            -- 8-Port 400GBase-QSFP-DD FlexE MACsec Flexible Card L CM(P6T4-L-CM,400GE Port Enabled with 100GE by default)
              subbname8090DEVCR8D800E8KC0(709863),            -- 8-Port 400GBase-QSFP-DD FlexE MACsec Flexible Card CM(P6T4-CM,400GE Port Enabled with 100GE by default)
              subbname8090DEVCR8D800E8KE0(709864),            -- 8-Port 400GBase-QSFP-DD FlexE MACsec Flexible Card E CM(P6T4-E-CM,400GE Port Enabled with 100GE by default)
              subbname8090DEVCR8D800E8KL0(709865),            -- 8-Port 400GBase-QSFP-DD FlexE MACsec Flexible Card L CM(P6T4-L-CM,400GE Port Enabled with 100GE by default)
              subbname8090DEVIG2DE4KEDND1(709780),            -- 4-Port 400GBase-QSFP-DD + 16-Port 100GBase-QSFP28 FlexE MACsec Flexible Card(P6T4)
              subbname8090DEVIG2D00SP8001(709781),            -- Service Processing Flexible Card(SP800)-with 8*10GE port
              subbname8090DEVCR8DVSSP8HE1(709787),            --Versatile Service Flexible Card E(SP800-E)
              subbname8090DEVCR8DVSSP8HS1(709783),            --Versatile Service Flexible Card(SP800-S)
              subbname8090DEVCR8DVSSP8HE2(709788),           --Versatile Service Flexible Card E(SP800A-E)
              subbname8090DEVCR8DVSSP8HS2(709784),           --Versatile Service Flexible Card(SP800A-S)
              subbname8090DEVCR8DMSSP8HE0(709789),           --Multi-Function Service Flexible Card E(MSP800-E)
              subbname8090DEVCR8DMSSP8HS0(709785),           --Multi-Function Service Flexible Card(MSP800-S)
              subbname8090DEVCR8DMSSP8HE1(709790),           --Multi-Function Service Flexible Card E(MSP800A-E)
              subbname8090DEVCR8DMSSP8HS1(709786),           --Multi-Function Service Flexible Card(MSP800A-S)
              subbname8090DEVCR8D8VSP8HE1(709792),           --Versatile Service Flexible Card E(SP800-E)
              subbname8090DEVCR8D8VSP8HS1(709778),           --Versatile Service Flexible Card(SP800-S)
              subbname8090DEVCR8D6VSP8HE1(709791),           --Versatile Service Flexible Card E(SP800-E)
              subbname8090DEVCR8D6VSP8HS1(709779),          --Versatile Service Flexible Card(SP800-S)
              subbname8090DEVIG2D00SP8002(709782),            -- Service Processing Enhanced Flexible Card(SP800E)-with 8*10GE port
              subbname8090DEVCR8DEFNBFCC1(709839),            -- 24-Port 100GBase-QSFP28 FlexE MACsec Flexible Card CM(P6T4-CM)
              subbname8090DEVCR8DE1KE1NCQ(709826),            -- 1-Port 400GBase-QSFP-DD FlexE + 1-Port 100GBase-QSFP28 Flexible Card CM(P1T-CM,400GE Port Enabled with 100GE by default)
              subbname8090DEVCR8DE1KE1NEQ(709827),            -- 1-Port 400GBase-QSFP-DD FlexE + 1-Port 100GBase-QSFP28 Flexible Card E CM(P1T-E-CM,400GE Port Enabled with 100GE by default)
              subbname8090DEVCR8DEDNBFECQ(709858),            -- 16-Port 100GBase-QSFP28 FlexE MACsec Flexible Card CM(P3T2-CM)
              subbname8090DEVCR8DEDNBFEEQ(709859),            -- 16-Port 100GBase-QSFP28 FlexE MACsec Flexible Card E CM(P3T2-E-CM)
              subbname8090DEVCR8DE4KBFECQ(709848),            -- 4-Port 400GBase-QSFP-DD FlexE MACsec Flexible Card CM(P3T2-CM,400GE Port Enabled with 100GE by default)
              subbname8090DEVCR8DE4KBFEEQ(709849),            -- 4-Port 400GBase-QSFP-DD FlexE MACsec Flexible Card E CM(P3T2-E-CM,400GE Port Enabled with 100GE by default)
              subbname8090DEVCR8DE00E8KN1(709805),            -- 8-Port 400GBase-QSFP-DD FlexE MACsec Flexible Card CM(P6T4-CM,400GE Port Enabled with 100GE by default)
              subbname8090DEVCR8DE00E8KE1(709806),            -- 8-Port 400GBase-QSFP-DD FlexE MACsec Flexible Card E CM(P6T4-E-CM,400GE Port Enabled with 100GE by default)
              subbname8090DEVNSRCPA1(548688),            -- 1-Port 100GBase/50GBase-QSFP28 FlexE MACsec+8-Port 10GE(SFP+)/GE(SFP) MACsec Physical Interface Card(PIC)
              subbname8090DEVNSRCPA1A(548689),            -- VIRTUALPIC_NSRCPA1A_CARD
              subbname8090DEVANND001EY800(709807),            -- 8 Channels 25G (SFP28) High Speed Interface Board
              subbname8090DEVANOD00E8XM2A(709808),            -- 8 Channels 25G (SFP28) High Speed Interface Board
              subbname8090DEVANNDE1NBFM02(709818),            -- 1-Port 100GBase/50GBase-QSFP28 FlexE MACsec+8-Port 10GE(SFP+)/GE(SFP) MACsec Physical Interface Card(PIC)
              subbname8090DEVCR8D6E1K1NCP(709887),            -- 1-Port 400GBase-QSFP-DD FlexE + 1-Port 100GBase-QSFP28 Flexible Card CM(P1T-CM,400GE Port Enabled with 100GE by default)
              subbname8090DEVCR8D6E1K1NEP(709888),            -- 1-Port 400GBase-QSFP-DD + 1-Port 100GBase-QSFP28 FlexE MACsec Flexible Card E CM(P1T-E-CM,400GE Port Enabled with 100GE by default)
              subbname8090DEVCR8D6LJXXCC0(709889),            -- 36-Port 10GBase LAN/WAN-SFP+ MACsec Flexible Card CM(P1T-CM)
              subbname8090DEVCR8D6LJXXCE0(709890),            -- 36-Port 10GBase LAN/WAN-SFP+ MACsec Flexible Card E CM(P1T-E-CM)
              subbname8090DEVCR8D6MUF00X1(709891),            -- 16-Port 10GE(SFP+)/GE(SFP) + 16-Port 155M/16-Port 622M/8-Port 2.5G/2-Port 10GPOS Flexible Card (P1T-CM)
              subbname8090DEVCR8D62KE2NC0(709892),            -- 2-Port 400GBase-QSFP-DD FlexE + 2-Port 100GBase-QSFP28 Flexible Card CM(P2T-CM)
              subbname8090DEVCR8D6E5NBCC0(709893),            -- 5-Port 100GBase-QSFP28 FlexE MACsec Flexible Card CM(P1T-CM)
              subbname8090DEVCR8D6E5NBCE0(709894),            -- 5-Port 100GBase-QSFP28 FlexE MACsec Flexible Card E CM(P1T-E-CM)
              subbname8090DEVCR8D6ANBFECQ(709895),            -- 10-Port 100GBase-QSFP28 FlexE MACsec Flexible Card CM(P2T-CM)
              subbname8090DEVCR8DEE5NBCL0(709900),            -- 5-Port 100GBase-QSFP28 FlexE MACsec Flexible Card L CM(P1T-L-CM)
              subbname8090DEVCR8DEE5NBCC0(709901),            -- 5-Port 100GBase-QSFP28 FlexE MACsec Flexible Card CM(P1T-CM)
              subbname8090DEVCR8DEE5NBCE0(709902),            -- 5-Port 100GBase-QSFP28 FlexE MACsec Flexible Card E CM(P1T-E-CM)
              subbname8090DEVCR8DELJXXCL0(709903),            -- 36-Port 10GBase LAN/WAN-SFP+ MACsec Flexible Card L CM(P1T-L-CM)
              subbname8090DEVCR8DELJXXCC0(709904),            -- 36-Port 10GBase LAN/WAN-SFP+ MACsec Flexible Card CM(P1T-CM)
              subbname8090DEVCR8DELJXXCE0(709905),            -- 36-Port 10GBase LAN/WAN-SFP+ MACsec Flexible Card E CM(P1T-E-CM)
              subbname8090DEVCR8DEE1K1NLP(709906),            -- 1-Port 400GBase-QSFP-DD FlexE + 1-Port 100GBase-QSFP28 Flexible Card L CM(P1T-L-CM,400GE Port Enabled with 100GE by default)
              subbname8090DEVCR8DEE1K1NCP(709907),            -- 1-Port 400GBase-QSFP-DD FlexE + 1-Port 100GBase-QSFP28 Flexible Card CM(P1T-CM,400GE Port Enabled with 100GE by default)
              subbname8090DEVCR8DEE1K1NEP(709908),            -- 1-Port 400GBase-QSFP-DD FlexE + 1-Port 100GBase-QSFP28 Flexible Card E CM(P1T-E-CM,400GE Port Enabled with 100GE by default)
              subbname8090DEVXHXDEBNBFEC0(709909),            -- 12-Port 100GBase-QSFP28 FlexE MACsec Flexible Card CM(P2T4-CM)
              subbname8090DEVXHXDE3KBFEC0(709910),            -- 3-Port 400GBase-QSFP-DD FlexE MACsec Flexible Card CM(P2T4-CM,400GE Port Enabled with 100GE by default)
              subbname8090DEVXHXDE6KBFEC3(709911),            -- 6-Port 400GBase-QSFP-DD FlexE MACsec Flexible Card CM(P4T8-CM,400GE Port Enabled with 100GE by default)
              subbname8090DEVGPR32CQ56YS(709912),             -- 32-Port 400GBase-QSFPDD + 56-Port 100GBase-QSFP28
              subbname8090DEVCR8DEANBFECQ(709913),            -- 10-Port 100GBase-QSFP28 FlexE Flexible Card CM(P2T-CM)
              subbname8090DEVCR8D8ANBFECQ(709914),            -- 10-Port 100GBase-QSFP28 FlexE MACsec Flexible Card CM(P2T-CM)
              subbname8090DEVCR8D8ANBFELQ(709915),            -- 10-Port 100GBase-QSFP28 FlexE MACsec Flexible Card L CM(P2T-L-CM)
              subbname8090DEVXHXDE3KBFEC1(709920),            -- 3-Port 400GBase-QSFP-DD FlexE MACsec Flexible Card CM(P2T4-CM,400GE Port Enabled with 100GE by default)
              subbname8090DEVXHXDEBNBFEC1(709921),            -- 12-Port 100GBase-QSFP28 FlexE MACsec Flexible Card CM(P2T4-CM)
              subbname8090DEVXHXDE6KBFEC1(709922),            -- 6-Port 400GBase-QSFP-DD FlexE MACsec Flexible Card CM(P4T8-CM,400GE Port Enabled with 100GE by default)
              subbname8090DEVXHXDEFNBFEC1(709923),            -- 24-Port 100GBase-QSFP28 FlexE MACsec Flexible Card CM(P4T8-CM)
              subbname8090DEVXHXDE3KBFEC2(709924),            -- 3-Port 400GBase-QSFP-DD FlexE MACsec Flexible Card CM(P2T4-CM,400GE Port Enabled with 100GE by default)
              subbname8090DEVXHXDEBNBFEC2(709925),            -- 12-Port 100GBase-QSFP28 FlexE MACsec Flexible Card CM(P2T4-CM)
              subbname8090DEVCR8DEANBFECT(709926),            -- 10-Port 100GBase-QSFP28 FlexE Flexible Card CM(P2T-L-CM)
              subbname8090DEVCR8D8EKE2NCQ(709927),            -- 2-Port 400GBase-QSFP-DD FlexE + 2-Port 100GBase-QSFP28 Flexible Card CM(P2T-L-CM)
              subbname8090DEVCR8DEANBFECS(709928),            -- 10-Port 100GBase-QSFP28 FlexE Flexible Card CM(P2T-CM)
              subbname8090DEVCR8D8EKE2NCP(709929),            -- 2-Port 400GBase-QSFP-DD FlexE + 2-Port 100GBase-QSFP28 Flexible Card CM(P2T-CM)
              subbname8090DEVCR8DVSSP8EE1(709940),            -- Versatile Service Flexible Card E(SP800-E)
              subbname8090DEVCR8DVSSP8EE0(709941),            -- Versatile Service Flexible Card E(SP800A-E)
              subbname8090DEVCR8DVSSP8ES1(709942),            -- Versatile Service Flexible Card(SP800-S)
              subbname8090DEVCR8DVSSP8ES0(709943),            -- Versatile Service Flexible Card(SP800A-S)
              subbname8090DEVCR8DMSSP8EE0(709944),            -- Multi-Function Service Flexible Card E(MSP800-E)
              subbname8090DEVCR8DMSSP8EE1(709945),            -- Multi-Function Service Flexible Card E(MSP800A-E)
              subbname8090DEVCR8DMSSP8ES0(709946),            -- Multi-Function Service Flexible Card(MSP800-S)
              subbname8090DEVCR8DMSSP8ES1(709947),            -- Multi-Function Service Flexible Card(MSP800A-S)
              subbname8090DEVCR8D00P8CFC2(226891),            -- 8-Port STM-1c/8-Port STM-4c POS Card (PIC)(Default Enable 4*STM-1c)
              subbname8090DEVCR8D00P8CFC3(226892),            -- 8-Port STM-1c/8-Port STM-4c POS Card (PIC)(Default Enable 4*STM-1c)
              subbname8090DEVCR8D00P8CFD3(226893),            -- 8-Port STM-1c/8-Port STM-4c POS Card (PIC)(Default Enable 4*STM-1c)
              subbname8090DEVCR8D00P8CFD2(226894),            -- 8-Port STM-1c/8-Port STM-4c POS Card (PIC)(Default Enable 4*STM-1c)
              subbname8090DEVXHXD0LJXXCCP(364092),            -- 36-Port 10GBase LAN/WAN-SFP+ MACsec Flexible Card CM(P1T-CM)
              subbname8090DEVCR8S16APTHE1(364093),            -- Threat Prortection Flexible Card S(TPP800A-S)
              subbname8090DEVCR8S16APTHE2(364094),            -- Threat Prortection Flexible Card S(TPP800A-S)
              subbname8090DEVCR8D000SA891(364095),            -- 8-Channel X.21/V.24 Board
              subbname8090DEVCR8D000SA890(364096),            -- 8-Channel X.21/V.24 Board
            

-- ME60:
                fnameME60Unknown(159744),           -- Quidway unknown FRAME,
                fnameME60Whole(159745),            -- Quidway ME60-16 FRAME,
                fnameME60Half(159746),             -- Quidway ME60-8 FRAME,
                fnameME60HalfLow(159747),               -- Quidway ME60-8 FRAME,
                fnameME60WholeBKPC(159748),             -- Quidway ME60-16 FRAME
                fnameME60Quarter(159749),                -- Quidway ME60-4 FRAME
                fnameME60X3DC(159750),              -- Quidway ME60-X3 FRAME
                fnameME60X3AC(159751),              -- Quidway ME60-X3 FRAME
                fnameME60X8(159752),                -- Quidway ME60-X8  FRAME
                fnameME60X16(159753),               -- Quidway ME60-X16 FRAME
                fnameME60X8A-AC(159754),                --ME60-X8A Integrated Chassis AC Components
                fnameME60X8A-DC(159755),             --ME60-X8A Integrated Chassis DC Components
                fnameME60X16A-AC(159756),                -- ME60-X16A Integrated AC Chassis Components
                fnameME60X16A-DC(159757),              --ME60-X16A Integrated DC Chassis Components
                fnameME60-X3A(159758),              -- Quidway ME60-X3A FRAME
                fnameME60S4(159759),                -- Quidway ME60S-X1-S4 FRAME
                fnameME60S4-DC(159760),             -- Quidway ME60S-X1-S4-DC FRAME
                fnameME60S8(159761),                -- Quidway ME60S-X2-S8 FRAME
                fnameME60S8-DC(159762),             -- Quidway ME60S-X2-S8-DC FRAME
                fnameME60S16(159763),               -- Quidway ME60S-X2-S16 FRAME
                fnameME60X1M4(159764),              -- Quidway ME60M-X1-M4 FRAME
                fnameME60X1M4-DC(159765),           -- Quidway ME60M-X1-M4-DC FRAME
                fnameME60X2-M8(159766),             -- Quidway ME60M-X2-M8 FRAME
                fnameME60X2-M8-DC(159767),          -- Quidway ME60M-X2-M8-DC FRAME
                fnameME60X2-M16(159768),            -- Quidway ME60M-X2-M16 FRAME
                fnameME60X2-M8A(161583),            -- Quidway ME60M-X2-M8A FRAME
                fnameME60X2-M8A-DC(161584),         -- Quidway ME60M-X2-M8A-DC FRAME
                fnameME60X2-M16A(161585),           -- Quidway ME60M-X2-M16A FRAME
        fnameME60S8A(161586),               -- Quidway ME60S-X2-S8A FRAME
                fnameME60S8A-DC(161587),            -- Quidway ME60S-X2-S8A-DC FRAME
                fnameME60S16A(161588),              -- Quidway ME60S-X2-S16A FRAME

-- S9300:       0x000A1000~0x000A1fff(659456~663551)
                fnameLE0KS9303(659456),                -- Quidway S9303 FRAME
                fnameLE0KS9306(659457),                -- Quidway S9306 FRAME
                fnameLE0KS9312(659458),                -- Quidway S9312 FRAME
                fnameLE0110(659459),                -- Quidway S9310 FRAME
                fnameLE0203Poe(659460),             -- Quidway S9303 POE FRAME
                fnameLE0BS9306P1(659461),             -- Quidway S9306 POE FRAME
                fnameLE02WMMPA(659462),
                fnameLE0BS9312P1(659463),             -- Quidway S9312 POE FRAME
                fnameLE02Spu(659464),               -- Quidway S9300 SPU FRAME
                fnameLE2BS9303E00(659465),               -- Quidway S9303E FRAME
                fnameLE2BS9306E00(659466),               -- Quidway S9306E FRAME
                fnameLE2BS9312E00(659467),               -- Quidway S9312E FRAME
                fnameLE2BS9303E01(659468),               -- Quidway S9303E_01 FRAME
                fnameLE2BS9306E01(659469),               -- Quidway S9306E_01 FRAME
                fnameLE2BS9312E01(659470),               -- Quidway S9312E_01 FRAME
                fnameLX1BS9303S00(659471),               -- Quidway S9303X FRAME
                fnameLX1BS9306S00(659472),               -- Quidway S9306X FRAME
                fnameLX1BS9312S00(659473),               -- Quidway S9312X FRAME
                fnameLX1BS9310S00(659474),               -- Quidway S9310X FRAME
                fnameLE0KS9310(659475),                      -- Quidway S9310  FRAME
                fnameLE1BS9316S00(659476),               -- Quidway S9316  FRAME
                fnameLE3BSS9308X0(659477),               --S9300X-8 assembly chassis
                fnameLE3BSS9312X0(659478),              --S9300X-12 assembly chassis
                fnameLE3BSS9304X0(659479),              --S9300X-4 assembly chassis
                fnameLE3BSS9312X1(659480),              --S9300X-12 assembly chassis
                fnameLE1BS9312XS00(659481),             --S9300XS-12 assembly chassis
                fnameLE5BS9304XE0(659482),              --S9300XE-4 assembly chassis
                fnameLE5BS9308XE0(659483),              --S9300XE-8 assembly chassis



--V8R9C10   X1X2
               subbname8090DEVCR5D3DMR4M01(561724),      -- 4-Channel CWDM Optical Add/Drop Multiplexing (1471/1491/1511/1531nm) Physical Interface Card(PIC)
               subbname8090DEVCR5D3DMR4M02(561725),      -- 4-Channel CWDM Optical Add/Drop Multiplexing (1551/1571/1591/1611nm) Physical Interface Card(PIC)
               subbname8090DEVCR5D00EEGF71(561635), -- 20-Port 100/1000Base-X-CSFP Physical Interface Card(PIC)
               subbname8090DEVCR2D00EEGF11(561636), -- 20-Port 100/1000Base-X-CSFP Physical Interface Card(PIC)
               subbname8090DEVCX6D00EEGF10(561637), -- 20-Port 100/1000Base-X-CSFP Physical Interface Card(PIC)

--V8R9C10   X3X8X16
               subbname8090DEVCR5D00E1NC77(561713),      -- 1-Port 100GBase-CFP2 Flexible Card A(P120-A)
               subbname8090DEVCR5D00E1NC7A(561714),      -- 1-Port 100GBase-CFP2 Flexible CardA(P240-A)
               subbname8090DEVME0D0E1NCB70(561715),      -- 1-Port 100GBase-CFP2 Flexible Card(BP100)
               subbname8090DEVME0D0E1NCB71(561729),      -- 1-Port 100GBase-CFP2 Flexible Card(BP240)
               subbname8090DEVCR57E1NCF2(561717),      -- 1-Port 100GBase-CFP2 Fixed Card
               subbname8090DEVCX6D0E1NCA11(561718),      -- 1-Port 100GBase-CFP2 Flexible Card A(S102-A)
               subbname8090DEVCR5CR5D00E1ND70(561719),   -- 1-Port 100GBase-QSFP28 Flexible Card A(P120-A)
               subbname8090DEVCR5CR5D00E1ND73(561720),   -- 1-Port 100GBase-QSFP28 Flexible Card A(P240-A)
               subbname8090DEVCR5ME0D0E1NDB70(561721),   -- 1-Port 100GBase-QSFP28 Flexible Card(BP100)
               subbname8090DEVCR5ME0D0E1NDB71(561722),   -- 1-Port 100GBase-QSFP28 Flexible Card(BP240)
               subbname8090DEVCR5CX6D0E1NDA10(561723),   -- 1-Port 100GBase-QSFP28 Flexible Card A(S102-A)
               subbname8090DEVCR5D00E2NF70(561727),      -- 2-Port 100GBase-QSFP28 Flexible Card A(P480-A)
               subbname8090DEVCR5D00MD8A70(561726),      -- 8-Channel CWDM Multiplexing & Demultiplexing (1471/1491/1511/1531/1551/1571/1591/1611nm) Flexible Card(P50)

--V8R9C10 NE5000
               subbname8090DEVCR5D00N6GF60(561625),   -- 6-Port 10G OTN/ETH-SFP+ Flexible Card(CP400,Occupy 1 sub-slot)
               subbname8090DEVCR5D00NBGF60(561626),   -- 12-Port 10G OTN/ETH-SFP+ Flexible Card(CP400,Occupy 1 sub-slot)
               subbname8090DEVCR5D00E2NB60(561728),     -- 2-Port 100GBase-QSFP28 Flexible Card(CP400,Occupy 1 sub-slot)



-- S7700:       0x000A2000~0x000A2fff(663552~667647)
                fnameES0B00770300(663552),                -- Quidway S7703 FRAME
                fnameES0B00770600(663553),                -- Quidway S7706 FRAME
                fnameES0B00771200(663554),                -- Quidway S7712 FRAME
                fnameES0203Poe(663555),             -- Quidway S7703 POE FRAME
                fnameES0B017706P0(663556),             -- Quidway S7706 POE FRAME
                fnameES0B017712P0(663557),             -- Quidway S7712 POE FRAME
                fnameES02Spu(663558),               -- Quidway S7700 SPU FRAME
                fnameES1B00770301(663559),          -- Quidway S7703 FRAME FCC
                fnameES1B00770601(663560),          -- Quidway S7706 FRAME FCC
                fnameES1B00771201(663561),          -- Quidway S7712 FRAME FCC
                fnameES1B017706P1(663562),          -- Quidway S7706 POE FRAME FCC
                fnameES1B017712P1(663563),          -- Quidway S7712 POE FRAME FCC
                fnameES02BAKG7712(663564),          -- Quidway S7712 FRAME FCC
                fnameES02BAKR7712POE(663565),       -- Quidway S7712 POE FRAME FCC
                fnameES1BS7710S00(663566),          -- Quidway S7710 FRAME
                fnameES1BS7706SP1(663567),          -- Quidway S7706 POE FRAME FCC delete by v2r13
                fnameES1BS7703SP0(663568),          -- Quidway S7703 POE FRAME delete by v2r13
                fnameES1BS7703EP0(663569),          -- Quidway S7703 POE FRAME FCC delete by v2r13
                fnameES1BS7706SP0(663570),          -- S7706 PoE Assembly Chassis add for v2r13
                fnameS7706S(663571),                -- S7706S Assembly Chassis add for v2r23c00
		fnameS7703S(663572),                -- S7703S Assembly Chassis add for v2r23c00

-- S9700:       0x000A7000~0x000A7fff(684032~688127)
                fnameEH1BS9703E00(684032),                -- Quidway S9703 FRAME
                fnameEH1BS9706E00(684033),                -- Quidway S9706 FRAME
                fnameEH1BS9712E00(684034),                -- Quidway S9712 FRAME
                fnameEH02Spu(684035),                     -- Quidway S9700 SPU FRAME

-- S12700:      0x000AB000~0x000ABfff(700416~704511)
                fnameET1D2S1270800(700416),              -- HUAWEI S12708 FRAME
                fnameET1D2S1271200(700417),              -- HUAWEI S12712 FRAME
                fnameET1D2BAKQS12704(700418),            -- HUAWEI S12704 FRAME
                fnameET1BS12710S0(700419),               -- HUAWEI S12710 FRAME
                fnameET1BS12708S0(700420),               -- HUAWEI S12708 FRAME Speed-up
                fnameET1BS12712S0(700421),               -- HUAWEI S12712 FRAME Speed-up
                fnameET1BS12703S0(700422),               -- HUAWEI S12703 FRAME
                fnameET1BS12704E0(700423),               -- HUAWEI S12704 FRAME Speed-up for V2R19C00
                fnameET1BS12708E0(700424),               -- HUAWEI S12708 FRAME Speed-up for V2R19C00
                fnameET1BS12712E0(700425),               -- HUAWEI S12712 FRAME Speed-up for V2R19C00
                fnameET1BS12712E1(700426),               --S12700E-12 assembly chassis for V2R19C00
                fnameET1BS12704EZ0(700427),				 -- S12700E-4-Z Assembly Chassis for V2R22C10
                fnameET1BS12708EZ0(700428),				 -- S12700E-8-Z Assembly Chassis for V2R22C10   
                fnameLSS12704SP0(700429),                -- S12700H-4,S12700H-4 assembly chassis
                fnameLSS12708SP0(700430),                -- S12700H-8,S12700H-8 assembly chassis

-- S7900:       0x000AE000~0x000AEfff(712704~716799)
                fnameEF1BS7905S00(712704),              -- HUAWEI S7905 FRAME
                fnameEF1BS7908S00(712705),              -- HUAWEI S7908 FRAME
                                                                               
-- S8700:       0x00AE300~0x000AE3ff(713472~713727)              
                fnameES1BS8706SP0(713472),              -- HUAWEI S8706 FRAME
                fnameES1BS8710SP0(713473),              -- HUAWEI S8710 FRAME
                fnameLSS8704SP0(713474),                -- HUAWEI S8704 FRAME   
                fnameLSS8704SP1(713475),                -- HUAWEI S8704S FRAME
-- S16700:      0x00AE400~0x000AE4ff(713728~713983)
                fnameEX1BS16704SA0(713728),              -- HUAWEI S16704 FRAME
                fnameEX1BS16704SD0(713729),              -- HUAWEI S16704 FRAME
                fnameEX1BS16708SA0(713730),              -- HUAWEI S16708 FRAME
                fnameEX1BS16708SD0(713731),              -- HUAWEI S16708 FRAME

-- lanSwChassis: 0x00AE500~0x000AE5ff(713984~714239)
                fnameS750(713984),                      -- S750 assembly chassis

-- NSE:
                fnameNSEUnknown(570152),            -- Quidway unknown FRAME,
                fnameSSPHalf(570154),                       -- Quidway SSP1000 FRAME
                fnameSSPWhole(570155),                   -- Quidway SSP2000 FRAME
                fnameSSPNE5000E(570156),             -- Quidway SSP3000 FRAME
                fnameNSEQuarter(570157),                -- Quidway NSE1000-4 FRAME
                fnameNSEHalf(570158),                    -- Quidway NSE1000-8 FRAME
                fnameSSP5000X8(696322),              -- Quidway SSP5000X8 FRAME
                fnameSSP5000X16(696321),             -- Quidway SSP5000X16 FRAME

-- ATN:
                fnameATNUnknown(225280),           -- ATN unknown FRAME,
                fnameATNDEV980(225281),            -- ATN 980 FRAME,
                fnameATNDEV990(225282),            -- ATN 990 FRAME,
                fnameATNDEV905-F-AC(225600),      --ATN905-F-AC chassis
                fnameATNDEV905-F-DC(225602),      --ATN905-F-DC chassis
                fnameATNDEV905-G-AC(225660),      --ATN905-G-AC chassis

--ATN 910&950,950B
--chassis
               fnameATNDEV910(225283),          --ATN910 chassis
               fnameATNDEV950(225284),           --ATN950 chassis
               fnameATNDEV950B(225285),          --ATN950B chassis
               fnameATNDEV910IA(225483),          --910I AC chassis
               fnameATNDEV910IB(225494),          --910I DC chassis
               fnameATNDEV910IC(225495),          --910I-C AC chassis
               fnameATNDEV910ID(225496),          --910I-TC DC chassis
               fnameATNDEV910IE(225515),          --910I-AC poe chassis
               fnameATNDEV905A(225508),           --905-AC indoor chassis
               fnameATNDEV905B(225509),           --905-AC outdoor chassis
               fnameATNDEV905C(225510),           --905-AC outdoor poe chassis
               fnameATNDEV905AV(225528),           --905A-V AC outdoor chassis
               fnameATNDEV910B(225529),            --910B chassis
               fnameATNDEV910IF(225533),           --910I-D AC chassis
               fnameATNDEV910IG(225534),           --910I-D DC chassis
               fnameATNDEV910IH(225535),           --910I-B DC chassis
               fnameATNDEV910II(225543),           --910I-E DC chassis
               fnameATNDEV905V (225544),           -- 905-V AC chassis
               fnameATNDEV905DC(225545),           -- 905-DC chassis
               fnameATNDEV910B-E(225546),         --910B-E chassis
               fnameATNDEV910B-DDC(225547),         --910B-D DC chassis
               fnameATNDEV910B-DAC(225548),         --910B-D AC chassis
               fnameATNDEV905-EAC(225549),            --905-E chassis
               fnameATNDEV905A-CDC(225550),         --905A-C chassis
               fnameATNDEV905A-DDC(225551),         --905A-D chassis
               fnameATNDEV980B-DC(225552),            --980B DC chassis
               fnameATNDEV980B-AC(225553),            --980B AC chassis
               fnameATNDEV910B-FDC(225554),         --910B-F DC chassis
               fnameATNDEV910B-FAC(225555),         --910B-F AC chassis
               fnameATNDEV910C-A(225556),           --910C-A chassis
               fnameATNDEV910C-B(225557),           --910C-B chassis
               fnameATNDEV950C(225558),             --950C chassis
               fnameATNDEV910C-D(225559),          --910C-D  chassis
               fnameATNDEV910C-F(225607),          --910C-F  chassis
               fnameATNDEV910C-E(225608),          --910C-E  chassis
               fnameATNDEV910C-DAC(225609),          --910C-D AC  chassis
               fnameATNDEV910C-H(225610),          --910C-H  chassis
               fnameATNDEV910C-S(225611),          --910C-S  chassis
               fnameATNDEV980C(225612),            --980C  chassis
               fnameATNDEV910C-G-DC(225613),       --910C-G-DC  chassis
               fnameATNDEV980C-AC(225614),         --980C  chassis
               fnameATNDEV980C-DC(225615),         --980C  chassis
               fnameATNDEV910C-G-AC(225616),       --910C-G-AC  chassis
               fnameATNDEV950D(225617),            --ATN950D chassis
               fnameATNDEV910D(225618),            --ATN910D chassis
               fnameATNDEV950D-AC(225619),            --ATN950D-AC chassis
               fnameATNDEV950D-DC(225620),            --ATN950D-DC chassis
               fnameATNDEV910D-A-AC(225621),             -- ATN910D-A-AC chassis
               fnameATNDEV910D-A-DC(225639),             -- ATN910D-A-DC chassis
               fnameATNDEV910D-A(225641),             -- ATN910D-A chassis
               fnameATNDEV-950C(226100),             -- ATN-950C chassis
               fnameATNDEV-950C-AC(226101),             -- ATN-950C-AC chassis
               fnameATNDEV-950C-DC(226102),             -- ATN-950C-DC chassis
               fnameATNDEV910C-KDC(226110),        --ATN910-C-K DC chassis
               fnameATNDEV910C-KAC(226111),        --ATN910-C-K AC chassis
               fnameATNDEV910C-MDC(226112),        --ATN910-C-M DC chassis
               fnameATNDEV910C-MAC(226113),        --ATN910-C-M AC chassis
               fnameATNDEV910C-K(226116),             --ATN910-C-K chassis
               fnameATNDEV910C-M(226117),             --ATN910-C-M chassis
               fnameATNDEV980D(229798),            --ATN980D chassis
               fnameATNDEV980D-DC(229799),         --ATN980D-DC chassis
               fnameATNDEV980D-AC(229800),         --ATN980D-AC chassis
               fnameATNDEV980C-PL-DC(229801),         --ATN980C-PL-DC chassis
               fnameATNDEV980C-PL-AC(229802),         --ATN980C-PL-AC chassis
               fnameATNDEV910C-H-AC(225622),          --910C-H-AC chassis
               fnameATNDEV910C-S-AC(225623),          --910C-S-AC chassis
               fnameATNDEV980E-AC(229813),         --980E  chassis
               fnameATNDEV980E-DC(229814),         --980E  chassis

--etn: 0x000ad000~0x000adfff(708608~712703)
--chassis
            fnameETN500-A(708608),              --ETN500-A chassis
            fnameETN550-A(708609),              --ETN550-A chassis
            fnameETN500-F(708624),              --ETN500-F chassis

--NE0508E :  range     0x000AC000~0x000Acfff (704512 ~ 708607)
--chassis
            fnameNE08E-S6(704512),            -- NE08E-S6 chassis
            fnameNE05E-S2(704513),            -- NE05E-S2 chassis
            fnameNE05E-SE(704514),            -- NE05E-SE chassis
            fnameNE05E-SF(704515),            -- NE05E-SF chassis
            fnameNE05E-SG(704516),            -- NE05E-SG chassis
            fnameNE05E-SH(704517),            -- NE05E-SH chassis
            fnameNE05E-SI(704518),            -- NE05E-SI chassis
            fnameNE05E-SJ(704519),            -- NE05E-SJ chassis
            fnameNE05E-SK(704520),            -- NE05E-SK chassis
            fnameNE05E-SL(704521),            -- NE05E-SL chassis
            fnameNE05E-SM(704522),            -- NE05E-SM chassis
            fnameNE05E-SQ(704524),            -- NE05E-SQ chassis
            fnameNE05E-SR(704571),            -- NE05E-SR chassis
            fnameNE08E-S6E(704525),           -- NE08E-S6E chassis
            fnameNE08E-S9(704573),            -- NE08E-S9 chassis
            fname8090NE20E-S4-AC(676110),            -- NE20E-S4-AC chassis
            fname8090NE20E-S4-DC(676111),            -- NE20E-S4-DC chassis
            fname8090PTN6900-1-M4-AC(676112),        -- PTN6900-1-M4-AC chassis
            fname8090PTN6900-1-M4-DC(676113),        -- PTN6900-1-M4-DC chassis
            fnameNE08E-S9-DC(704578),                -- NE08E-S9-DC chassis
            fnameNE08E-S9-AC(704579),                -- NE08E-S9-AC chassis
-- PTN:
               fnamePTNUnknown(229376),                  --Unknown chassis type
               fnamePTN6900Half(229377),                 --PTN6900-8 chassis
               fnamePTN6900Whole(229378),                 --PTN6900-16 chassis
               -- for VDF
               fnamePTN6900TNRZ1BKPE(229379),      --Integrated DC Chassis Components (PTN 6900-3)
               fnamePTN6900TNRK003BKP01(229380),   --Integrated AC Chassis Components (PTN 6900-3)
               fnamePTN6900TNRB0BKP0270(229381),   --PTN 6900-2 Integrated Chassis Components
               fnamePTN6900TNRB0BKP0170(229382),   --PTN 6900-1 Integrated Chassis Components
           --for V8 CX600 packaging
           fnamePTN6900TNRB0BKP0171(229383),   --PTN 6900-1-M4 Integrated Chassis Components
           fnamePTN6900TNRB0BKP0271(229384),   --PTN 6900-2-M8 Integrated DC Chassis Components
           fnamePTN6900TNRB0BKP0273(229385),   --PTN 6900-2-M8 Integrated AC Chassis Components
           fnamePTN6900TNRB0BKP0272(229386),   --PTN 6900-2-M16 Integrated Chassis Components
           fnamePTN6900-M2E(229389),            --PTN 6900-M2E Integrated Chassis Components
           fnamePTN6900-M2F(229390),            --PTN 6900-M2F Integrated Chassis Components

           --for PTN7900 V100R006C00 2013-8-8 by lishaobin begin
               fnamePTN7900TPA1AFBTBKP00A(229387),   --PTN 7900-32 Integrated Chassis Components
               fnamePTN7900TPB1AFBTBKP00A(229388),   --PTN 7900-24 Integrated Chassis Components
           --for PTN7900 V100R006C00 2013-8-8 by lishaobin end
               fnamePTN6900-8A-AC(229391),            --PTN 6900-8A Integrated Chassis AC Components
               fnamePTN6900-8A-DC(229392),         --PTN 6900-8A Integrated Chassis DC Components
               fnamePTN6900-16A-AC(229393),            --PTN 6900-16A Integrated AC Chassis Components
               fnamePTN6900-16A-DC(229394),         --PTN 6900-16A Integrated DC Chassis Components
               fnamePTN6900-3A(229395),             --Integrated Chassis Components (PTN 6900-3A)
               fnamePTN7900TPC1AFBTBKP00A(229396),   --PTN 7900-12 Integrated Chassis Components
               fnamePTN990(229397),                  --PTN 990 Integrated DC Chassis Components
               fnamePTN6900-M8A(229398),      --PTN 6900-2-M8A Integrated DC Chassis Components
               fnamePTN6900-M8A-DC(229399),   --PTN 6900-2-M8A Integrated AC Chassis Components
               fnamePTN6900-M16A(229400),     --PTN 6900-2-M16A Integrated Chassis Components
               fnamePTN990-AC(229401),        --PTN 990 Integrated AC Chassis Components
               fnamePTN980(226364),                         -- PTN980 chassis
               fnamePTN970C(226363),                       -- PTN970C chassis
               fnamePTN916-F(226362),                      -- PTN916-F chassis
               fnamePTN916-F-AC(226366),                   -- PTN916-F-AC chassis
               fnamePTN916-F-DC(226367),                   -- PTN916-F-DC chassis
               fnamePTN970(229402),                         --PTN 970 Integrated DC Chassis Components
               fnamePTN930(229403),                         --PTN930  chassis
               fnamePTN905G(229404),                      --PTN905G  chassis
               fnamePTN905E(229405),                       --PTN905E  chassis
               fnamePTN905D(229406),                       --PTN905D  chassis
               fnamePTN905F(229407),                       --PTN905F  chassis
               fnamePTN7900TPD1CHASSIS(229408),   --PTN 7900E-32 Integrated Chassis Components
			   fnamePTN7900TPH1CHASSIS(229700),   --PTN 7900F-32 Integrated Chassis Components
               fnamePTN960E(229409),                       --PTN960E chassis
               fnamePTN990E(229411),                       --PTN990E chassis
               fnamePTN980B(226369),                              -- PTN980B chassis
               fnamePTN990B(226370),                              -- PTN990B chassis
               fnameSPN985-DC(226708),                              -- SPN985-DC chassis
               fnameSPN985-AC(226710),                              -- SPN985-AC chassis

--HVDC fram:
                fname8090NE40E-X16A-HVDC(561181),        --Quidway NE40E-X16A FRAME,HVDC
                fname8090NE40E-X8A-HVDC(561182),        --Quidway NE40E-X8A FRAME,HVDC
                fnameME60-X16A-HVDC(159769),        --Quidway ME60-X16A FRAME,HVDC
                fnameME60-X8A-HVDC(159770),        --Quidway ME60-X8A FRAME,HVDC
                fname8090CX600-X16A-HVDC(561183),        --Quidway CX600-X16A FRAME,HVDC
                fname8090CX600-X8A-HVDC(561184),        --Quidway CX600-X8A FRAME,HVDC
                fnamePTN6900-16A-HVDC(561185),        --Quidway PTN6900-16A FRAME,HVDC
                fnamePTN6900-8A-HVDC(561186),        --Quidway PTN6900-8A FRAME,HVDC
                fname8090CX600-X16A-DO-HVDC(561187),        --Quidway CX600-X16A-DO FRAME,HVDC
                fname8090CX600-X8A-DO-HVDC(561188),        --Quidway CX600-X8A-DO FRAME,HVDC
                fname8090NE40E-X16A(561641),        --Quidway NE40E-X16A FRAME
                fname8090NE40E-X8A(561642),        --Quidway NE40E-X8A FRAME
                fnameME60-X16A(561643),        --Quidway ME60-X16A FRAME
                fnameME60-X8A(561644),        --Quidway ME60-X8A FRAME
                fname8090CX600-X16A(561645),        --Quidway CX600-X16A FRAME
                fname8090CX600-X8A(561646),        --Quidway CX600-X8A FRAME
                fnamePTN6900-16A(561647),        --Quidway PTN6900-16A FRAME
                fnamePTN6900-8A(561648),        --Quidway PTN6900-8A FRAME
                fname8090CX600-X16A-DO(561649),        --Quidway CX600-X16A-DO FRAME
                fname8090CX600-X8A-DO(561650),        --Quidway CX600-X8A-DO FRAME
                fname8090NE40E-X16C-HVDC(562102),        --Quidway NE40E-X16C FRAME,HVDC
                fname8090NE40E-X8C-HVDC(562104),        --Quidway NE40E-X8C FRAME,HVDC


-- AR:          0x000A3000~0x000A3fff(667648~671743)
                fnameAR1220(667648),           -- Quidway AR1220 FRAME
                fnameAR1220W(667649),          -- Quidway AR1220W FRAME
                fnameAR1240(667650),           -- Quidway AR1240 FRAME
                fnameAR1240W(667651),          -- Quidway AR1240W FRAME
                fnameAR2220(667652),           -- Quidway AR2220 150W AC Power FRAME
                fnameAR2240(667653),           -- Quidway AR2240 350W AC Power,Router Unit 40 FRAME
                fnameAR3260(667654),           -- Quidway AR3260 350W AC Power,Router Unit 80 FRAME
                fnameAR1220V(667655),          -- Quidway AR1220V POE FRAME
                fnameAR201(667656),            -- Quidway AR201 FRAME
                fnameAR206(667657),            -- Quidway AR206 FRAME
                fnameAR207(667658),            -- Quidway AR207 FRAME
                fnameAR207V(667659),           -- Quidway AR207V FRAME
                fnameAR208(667660),            -- Quidway AR208 FRAME
                fnameAR1220VW(667661),         -- Quidway AR1220VW FRAME
                fnameAR1220S(667662),          -- Quidway AR1220S FRAME
                fnameAR1220WS(667663),         -- Quidway AR1220WS FRAME
                fnameAR207VP(667671),          -- Quidway AR207VP FRAME
                fnameAR201S(667672),           -- Quidway AR201S FRAME
                fnameAR207S(667673),           -- Quidway AR207S FRAME
                fnameAR151(667674),            -- Quidway AR151 FRAME
                fnameAR157(667675),            -- Quidway AR157 FRAME
                fnameAR2220S(667676),          -- Quidway AR2220S FRAME
                fnameAR1220L(667677),          -- Quidway AR1220L FRAME
                fnameAR207GHSPA(667678),       -- Quidway AR207G-HSPA+7 FRAME
                fnameSRG1320V(667679),         -- Quidway SRG1320V FRAME
                fnameSRG1320VW(667680),        -- Quidway RG1320VW FRAME
                fnameSRG2320(667681),          -- Quidway SRG2320 FRAME
                fnameSRG3340(667682),          -- Quidway SRG3340 FRAME
                fnameSRG3360(667683),          -- Quidway SRG3360 FRAME
                fnameAR156(667684),            -- Quidway AR156 FRAME
                fnameAR158E(667685),           -- Quidway AR158E FRAME
                fnameAR151GHSPA(667686),       -- Quidway AR151G-HSPA+7 FRAME
                fnameAR157GHSPA(667687),       -- Quidway AR157G-HSPA+7 FRAME
                fnameAR151WP(667688),          -- Quidway AR151W-P FRAME
                fnameAR157W(667689),           -- Quidway AR157W FRAME
                fnameAR1220D(667690),          -- Quidway AR158EGVW-HSPA+7-P FRAME
                fnameAR157VW(667691),          -- Quidway AR157VW FRAME
                fnameAR158EVW(667692),         -- Quidway AR158EVW FRAME
                fnameAR220148FE(667693),       -- Quidway AR2201-48FE FRAME
                fnameAR220248FE(667694),       -- Quidway AR2202-48FE FRAME
                fnameAR2220L(667695),          -- Quidway AR2220L FRAME
                fnameAR201VWP(667696),         -- Quidway AR201VWP FRAME
                fnameAR207VW(667697),         -- Quidway AR207VW FRAME
                fnameAR2230(667698),         -- Quidway AR2230 FRAME
                fnameAR2220D(667699),         -- Quidway AR2220D FRAME
                fnameAR2204(667700),         -- Quidway AR2204 FRAME
                fnameUSR206(667701),         -- Quidway USR20-6 FRAME
                fnameUSR208(667702),         -- Quidway USR20-8 FRAME
                fnameSRG303W(667703),         -- Quidway SRG303W FRAME
                fnameSRG303VW(667704),         -- Quidway SRG303VW FRAME
                fnameSRG2320D(667705),         -- Quidway SRG2320D FRAME
                fnameSRG2304(667706),         -- Quidway SRG2304 FRAME
                fnameSRG2330(667707),         -- Quidway SRG2330 FRAME
                fnameSRG1320(667708),         -- Quidway SRG1320 FRAME
                fnameSRG1320W(667709),         -- Quidway SRG1320W FRAME
                fnameAR151GEVDO(667710),       -- Quidway AR151G-EVDO FRAME
                fnameAR156I(667711),           -- Quidway AR156I FRAME
                fnameAR156IW(667712),          -- Quidway AR156IW FRAME
                fnameAR157I(667713),           -- Quidway AR157I FRAME
                fnameAR157IW(667714),          -- Quidway AR157IW FRAME
                fnameAR168F(667715),           -- Quidway AR168F FRAME
                fnameAR168FW(667716),          -- Quidway AR168FW FRAME
                fnameAR169F(667717),           -- Quidway AR169F FRAME
                fnameAR169W(667718),           -- Quidway AR169W FRAME
                fnameAR169FW(667719),          -- Quidway AR169FW FRAME
                fnameAR169BF(667720),          -- Quidway AR169BF FRAME
                fnameAR169BFW(667721),         -- Quidway AR169BFW FRAME
                fnameAR1220F(667722),          -- Quidway AR1220F FRAME
                fnameAR1220FW(667723),         -- Quidway AR1220FW FRAME
                fnameAR151S(667724),           -- Quidway AR151-S FRAME
                fnameAR151WPS(667725),         -- Quidway AR151W-P-S FRAME
                fnameAR151GUS(667726),         -- Quidway AR151G-U-S FRAME
                fnameAR1220LS(667727),         -- Quidway AR1220L-S FRAME
                fnameAR220148FES(667728),      -- Quidway AR2201-48FE-S FRAME
                fnameAR2204S(667729),          -- Quidway AR2204-S FRAME
                fnameAR2240S(667730),          -- Quidway AR2240-S FRAME
                fnameAR159(667731),            -- Quidway AR159 FRAME
                fnameAR531GPH(667732),         -- Quidway AR531GP-H FRAME
                fnameAR531GBPDH(667733),       -- Quidway AR531GBP-D-H FRAME
                fnameAR5312CH(667734),         -- Quidway AR531-2C-H FRAME
                fnameAR531F2CH(667735),        -- Quidway AR531-F2C-H FRAME
                fnameAR2540H(667736),          -- Quidway AR2540-H FRAME
                fnameAR3560H(667737),          -- Quidway AR3560-H FRAME
                fnameNE16EX-8(667738),         -- Quidway NE16EX-8 FRAME
                fnameAR121S(667739),           -- Quidway AR121-S FRAME
                fnameAR161FS(667740),          -- Quidway AR161F-S FRAME
                fnameAR156W(667741),           -- Quidway AR156W FRAME
                fnameAR159FW(667742),          -- Quidway AR159FW FRAME
                fnameAR161FGWL(667743),        -- Quidway AR161FGW-L FRAME
                fnameAR161FGL(667744),         -- Quidway AR161FG-L FRAME
                fnameNE16EX-6(667745),         -- Quidway NE16EX-6 FRAME
                fnameSRG2320E(667746),         -- Quidway SRG2320E FRAME
                fnameAR162F(667747),           -- Quidway AR162F FRAME
                fnameAR169FVW(667748),         -- Quidway AR169FVW FRAME
                fnameAR161FW-P-M5(667749),     -- Quidway AR161FW-P-M5 FRAME
                fnameAR511GW-UAV2M5(667750),   -- Quidway AR511GW-UAV2M5 FRAME
                fnameAR169GFVW-L(667751),      -- Quidway AR169GFVW-L FRAME
                fnameAR531GBP-U-H(667752),     -- Quidway AR531GBP-U-H FRAME
                fnameAR161FW(667753),          -- Quidway AR161FW FRAME
                fnameAR1220F-S(667754),        -- Quidway AR1220F-S FRAME
                fnameAR511GW-LAV2M3(667756),   -- Quidway AR511GW-LAV2M3 FRAME
                fnameAR161A(667757),           -- Quidway AR161A FRAME
                fnameAR169A(667758),           -- Quidway AR169A FRAME
                fnameAR161AG-L(667759),        -- Quidway AR161AG-L FRAME
                fnameAR169AGW-I(667760),       -- Quidway AR169AGW-I FRAME
                fnameAR1220EVW(667761),        -- Quidway AR1220EVW FRAME
                fnameAR2220E(667762),          -- Quidway AR2220E FRAME
                fnameAR3670(667763),           -- Quidway AR3670 FRAME
                fnameAR3650(667764),           -- Quidway AR3650 FRAME
                fnameAR2630(667765),           -- Quidway AR2630 FRAME
                fnameAR2204E(667766),          -- Quidway AR2204E FRAME
                fnameAR2220E-L(667767),        -- Quidway AR2220E-L FRAME
                fnameAR511GW-L-B3(667768),     -- Quidway AR511GW-L-B3 FRAME
                fnameAR511GW-LM7(667769),      -- Quidway AR511GW-LM7 FRAME
                fnameAR513W-V3M8(667770),      -- Quidway AR513W-V3M8 FRAME
                fnameAR1220E-S(667771),        -- Quidway AR1220E-S FRAME
                fnameAR3260-S(667772),         -- Quidway AR3260-S FRAME
                fnameAR531G-U-D-H(667773),     -- Quidway AR531G-U-D-H FRAME
                fnameAR531GPe-U-H(667774),     -- Quidway AR531GPe-U-H FRAME
                fnameAR531GR-U-H(667775),      -- Quidway AR531GR-U-H FRAME
                fnameAR550-8FE-D-H(667776),    -- Quidway AR550-8FE-D-H FRAME
                fnameAR550-24FE-D-H(667777),   -- Quidway AR550-24FE-D-H FRAME
                fnameAR502G(667778),           -- Quidway AR502G FRAME
                fnameAR531GP-H(667779),        -- Quidway AR531GP-H FRAME
                fnameAR531GB-U-D-H(667780),    -- Quidway AR531GB-U-D-H FRAME
                fnameAR161(667781),            -- Quidway AR161 FRAME
                fnameAR161G-LE(667782),        -- Quidway AR161G-LE FRAME
                fnameAR161G-HSPA7(667783),     -- Quidway AR161G-HSPA+7 FRAME
                fnameAR161GW-L(667784),        -- Quidway AR161GW-L FRAME
                fnameAR169(667785),            -- Quidway AR169 FRAME
                fnameAR169G-LE(667786),        -- Quidway AR169G-LE FRAME
                fnameAR169G-HSPA7(667787),     -- Quidway AR169G-HSPA+7 FRAME
                fnameAR121(667788),            -- Quidway AR121 FRAME
                fnameAR129(667789),            -- Quidway AR129 FRAME
                fnameAR503GW-LM6(667790),      -- Quidway AR503GW-LM6 FRAME
                fnameAR169-P-M9(667791),       -- Quidway AR169-P-M9 FRAME
                fnameAR1220E(667792),          -- Quidway AR1220E FRAME
                fnameAR1220EV(667793),         -- Quidway AR1220EV FRAME
                fnameAR161F(667794),           -- Quidway AR161F FRAME
                fnameAR169FGW-L(667795),       -- Quidway AR169FGW-L FRAME
                fnameAR151-S2(667796),         -- Quidway AR151-S2 FRAME
                fnameAR509G-L-D-H(667797),     -- Quidway AR509G-L-D-H FRAME
                fnameAR169FV-8S(667798),       -- Quidway AR169FV-8S FRAME
                fnameAR169FVW-8S(667799),      -- Quidway AR169FVW-8S FRAME
                fnameAR121W(667800),           -- Quidway AR121W FRAME
                fnameAR121W-S(667801),         -- Quidway AR121W-S FRAME
                fnameAR161W(667802),           -- Quidway AR161W FRAME
                fnameAR129W(667803),           -- Quidway AR129W FRAME
                fnameAR2204-27GE(667804),      -- Quidway AR2204-27GE FRAME
                fnameAR2204-27GE-P(667805),    -- Quidway AR2204-27GE-P FRAME
                fnameAR2204-51GE-P(667806),    -- Quidway AR2204-51GE-P FRAME
                fnameAR1220C(667807),          -- Quidway AR1220C FRAME
                fnameAR1220-S2(667808),        -- Quidway AR1220-S2 FRAME
                fnameAR2240C(667809),          -- Quidway AR2240C FRAME
                fnameAR2504-H(667810),         -- Quidway AR2504-H FRAME
                fnameAR161FV-1P(667811),       -- Quidway AR161FV-1P FRAME
                fnameAR169W-P-M9(667812),      -- Quidway AR169W-P-M9 FRAME
                fnameAR169RW-P-M9(667813),     -- Quidway AR169RW-P-M9 FRAME
                fnameAR531GZ-U-D(667814),      -- AR531GZ-U-D FRAME
                fnameAR161FGW-LA(667815),      -- AR161FGW-LA FRAME
                fnameAR515GW-LM9-D(667816),    -- AR515GW-LM9-D FRAME
                fnameAR161G-U(667817),         -- AR161G-U FRAME
                fnameAR121GW-L(667818),        -- AR121GW-L FRAME
                fnameAR129GW-L(667819),        -- AR129GW-L FRAME
                fnameAR502G-L-D-H(667820),     -- AR502G-L-D-H FRAME
                fnameAR502GR-L-D-H(667821),    -- AR502GR-L-D-H FRAME
                fnameAR531G-F(667822),         -- AR531G-F FRAME
                fnameAR511CGW-LAV2M3(667823),  -- AR511CGW-LAV2M3 FRAME
                fnameAR111-S(667824),          -- AR111-S FRAME
                fnameAR503GW-LcM7(667825),     -- AR503GW-LcM7 FRAME
                fnameAR511GW-LcAV2M3(667826),  -- AR511GW-LcAV2M3 FRAME
                fnameAR1000V(667827),          -- AR1000V FRAME
                fnameAR511DcGW-LcAV2(667828),  -- AR511DcGW-LcAV2 FRAME
                fnameAR2204-51GE(667829),      -- AR2204-51GE FRAME
                fnameAR2204E-D(667830),        -- AR2204E-D FRAME
                fnameAR2504E-H(667831),        -- AR2504E-H FRAME
                fnameAR509G-Lc(667832),        -- AR509G-Lc FRAME
                fnameAR129CGVW-L(667833),      -- AR129CGVW-L FRAME
                fnameAR101-S(667834),          -- AR101-S FRAME
                fnameAR101W-S(667835),         -- AR101W-S FRAME
                fnameAR550C-4GE(667836),       -- AR550C-4GE FRAME
                fnameAR550C-2C6GE(667837),     -- AR550C-2C6GE FRAME
                fnameAR509CG-Lt(667838),       -- AR509CG-Lt FRAME
                fnameAR509CG-Lt-N(667839),     -- AR509CG-Lt-N FRAME
                fnameAR503EQGW-L(667840),      -- AR503EQGW-L FRAME
                fnameAR503EW(667841),          -- AR503EW FRAME
                fnameAR503EDGW-Lc(667842),     -- AR503EDGW-Lc FRAME
                fnameAR509CG-L(667843),        -- AR509CG-L FRAME
                fnameAR168FVW(667844),         -- AR168FVW FRAME
                fnameAR532(667845),            -- AR532 FRAME
                fnameAR502ERc(667846),         -- AR502ERc FRAME
                fnameAR502EGR-L(667847),       -- AR502EGR-L FRAME
                fnameAR502EG-L(667848),        -- AR502EG-L FRAME
                fnameAR502EGW-L(667849),       -- AR502EGW-L FRAME
                fnameAR550E(667850),           -- AR550E FRAME
                fnameAR509CG-Lc(667851),       -- AR509CG-Lc FRAME
                fnameAR2204-51GE-R(667852),    -- AR2204-51GE-R FRAME
                fnameAR161-S(667853),          -- AR161-S FRAME
                fnameAR161W-S(667854),         -- AR161W-S FRAME
                fnameAR161GW-Lc-S(667855),     -- AR161GW-Lc-S FRAME
                fnameAR509GW-L-D-H(667856),    -- AR509GW-L-D-H FRAME
                fnameSRG2340E(667857),         -- SRG2340E FRAME
                fnameSRG2320EI(667858),        -- SRG2320EI FRAME
                fnameSRG1320E(667859),         -- SRG1320E FRAME
                fnameAR1200EW-T1(667860),      -- AR1200EW-T1 FRAME
                fnameAR509EG-U-A(667861),      -- AR509EG-U-A FRAME
                fnameAR169G-Lo(667862),        -- AR169G-Lo FRAME
                fnameAR161FG-Lc(667863),       -- AR161FG-Lc FRAME
                fnameAR161FGW-Lc(667864),      -- AR161FGW-Lc FRAME
                fnameAR161G-Lc(667865),        -- AR161G-Lc FRAME
                fnameAR101GW-Lc-S(667866),     -- AR101GW-Lc-S FRAME
                fnameAR201V(667867),           -- AR201V FRAME
                fnameAR503EDGW-Lc3(667868),    -- AR503EDGW-Lc3 FRAME
                fnameAR109(667869),            -- AR109 FRAME
                fnameAR109W(667870),           -- AR109W FRAME
                fnameAR109GW-L(667871),        -- AR109GW-L FRAME
                fnameAR502CG-L(667872),        -- AR502CG-L FRAME
                fnameAR2220E-S(667873),        -- AR2220E-S FRAME
                fnameAR2240C-S(667874),        -- AR2240C-S FRAME
                fnameAR3260E-S(667875),        -- AR3260E-S FRAME
                fnameAR129CVW(667876),         -- AR129CVW FRAME
                fnameAR1220-8GE(667877),       -- AR1220-8GE FRAME
                fnameAR2204-24GE(667878),      -- AR2204-24GE FRAME
                fnameAR2204-48GE-P(667879),    -- AR2204-48GE-P FRAME
                fnameAR505Kc-L-RM(667880),     -- AR505Kc-L-RM FRAME
                fnameAR505Ke-L(667881),        -- AR505Ke-L FRAME
                fnameAR2504-D-H(667882),       -- AR2504-D-H FRAME
                fnameAR502EGRb-L(667883),      -- AR502EGRb-L FRAME
                fnameAR169CVW-4B4S(667884),    -- AR169CVW-4B4S FRAME
                fnameAR169CVW(667885),         -- AR169CVW FRAME
                fnameAR169EGW-L(667886),       -- AR169EGW-L FRAME
                fnameAR169EW(667887),          -- AR169EW FRAME
                fnameAR161EW(667888),          -- AR161EW FRAME
                fnameAR161EW-M1(667889),       -- AR161EW-M1 FRAME
                fnameAR509CGW-L(667890),       -- AR509CGW-L FRAME
                fnameAR509CG-Lt-7(667891),     -- AR509CG-Lt-7 FRAME
                fnameAR-Sc-Lc(667892),         -- AR-Sc-Lc FRAME
                fnameAR-Sc-Le(667893),         -- AR-Sc-Le FRAME
                fnameAR-Sc-La(667894),         -- AR-Sc-La FRAME
                fnameAR502ER(667895),          -- AR502ER FRAME
                fnameAR169FGVW-L-8S(667896),   -- AR169FGVW-L-8S FRAME
                fnameAR502ERb(667897),         -- AR502ERb FRAME
                fnameAR502EGRc-Lc(667898),     -- AR502EGRc-Lc FRAME
                fnameAR111P-S(667899),         -- AR111P-S FRAME
                fnameAR513GW-LcV1(667900),     -- AR513GW-LcV1 FRAME
                fnameAR513W-V1(667901),        -- AR513W-V1 FRAME
                fnameAR1610(667902),           -- AR1610 FRAME
                fnameAR161EGW-L(667903),       -- AR161EGW-L FRAME
                fnameAR2204XE(667904),         -- AR2204XE FRAME
                fnameAR169JFVW-4B4S(667905),   -- AR169JFVW-4B4S FRAME
                fnameAR511EGW-LcAV2(667906),   -- AR511EGW-LcAV2 FRAME
                fnameAR503HGW-L(667907),       -- AR503HGW-L FRAME
                fnameAR503HGW-Lc(667908),      -- AR503HGW-Lc FRAME
                fnameAR502EGRz-Lc(667909),     -- AR502EGRz-Lc FRAME
                fnameAR515CGW-L(667910),       -- AR515CGW-L FRAME
                fnameAR1504-24S(667911),       -- AR1504-24S FRAME
                fnameAR1504-24T(667912),       -- AR1504-24T FRAME
                fnameAR1504-16S8T(667913),     -- AR1504-16S8T FRAME
                fnameAR1504-8S16T(667914),     -- AR1504-8S16T FRAME
                fnameAR168F-4P(667915),        -- AR168F-4P FRAME
                fnameAR550C-2C6GE-2D(667916),  -- AR550C-2C6GE-2D FRAME
                fnameAR502EG-L-PD(667917),    -- AR502EG-L-PD FRAME
                fnameAR129CV(667918),          -- AR129CV FRAME
                fnameAR-Sc-U-BC(667919),       -- AR-Sc-U-BC FRAME
                fnameAR-Se-U-BC(667920),       -- AR-Se-U-BC FRAME
                fnameAR-Sa-U-BC(667921),       -- AR-Sa-U-BC FRAME
                fnameAR-Sc-Lc-BC(667922),      -- AR-Sc-Lc-BC FRAME
                fnameAR-Se-L-BC(667923),       -- AR-Se-L-BC FRAME
                fnameAR-Sa-La-BC(667924),      -- AR-Sa-La-BC FRAME
                fnameAR-Sc-Lc-MC(667925),      -- AR-Sc-Lc-MC FRAME
                fnameAR-Se-L-MC(667926),       -- AR-Se-L-MC FRAME
                fnameAR-Sa-La-MC(667927),      -- AR-Sa-La-MC FRAME
                fnameAR-Sc-MC(667928),         -- AR-Sc-MC FRAME
                fnameAR-Se-MC(667929),         -- AR-Se-MC FRAME
                fnameSRG550C-4GE(667930),      -- SRG550C-4GE FRAME
                fnameSRG550C-2C6GE(667931),    -- SRG550C-2C6GE FRAME
                fnameSRG509CG-Lc(667932),      -- SRG509CG-Lc FRAME
                fnameSRG550-24FE(667933),      -- SRG550-24FE FRAME
                fnameAR503EDGW-Lo(667934),     -- AR503EDGW-Lo FRAME
                fnameAR161FW-DGP(667935),      -- AR161FW-DGP FRAME
                fnameAR161F-DGP(667936),       -- AR161F-DGP FRAME
                fnameAR-So-Lo-BC(667937),      -- AR-So-Lo-BC FRAME
                fnameAR-So-Lo-MC(667938),      -- AR-So-Lo-MC FRAME
                fnameAR-So-U-BC(667939),       -- AR-So-U-BC FRAME
                fnameAR505Ka-L(667940),        -- AR505Ka-L FRAME
                fnameAR502EGW-Lc(667941),      -- AR502EGW-Lc FRAME
                fnameAR502EGRz-L(667942),      -- AR502EGRz-L FRAME
                fnameAR503GW-Lo(667943),       -- AR503GW-Lo FRAME
                fnameAR502EG-La(667944),       -- AR502EG-La FRAME
                fnameAR651W-X4(667945),        -- AR651W-X4 FRAME
                fnameAR651-X8(667946),         -- AR651-X8 FRAME
                fnameAR651U(667947),           -- AR651U FRAME
                fnameAR651-L(667948),          -- AR651-L FRAME
                fnameAR651-L6(667949),         -- AR651-L6 FRAME
                fnameAR111EC(667950),          -- AR111EC FRAME
                fnameAR111EC-S(667951),        -- AR111EC-S FRAME
                fnameAR161EC(667952),          -- AR161EC FRAME
                fnameAR1220EC(667953),         -- AR1220EC FRAME
                fnameAR1220C-S(667954),        -- AR1220C-S FRAME
                fnameAR2204-27GE-S(667955),    -- AR2204-27GE-S FRAME
                fnameAR502EG-Lj(667956),       -- AR502EG-Lj FRAME
                fnameAR651F-Lite(667957),      -- AR651F-Lite FRAME
                fnameAR631-Lite(667958),       -- AR631-Lite FRAME
                fnameAR651W(667959),           -- AR651W FRAME
                fnameAR169JFVW-2S(667960),     -- AR169JFVW-2S FRAME
                fnameAR6120(667961),           -- AR6120 FRAME
                fnameAR6120V(667962),          -- AR6120V FRAME
                fnameAR6120VW(667963),         -- AR6120VW FRAME
                fnameAR1660(667964),           -- AR1660 FRAME
                fnameAR1660C(667965),          -- AR1660C FRAME
                fnameAR6300(667966),           -- AR6300 FRAME
                fnameAR6280(667967),           -- AR6280 FRAME
                fnameAR336VW(667968),          -- AR336VW FRAME
                fnameAR1600U-X14(667969),      -- AR1600U-X14 FRAME
                fnameAR2204XE-DC(667970),      --AR2204XE-DC FRAME
                fnameAR651(667971),            --AR651 FRAME
                fnameAR651-L4EA(667972),       --AR651-L4EA FRAME
                fnameAR651-L6EA(667973),       --AR651-L6EA FRAME
                fnameAR6120-S(667974),         --AR6120-S FRAME
                fnameAR1660-S(667975),         --AR1660-S FRAME
                fnameAR657-35B(667976),        --AR657-35B FRAME
                fnameAR657W-35B(667977),       --AR657W-35B FRAME
                fnameAR6140-16G4XG(667978),    --AR6140-16G4XG FRAME
                fnameAR2204E-D-27GE(667979),   --AR2204E-D-27GE FRAME
                fnameAR6140L-9G-2AC(667980),   --AR6140L-9G-2AC FRAME
                fnameAR651-Lite(667981),       --AR651-Lite FRAME
                fnameAR6140L-S(667982),        --AR6140L-S FRAME
                fnameAR6300-S(667983),         --AR6300-S FRAME
                fnameAR611W(667984),           --AR611W FRAME
                fnameAR611W-LTE4CN(667985),    --AR611W-LTE4CN FRAME
                fnameAR617VW(667986),          --AR617VW FRAME
                fnameAR617VW-LTE4EA(667987),   --AR617VW-LTE4EA FRAME
                fnameAR6121(667988),           --AR6121 FRAME
                fnameSRG1340-9G(667990),       --SRG1340-9G FRAME
                fnameSRG33X0(667991),          --SRG33X0 FRAME
                fnameAR651-C(667992),          --AR651-C FRAME
                fnameAR651W-C(667993),         --AR651W-C FRAME
                fnameAR651U-A4-C(667994),      --AR651U-A4-C FRAME
                fnameAR657W-C(667995),         --AR657W-C FRAME
                fnameAR6121C-S(667996),        --AR6121C-S FRAME
                fnameAR6121-S(667997),         --AR6121-S FRAME
                fnameAR6140H-S(667998),        --AR6140H-S FRAME
                fnameSRG1301(667999),          --SRG1301 FRAME
                fnameAR6280-S(668000),   	   --AR6280-S FRAME
		        fnameAR8140-12G10XG(668001),   --AR8140-12G10XG FRAME
		        fnameAR8140-T-12G10XG(668002), --AR8140-T-12G10XG FRAME
		        fnameAR502H(668003),     	   --AR502H FRAME
		        fnameAR502H-CN(668004),        --AR502H-CN FRAME
		        fnameAR502H-5G(668005),        --AR502H-5G FRAME
		        fnameAR651W-8P(668006),   	   --AR651W-8P FRAME
		        fnameAR6140E-9G-2AC(668007),   --AR6140E-9G-2AC FRAME
		        fnameAR6121E(668008),   	   --AR6121E FRAME
		        fnameAR10(668009),             --AR10 FRAME
				fnameAR651K(668010),           --AR651K FRAME
				fnameAR6140K-9G-2AC(668011),   --AR6140K-9G-2AC FRAME
				fnameAR6121K(668012),          --AR6121K FRAME
                fnameAR6280K(668013),          --AR6280K FRAME
                fnameAR6300K(668014),          --AR6300K FRAME
				fnameSRG1340-16G4XG(668016),   --SRG1340-16G4XG FRAME
				fnameSRG1321(668017),          --SRG1321 FRAME
				fnameAR720(668018),            --AR720 FRAME
				fnameAR730(668019),            --AR730 FRAME
				fnameAR6280C-S(668020),        --AR6280C-S FRAME
				fnameAR6300C-S(668021),        --AR6300C-S FRAME
				fnameAR611-S(668022),          --AR611-S FRAME
				fnameAR611W-S(668023),   	   --AR611W-S FRAME
				fnameAR303(668024),            --AR303 FRAME
				fnameAR303W(668025),   	       --AR303W FRAME
				fnameAR6121EC-S(668026),   	   --AR6121EC-S FRAME
				fnameAR6121E-S(668027),   	   --AR6121E-S FRAME
				fnameAR6140E-S(668028),   	   --AR6140E-S FRAME
				fnameSRG1311(668029),   	   --SRG1311 FRAME
				fnameSRG1340E(668030),   	   --SRG1340E FRAME
				fnameAR611(668031),   	       --AR611 FRAME
				fnameAR6710-L50T2X4(668032),   --AR6710-L50T2X4 FRAME
				fnameAR6710-L50T2X4-T(668033), --AR6710-L50T2X4-T FRAME
				fnameAR6710-L26T2X4(668034),   --AR6710-L26T2X4 FRAME
				fnameAR6710-L26T2X4-T(668035), --AR6710-L26T2X4-T FRAME
				fnameAR502H-5G-CN(668036),     --AR502H-5G-CN FRAME
				fnameAR5710-H8T2TS1(668037),   --AR6710-L8T3TS1X2 FRAME
				fnameAR5710-H8T2TS1-T(668038), --AR6710-L8T3TS1X2-T FRAME
				fnameAR6710-L8T3TS1X2(668039), --AR6710-L8T3TS1X2 FRAME
				fnameAR6710-L8T3TS1X2-T(668040), --AR6710-L8T3TS1X2-T FRAME
				fnameRU-5G-101(668041),        --RU-5G-101 FRAME
                fnameAR611E-S(668042),         --AR611E-S FRAME
                fnameAR611-LTE4EA(668043),   --AR611-LTE4EA FRAME
                fnameAR611W-LTE6EA(668044),   --AR611W-LTE6EA FRAME
                fnameAR631I-LTE4CN(668045),   --AR631I-LTE4CN FRAME
                fnameAR631I-LTE4EA(668046),   --AR631I-LTE4EA FRAME
                fnameAR8700-8(668047),        --AR8700-8 FRAME
                fnameAR6510-L11T1X2(668048),         --AR6510-L11T1X2 FRAME
                fnameAR6510-L5T4S4(668049),          --AR6510-L5T4S4 FRAME
                fnameAR5510-H8P2TW1(668050),      --AR5510-H8P2TW1 FRAME
                fnameAR5510-H10T1(668051),            --AR5510-H10T1 FRAME
                fnameAR5510-L5T-LTE4EA(668052),   --AR5510-L5T-LTE4EA FRAME
                fnameAR5510-L5T(668053),                 --AR5510-L5T FRAME
                fnameAR6500-10(668054),                   --AR6500-10 FRAME
                fnameAR5710-S10T1X2(668055),              --AR5710-S10T1X2 FRAME
                fnameAR5710-S8P2X(668056),                --AR5710-S8P2X FRAME
                fnameAR5710-S8P2X-LTE4CN(668057),         --AR5710-S8P2X-LTE4CN FRAME
                fnameAR5710-S8T2X(668058),                --AR5710-S8T2X FRAME
                fnameAR5710-S8T2X-LTE4EA(668059),         --AR5710-S8T2X-LTE4EA FRAME
                fnameAR5710-S8T2XE(668060),               --AR5710-S8T2XE FRAME
                fnameAR5710-S8T2XE-LTE4EA-T(668061),      --AR5710-S8T2XE-LTE4EA-T FRAME
                fnameAR5710-S8T2XE-NRCN(668062),          --AR5710-S8T2XE-NRCN FRAME
                fnameAR6710-L14T2X4(668063),              --AR6710-L14T2X4 FRAME
                fnameAR5510-S10T1X2(668064),              --AR5510-S10T1X2 FRAME
                fnameAR5510-S8P2X(668065),                --AR5510-S8P2X FRAME
                fnameAR5510-S8P2X-LTE4CN(668066),         --AR5510-S8P2X-LTE4CN FRAME
                fnameAR5510-S8T2X(668067),                --AR5510-S8T2X FRAME
                fnameAR5510-S8T2X-LTE4EA(668068),         --AR5510-S8T2X-LTE4EA FRAME
                fnameAR5510-S8T2XE-NRCN(668069),          --AR5510-S8T2XE-NRCN FRAME
                fnameAR617VW-LTE4(668070),                --AR617VW-LTE4 FRAME
                fnameAR5710S-S8T2X(668071),               --AR5710S-S8T2X FRAME
                fnameAR5710S-S10T1X2(668072),             --AR5710S-S10T1X2 FRAME
				fnameAR6710-H4T4X2Y7(668073),             --AR6710-H4T4X2Y7 FRAME
				fnameAR5710-S8T2XE-LTE4CN(668074),        --AR5710-S8T2XE-LTE4CN FRAME
				fnameAR5510-H10T2XW1(668075),             --AR5510-H10T2XW1 FRAME
				fnameAR5510-L5TW(668076),                 --AR5510-L5TW FRAME
				fnameAR5510-L5TWDS-LTE4EA(668077),        --AR5510-L5TWDS-LTE4EA FRAME
				fnameAR5510-L5TWDS(668078),               --AR5510-L5TWDS FRAME
				fnameAR5510-L5TW-LTE6EA(668079),          --AR5510-L5TW-LTE6EA FRAME
				fnameAR651EW(668080),                     --AR651EW FRAME
				fnameAR5710-S28T2S2XE4(668081),           --AR5710-S28T2S2XE4 FRAME
				fnameAR5710-S52T2XE4(668082),             --AR5710-S52T2XE4 FRAME
                fnameAR617(668083),                       --AR617 FRAME
                fnameAR617-LTE4EA(668084),                --AR617-LTE4EA FRAME
                fnameAR6140E-L14T2X4-V2(668085),          --AR6140E-L14T2X4-V2 FRAME
                fnameAR502H-LTE4AU-V2(668086),            --AR502H-LTE4AU-V2 FRAME
                fnameAR502H-LTE4CN-V2(668087),            --AR502H-LTE4CN-V2 FRAME
                fnameAR502H-LTE4EA-V2(668088),            --AR502H-LTE4EA-V2 FRAME
                fnameAR5710-S8T1XWE(668089),              --AR5710-S8T1XWE Main Control Unit
                fnameAR5710-S8T1XWE-NRGL(668090),         --AR5710-S8T1XWE-NRGL Main Control Unit
                fnameAR5710-S8P2XE-NRGL(668091),          --AR5710-S8P2XE-NRGL Main Control Unit
                fnameAR5710-S8T2XE-NRGL(668092),          --AR5710-S8T2XE-NRGL Main Control Unit
                fnameAR5710-S8T2S(668093),                --AR5710-S8T2S Main Control Unit
                fnameAR502H-NRGL-V2(668094),              --AR502H-NRGL-V2 FRAME
                fnameAR5710-H4T4N2X(668095),              --AR5710-H4T4N2X Main Control Unit
                fnameAR5710-H4T4N2X-LTE4EA(668096),       --AR5710-H4T4N2X-LTE4EA Main Control Unit
                fnameAR5710-H2T4N2X-NRGL(668097),         --AR5710-H2T4N2X-NRGL Main Control Unit
                fnameAR5710-H2T4PN2X-NRGL(668098),        --AR5710-H2T4PN2X-NRGL Main Control Unit
                fnameAR5710-S8P1XDSE-2LTE4EA(668099),     --AR5710-S8P1XDSE-2LTE4EA Main Control Unit
                fnameAR5710-S8TWDSE-LTE4EA(668100),       --AR5710-S8TWDSE-LTE4EA Main Control Unit
                fnameAR5710-S8T1XWE-LTE4CN(668101),       --AR5710-S8T1XWE-LTE4CN Main Control Unit
                fnameAR5510-S8T2XE-NRGL(668102),          --AR5510-S8T2XE-NRGL Main Control Unit
                fnameAR180(668103),                       --AR180 Main Control Unit
                fnameAR180PLUS(668104),                   --AR180PLUS Main Control Unit
                fnameAR180PRO(668105),                    --AR180PRO Main Control Unit
                fnameE3(668106),                          --E3 Main Control Unit
                fnameAR280(668107),                       --AR280 Main Control Unit
                fnameAR5510-S8T2S(668108),                --AR5510-S8T2S Main Control Unit
                fnameRU-301(668109),                      --RU-301 FRAME
                fnameAR580(668110),                       --AR580 FRAME
                fnameAR580Plus(668111),                   --AR580Plus FRAME
                fnameAR580Pro(668112),                    --AR580Pro FRAME
                fnameAR502H-ELTE-V2(668113),              --AR502H-ELTE-V2 FRAME
                fnameAR5710-S52T2XE4-2025(668114),        --AR5710-S52T2XE4-2025 FRAME
                fnameAR5710-S28T2S2XE4-2025(668115),      --AR5710-S28T2S2XE4-2025 FRAME
                fnameAR5710-S52T2XE(668116),              --AR5710-S52T2XE FRAME
                fnameAR5710-S28T2S2XE(668117),            --AR5710-S28T2S2XE FRAME
                fnameAR6700V-L-16vCPU(668118),            --AR6700V-L-16vCPU FRAME
                fnameAR6700V-L-8vCPU(668119),             --AR6700V-L-8vCPU FRAME
                fnameAR6700V-L-4vCPU(668120),             --AR6700V-L-4vCPU FRAME
                fnameAR6700V-L-2vCPU(668121),             --AR6700V-L-2vCPU FRAME
				fnameEG600-W-5G(668122),                  --EG600-W-5G FRAME
				fnameEG700-P-5G(668123),                  --EG700-P-5G FRAME
				fnameEG800-4C(668124),                    --EG800-4C FRAME

-- NE20E-X6:
               fnameNE20EX6DC(675840),        --NE20E-X6 chassis
               fnameNE20EX6AC(675841),        --NE20E-X6 chassis
               fnameNE20E-X2-M8(675842),   --Quidway CX600-X2-M8 FRAME,ne20e,AC. compatitable with old panel, no "AC" in name
               fnameNE20E-X1-M4(675843),      -- Quidway CX600-X1-M4 FRAME, ne20e
               fnameNE20E-X2-M16(675844),     -- Quidway CX600-X2-M16 FRAME, ne20e
               fnameNE20E-X2-M8-DC(675845),   --Quidway CX600-X2-M8 FRAME,ne20e,DC
                fnameNE20E-S2E(675846),      --Quidway CX600-M2E FRAME,ne20e-S2  80Gps
                fnameNE20E-S2F(675847),      --Quidway CX600-M2F FRAME,ne20e-S2 160Gps
                fnameNE20E-X2-M8A(675848),      --Quidway CX600-X2-M8A-AC FRAME,ne20e
                fnameNE20E-X2-M8A-DC(675849),   --Quidway CX600-X2-M8A-DC FRAME,ne20e
                fnameNE20E-X2-M16A(675850),     --Quidway CX600-X2-M16A FRAME,ne20e
-- vRGW:
               fnamevRGW(679939),         --vRGW chassis

-- CloudEngine: 0x000A8000~0x000A8fff(688128~692223)
                fnameCE12804(688128),                -- CloudEngine CE12804 FRAME,CE-BAK04A,12804 Backplane-1*1
                fnameCE12808(688129),                -- CloudEngine CE12808 FRAME,CE-BAK08A,12808 Backplane-1*1
                fnameCE12812(688130),                -- CloudEngine CE12812 FRAME,CE-BAK12A,12812 Backplane-1*1
                fnameCE585048T4S2QEI(688131),        -- CloudEngine CE5850-48T4S2Q-EI Switch(48-Port 1000BASE-T,4-Port 10GBASE-X,2-Port 40GBASE-SR4,AC 110/220V)
                fnameCE685048S4QEI(688132),          -- CloudEngine CE6850-48S4Q-EI Switch (48-Port 10GBASE-X,4-Port 40GBASE-SR4,AC 110/220V)
                fnameCE685048T4QEI(688133),          -- CloudEngine CE6850-48T4Q-EI Switch(48-port 10GBASE-T,4-port 40GBASE-SR4,AC 110/220V)
                fnameCE581024T4SEI(688134),          -- CloudEngine CE5810-24T4S-EI Switch(24-Port GE RJ45,4-Port 10GE SFP+)
                fnameCE581048T4SEI(688135),          -- CloudEngine CE5810-48T4S-EI Switch(48-Port GE RJ45,4-Port 10GE SFP+)
                fnameCE12816(688136),                -- CloudEngine CE12816 FRAME,CE-BAK16A,12816 Backplane-1*1
                fnameCE585048T4S2QHI(688137),        -- CloudEngine CE5850-48T4S2Q-HI Switch(48-Port GE RJ45,4-Port 10GE SFP+,2-Port 40GE QSFP+)
                fnameCE785032QEI(688138),            -- CloudEngine CE7850-32Q-EI Switch(32-Port 40GE QSFP+)
                fnameCE681048S4QEI(688139),          -- CloudEngine CE6810-48S4Q-EI Switch (48-Port 10GE SFP+,4-Port 40GE QSFP+)
                fnameCE681048S4QLI(688140),          -- CloudEngine CE6810-48S4Q-LI Switch (48-Port 10GE SFP+,4-Port 40GE QSFP+)
                fnameCE681048SLI(688141),            -- CloudEngine CE6810-48S-LI Switch (48-Port 10GE SFP+)
                fnameCE12804S(688142),               -- CloudEngine 12800S,CE01PBK04AS,CE12804S Power Backplane,1*1
                fnameCE12808S(688143),               -- CloudEngine 12800S,CE01BAK08AS,CE12808S Backplane A,1*1
                fnameCE685048S6QHI(688144),          -- CloudEngine CE6850-48S6Q-HI Switch (48-Port 10GE SFP+,6-Port 40GE QSFP+)
                fnameSVFLEAF(688145),                -- CloudEngine Svf Leaf Frame
                fnameCE6850U48S6QHI(688146),         -- CloudEngine CE6850U-48S6Q-HI Switch (24-Port 10GE SFP+,support 2/4/8G FC,2-Port 40GE QSFP+)
                fnameCE685048T6QHI(688147),          -- CloudEngine CE6850-48T6Q-HI Switch (48-Port 10GE RJ45,6-Port 40GE QSFP+)
                fnameCE681032T16S4QLI(688148),       -- CloudEngine CE6810-32T16S4Q-LI Switch (32-Port 10GE RJ45,16-Port 10GE SFP+,4-Port 40GE QSFP+ Optical)
                fnameCE585548T4S2QEI(688150),        -- CloudEngine CE5855-48T4S2Q-EI Switch (48-Port GE RJ45,4-Port SFP+,2-Port 40GE QSFP+)
                fnameCE585524T4S2QEI(688151),        -- CloudEngine CE5855-24T4S2Q-EI Switch (24-Port GE RJ45,4-Port SFP+,2-Port 40GE QSFP+)
                fnameCE6850U24S2QHI(688152),         -- CloudEngine CE6850U-24S2Q-HI Switch (24-Port 10GE SFP+,support 2/4/8G FC,2-Port 40GE QSFP+)
                fnameCE681024S2QLI(688153),          -- CloudEngine CE6810-24S2Q-LI Switch (24-Port 10GE SFP+,2-Port 40GE QSFP+)
                fnameCE685148S6QHI(688154),          -- CloudEngine CE6851-48S6Q-HI Switch (48-Port 10GE SFP+,6-Port 40GE QSFP+)
                fnameCE88604CEI(688155),             -- CloudEngine CE8860-4C-EI Switch(with 4 interface slots)
                fnameCE685548T6QHI(688156),          -- CloudEngine CE6855-48T6Q-HI Switch (48-Port 10GE RJ45, 6-Port 40GE QSFP+)
                fnameCE685548S6QHI(688157),          -- CloudEngine CE6855-48S6Q-HI Switch (48-Port SFP+ Optical,6-Port 40GE QSFP+)
                fnameCE686048S18CQEI(688158),        -- CloudEngine CE6860-48S18CQ-EI Switch (48-Port 25GE SFP28 Optical,18-Port 100GE QSFP28)
                fnameCE686048S8CQEI(688159),         -- CloudEngine CE6860-48S8CQ-EI Switch (48-Port 25GE SFP28 Optical,8-Port 100GE QSFP28)
                fnameCE687048S6CQEI(688160),         -- CloudEngine CE6870-48S6CQ-EI Switch (48-Port SFP+ Optical,6-Port 100GE QSFP28)
                fnameCE687024S6CQEI(688161),         -- CloudEngine CE6870-24S6CQ-EI Switch (24-Port SFP+ Optical,6-Port 100GE QSFP28)
                fnameCE785532QEI(688162),            -- CloudEngine CE7855-32Q-EI Switch(32-Port 40GE QSFP+)
                fnameCE688048S4Q2CQEI(688163),       -- CloudEngine CE6880-48S4Q2CQ-EI Switch(48*10G SFP+,6*40G QSFP+ or 44*10G SFP+,4*40G QSFP+,2*100G QSFP28)
                fnameCE688024S4Q2CQEI(688164),       -- CloudEngine CE6880-24S4Q2CQ-EI Switch(24*10G SFP+,4*40G QSFP+,2*100G QSFP28)
                fnameCE688048T4Q2CQEI(688165),       -- CloudEngine CE6880-48T4Q2CQ-EI Switch(48*10G RJ45,6*40G QSFP+ or 44*10G RJ45,4*40G QSFP+,2*100G QSFP28)
                fnameCE12804E(688166),               -- CE12804E Assembly Chassis
                fnameCE12808E(688167),               -- CE12808E Assembly Chassis
                fnameCE12812E(688168),               -- CE12812E Assembly Chassis
                fnameCE12816E(688169),               -- CE12816E Assembly Chassis
                fnameCE12816M(688170),               -- CE12816M DC Assembly Chassis
                fnameCE885032CQEI(688171),           -- CloudEngine CE8850-32CQ-EI Switch(32-Port 100GE QSFP28,2-Port 10GE SFP+)
                fnameCE687048T6CQEI(688172),         -- CloudEngine 6800,CE6870-48T6CQ-EI,CE6870-48T6CQ-EI Switch(48-Port 10GE RJ45,6-Port 100GE QSFP28)
                fnameCX916(688173),                  -- CX916
                fnameCE885064CQEI(688174),           -- CloudEngine CE8850-64CQ-EI Switch(64-Port 100GE QSFP28)
                fnameCE685648S6QHI(688175),          -- CloudEngine CE6856-48S6Q-HI Switch(48-Port 10G SFP+,6-Port 40GE QSFP+)
                fnameCE685648T6QHI(688176),          -- CloudEngine CE6856-48T6Q-HI Switch(48-Port 10GE RJ45,6-Port 40GE QSFP+)
                fnameCE687548S4CQEI(688178),         -- CloudEngine CE6875-48S4CQ-EI Switch(48-Port 10GE SFP+,4*100GE QSFP28)
                fnameCE686548S8CQEI(688179),         -- CloudEngine CE6865-48S8CQ-EI Switch(48-Port 25GE SFP28,8*100GE QSFP28)
                fnameCE88614CEI(688181),             -- CloudEngine CE8861-4C-EI Mainframe(With 4 Subcard Slots)
                fnameCE88684CEI(688182),             -- CloudEngine CE8868-4C-EI Mainframe(With 4 Subcard Slots)
                fnameCE588048T6QEI(688183),          -- CloudEngine CE5880-48T6Q-EI Switch(44*GE RJ45, 4*10GE RJ45, 6*40GE QSFP+)
                fnameCX930(688184),                  -- CX930_100G
                fnameCE685748S6CQEI(688185),         -- CloudEngine CE6857-48S6CQ-EI Switch(48*10GE SFP+, 6*100GE QSFP28)
                fnameCX930BASE(688186),              -- CX930BASE
                fnameCE16804(688187),                -- CloudEngine CE16804 FRAME
                fnameCE16808(688188),                -- CloudEngine CE16808 FRAME
                fnameCE16816(688189),                -- CloudEngine CE16816 FRAME
                fnameCE98604CEI(688191),             -- CloudEngine 9800,CE9860-4C-EI,CE9860-4C-EI mainframe
                fnameCE686348S6CQ(688194),           -- CloudEngine 6800,CE6863-48S6CQ-F,CE6863-48S6CQ-F switch
                fnameCE688148S6CQ(688195),           -- CloudEngine 6800,CE6881-48S6CQ-F,CE6881-48S6CQ-F switch
                fnameCE682048S6CQ(688197),           -- CloudEngine 6800, CE6820-48S6CQ, CE6820-48S6CQ switch
                fnameCE686548S8CQSI(688198),         -- CloudEngine 6800, CE6865-48S8CQ-SI, CE6865-48S8CQ-SI switch
                fnameCE686348S6CQK(688199),          -- CloudEngine 6800,CE6863-48S6CQ-KB,CE6863-48S6CQ-KB switch
				fnameCE688148S6CQK(688200),          -- CloudEngine 6800,CE6881-48S6CQ-KB,CE6881-48S6CQ-KB switch
				fnameCE6881E48S6CQ(688201),          -- CloudEngine 6800,CE6881E-48S6CQ-B,CE6881E-48S6CQ-B switch 
				fnameCE688148T6CQ(688202),           -- CloudEngine 6800,CE6881-48T6CQ,CE6881-48T6CQ switch
                fnameCE886832CQ8DQP(688203),         -- CloudEngine 8800,CE8868-32CQ8DQ-P,CE8868-32CQ8DQ-P Switch
                fnameCE885132CQ8DQP(688204),         -- CloudEngine 8800,CE8851-32CQ8DQ-P,CE8851-32CQ8DQ-P Switch
                fnameCE686848S8CQP(688205),          -- CloudEngine 6800,CE6868-48S8CQ-P,CE6868-48S8CQ-P switch 
                fnameCE686648S8CQP(688206),          -- CloudEngine 6800,CE6866-48S8CQ-P,CE6866-48S8CQ-P switch 
                fnameCE688148T6CQK(688207),          -- CloudEngine 6800,CE6881-48T6CQ-K,CE6881-48T6CQ-K switch 
				fnameCE588148T6CQ(688208),           -- CloudEngine 5800,CE5881-48T6CQ,CE5881-48T6CQ switch
				fnameCE885132CQ8DQK(688209),         -- CloudEngine 8800,CE8851-32CQ8DQ-K,CE8851-32CQ8DQ-K switch
				fnameCE686648S8CQK(688210),          -- CloudEngine 6800,CE6866-48S8CQ-K,CE6866-48S8CQ-K switch
				fnameDX110(688211),                  -- DX110
				fnameCE5855E48T4S2Q(688212),         -- CloudEngine 5800,CE5855E-48T4S2Q,CE5855E-48T4S2Q switch
				fnameCE6857E48S6CQ(688213),          -- CloudEngine 6800,CE6857E-48S6CQ,CE6857E-48S6CQ switch 
				fnameCE6857E48T6CQ(688214),          -- CloudEngine 6800,CE6857E-48T6CQ,CE6857E-48T6CQ switch 
				fnameCE6865E48S8CQ(688215),          -- CloudEngine 6800,CE6865E-48S8CQ,CE6865E-48S8CQ switch
				fnameCE6860SAN(688216),              -- CloudEngine 6800,CE6860-SAN switch (48*25G SFP28, 8*100G QSFP28, without fan and power modules)(CM)
				fnameCE8850SAN(688217),              -- CloudEngine 8800,CE8850-SAN switch (32*100G QSFP28, without fan and power modules)(CM)
                fnameCE6820H48S6CQ(688218),          -- Assembling Components,CloudEngine 6800,CE6820H-48S6CQ-F,CE6820H-48S6CQ switch(48*10G SFP+,6*100GE QSFP28,2*AC power modules,4*fan modules,port-side exhaust)				
				fnameCE5855F48T4S2Q(688219),         -- 
				fnameCE6857F48S6CQ(688220),          -- 
				fnameCE6857F48T6CQ(688221),          -- 
				fnameCE6863E48S6CQ(688222),          -- 
				fnameCE588248T4S(688223),            -- Assembling Components,CloudEngine 6800,CE6866-48S8CQ-F,CE6865E-48S8CQ-F switch (48*25G SFP28, 8*100G QSFP28, 2*AC power modules, 4*fan modules, port-side exhaust)
				fnameCE6881H48S6CQ(688224),          -- Assembling Components,CloudEngine 6800,CE6881H-48S6CQ-F,CE6881H-48S6CQ-F switch (48*10G SFP+, 6*100G QSFP28, 2*AC power modules, 4*fan modules, port-side exhaust)
				fnameCE6863H48S6CQ(688225),          -- Assembling Components,CE6863H-48S6CQ-F,CE6863H-48S6CQ-F,CE6863H-48S6CQ-F switch (48*25GE SFP28, 6*100GE QSFP28, 2*AC power modules, 4*fan modules, port-side exhaust)
				fnameCE8850E32CQEI(688226),            -- Assembling Components,CE8800,Switch(32-Port 100GE QSFP28,1-Port 10GE SFP+,2*AC Power Module,2*FAN Box,Port-side Exhaust)
				fnameCE8850E64CQ(688227),            -- Assembling Components,CE8800, Switch(32-Port 100GE QSFP28,1-Port 10GE SFP+,2*AC Power Module,2*FAN Box,Port-side Exhaust)
				fnameCE687048S6CQEIA(688228),        -- 
				fnameCE6881H48T6CQ(688229),			  -- CE V3R22C00,CloudEngine 6800,CE6881H-48T6CQ
			    fnameCE6881H48T6CQK(688230),		  -- CE V3R22C00,CloudEngine 6800,CE6881H-48T6CQ-K
			    fnameCE6820H48S6CQK(688231),		  -- CE V3R22C00,CloudEngine 6800,CE6820H-48S6CQ-K
			    fnameCE6881H48S6CQK(688232),		  -- CE V3R22C00,CloudEngine 6800,CE6881H-48S6CQ-K
			    fnameCE6863H48S6CQK(688233),		  -- CE V3R22C00,CloudEngine 6800,CE6863H-48S6CQ-K
			    fnameCE6820S48S6CQ(688234),			  -- CE V3R22C00,CloudEngine 6800,CE6820S-48S6CQ
				fnameCE6860HAM(688245),                --
				fnameCE8850HAM(688246),                --
				fnameCE686648S8CQP6(688247),          -- CE V3R22C00,CloudEngine 6800,CE6820S-48S6CQ-P6
				fnameCE98604CEIA(688248),  -- CE V2R22C10
				fnameDX511(688249),     -- DX511	
				fnameDX112(688250),     -- DX112			
				fnameCE685548XS8CQ(688251),			-- CE V3R23C00
				fnameCE6885LL56F(688252),				-- CE V3R23C00
				fnameCE688548YS8CQ(688253),			-- CE V3R23C00
				fnameCE688548YS8CQT(688254),		    -- CE V3R23C00
				fnameCE6885SAN56F(688256),				-- CE V3R23C00
				fnameCE885532CQ4BQ(688257),			-- CE V3R23C00
				fnameCE16800X4(688258),				-- CE V3R23C00
				fnameCE16800X8(688259),				-- CE V3R23C00
				fnameCE16800X16(688260),			-- CE V3R23C00
				fnameCE585548T4XS(688262),			-- CE V3R23C00
				fnameCE5855SH48T4XS(688263),			-- CE V3R23C00
				fnameCE5855SL48T4XS(688264),			-- CE V3R23C00
                fnameCE6885H48YS8CQ(688265),			-- CE V3R23C10
                fnameCE887524BQ8DQ(688266),
                fnameCE8865SAN4C(688267),
                fnameCE88654C(688268),
                fnameCE6885T48YS8CQ(688269),
                fnameCE6855T48XS8CQ(688270),
                fnameCE8855T32CQ4BQ(688271),
                fnameCE6885U48YS8CQ(688272),
                fnameCE6855U48XS8CQ(688273),
                fnameCE8855U32CQ4BQ(688274),
                fnameCE6885M48YS8CQ(688275),
                fnameCE6855M48XS8CQ(688276),
                fnameCE16890X8(688277),
                fnameCE16890X16(688278),
                fnameCE16870X4(688279),
                fnameCE16870X8(688280),
                fnameCE16870X16(688281),
                fnameCE16880X8(688282),
                fnameCE16880X16(688283),			-- CE V3R23C10
                fnameCE885132CQ4BQ(688284),			-- CE V3R23C00
                fnameCE6863E48S8CQ(688285),			-- CE V3R23C00
                fnameLQG311-L1(688286),
                fnameLQU311-L1(688287),
                fnameLQG311-L2(688288),
                fnameLQC311-L2(688289),
                fnameLQG311-L3(688290),
                fnameLQG311-L4(688291),
				fnameXH168008(688292),
				fnameXH1680016(688293),
				fnameXH811024BQ8DQ(688294),
				fnameXH911024BQ8DQ(688295),
				fnameCE985532DQ(688296),
				fnameXH821032DQ(688297),
				fnameXH921032DQ(688298),
				fnameCE682048S6CQA(688299),
				fnameCE6885L48YS8CQ(688300),
				fnameCE98654C(688303),
				fnameCE9865U4C(688304),
				fnameCE9865M4C(688305),
				fnameCE9865T4C(688306),
				fnameGM510MERGE(688307),
				fnameGM510STORAGE(688308),
				fnameGM110OOB(688309),
				fnameGM110NIC(688310),
				fnameCE9855U32DQ(688311),
				fnameCE9855T32DQ(688312),
				fnameCE9855M32DQ(688313),
                fnameGM111MERGE(688314),
                fnameXH90304C(688315),
				fnameXH901032CQ4BQ(688316),
			fnameXH932064EO(688317),
			fnameXH8230128DQLC(688318),
			fnameXH9230128DQLC(688319),
			fnameXH8230128DQ(688320),
			fnameXH9230128DQ(688321),
			fnameCE6820H24S6CQ(688322),
			fnameCE9866128DQLC(688323),
			fnameCE9866128DQ(688324),
			fnameCE987564EO(688325),
			fnameCE9875128EO(688326),
			fnameXH832064EO(688327),
			fnameLQC312L1(688328),
			fnameLQC313L1(688329),
			fnameLingQu630V1(688330),
			fnameXH9330128EO(688331),
			fnameCE6857S48S6CQ(688332),
            fnameLQC315L1(688333),
			fnameLingQu620V1(688334),
			fnameCE588548T8YS(688335),
			fnameCE685548T8CQ(687000),
			fnameCE8855H32CQ8DQ(687001),
			fnameCE986664DQ(687002),
			fnameXH922064DQ(687003),
			fnameXH822064DQ(687004),
			fnameXH8330128EO(687005),
			fnameXH1680016LC(687006),
			fnameCE6855ULLM(687007),
			fnameCE6855ULL(687008),
			fnameCE986740DQ(687009),
			fnameXH922040DQ(687010),
			fnameXH822040DQ(687011),
			fnameCE986724DQ8EO(687012),
            fnameLQU520-SW1(687013),
            fnameLQU520-SW2(687014),
            fnameLQU520-2C(687015),
            fnameLQU520-8N(687016),
            fnameLQU520-1RN(687017),
            fnameLQU520-2RN(687018),
            fnameLQU520-DB(687019),
            fnameLQU520-QT(687020),
            fnameLingQu650V2(687021),
            fnameLingQu651V2(687022),
            fnameLQ620V1(687023),
            fnameCE885548CD8DQ(687024),
            fnameSMN(687025),
            fnameLQU521(687026),
            fnameLQU522(687027),
            fnameLQU523(687028),
            fnameCE9866U128DQ(687029),
            fnameCE9866M128DQ(687030),
            fnameCE9866T128DQ(687031),
            fnameCE8855HSAN40F(687032),
            fnameLingQu652V2(687033),
            fnameXH991032DQ(687034),
            fnameXH9930128DQ(687035),
            fnameLingQu550LBox(687036),
            fnameLingQu550BoxA(687037),
            fnameLingQu550BoxB(687038),

				
-- wlan:       0x000A9000~0x000A9fff(692224~696319)
               fnameES02acu(692224),               --Quidway S9300 ACU FRAME
               fnameAC6605-26-PWR(692225),          --Quidway AC6605-26-PWR Metro Service Platform
               fnameAC6005-8(692226),
               fnameACU2(692227),
               fnameAP6010SN(692228),
               fnameAP6010DN(692229),
               fnameAP6510DN(692231),
               fnameAP6610DN(692232),
               fnameAP5010DN(692233),
               fnameAP5010SN(692234),
               fnameAP7110DN(692235),
               fnameAP3010DN(692237),
               fnameAP5030DN(692238),
               fnameAP5130DN(692239),
               fnameAC6005-8-PWR(692240),
               fnameAT815SN(692243),
               fnameAP8030DN(692245),
               fnameAP8130DN(692246),
               fnameAP9130DN(692247),
               fnameAP3030DN(692249),
               fnameAP4030DN(692250),
               fnameAP4130DN(692251),
               fnameAP9131DN(692253),
               fnameAP5030DN-S(692254),
               fnameAP9132DN(692255),
               fnameAP3010DN-V2(692259),
               fnameAC6005-8-RU(692260),
               fnameAC6005-8-PWR-RU(692261),
               fnameAC6605-26-PWR-RU(692262),
               fnameACU2-RU(692263),
               fnameAC6003-8(692264),
               fnameAC6003-8-PWR(692265),
               fnameAP4030DN-E(692269),
               fnameAP7050DN-E(692274),
               fnameAD9430DN-24(692266),
               fnameAD9430DN-12(692271),
               fnameAP6150DN(692277),
               fnameAP6050DN(692273),
               fnameAP4030TN(692276),
               fnameAP4050DN-E(692275),
               fnameAP4050DN-HD(692278),
               fnameAP7050DE(692272),
               fnameAP1010SN(692280),
               fnameAP2050DN(692281),
               fnameAP2050DN-S(692282),
               fnameAP2050DN-E(692283),
               fnameAP4050DE(692284),
               fnameAP5030DN-C(692289),
               fnameAP4051DN(692290),
               fnameAP4050DN(692291),
               fnameAP4151DN(692292),
               fnameAP4051DN-S(692293),
               fnameAP4050DN-S(692294),
               fnameAP8050DN(692295),
               fnameAP8050DN-S(692296),
               fnameAP8150DN(692297),
               fnameAP1050DN-S(692298),
               fnameAD9431DN-24X(692299),
               fnameAP7152DN(692300),
               fnameAP6052DN(692301),
               fnameAP8082DN(692302),
               fnameAP8182DN(692303),
               fnameAP7052DE(692304),
               fnameAP7052TN-WI(692305),
               fnameAP8050TN-HD(692306),
               fnameAP4051TN(692307),
               fnameAP7052DN(692308),
               fnameAP5050DN-S(692309),
               fnameAP2030DN-S(692310),
               fnameAP2051DN-E(692311),
               fnameAP2051DN(692312),
               fnameAP2051DN-S(692313),
               fnameAP7060DN(692314),
               fnameAC6800V(692315),
               fnameAP100EC(692316),
               fnameAP200EC(692317),
               fnameAP300EC(692318),
               fnameAC600EC(692319),
               fnameAC600EC-PWR(692320),
               fnameAC6508(692321),
               fnameAC6805(692322),
               fnameAC6507S(692323),
               fnameAP4050DE-M(692324),
               fnameAP4050DE-M-S(692325),
               fnameWA375DD-CE(692326),
               fnameAP2051DN-L-S(692327),
               fnameAP2051DE-GP(692328),
               fnameAP4050DE-B-S(692329),
               fnameAP3050DE(692330),
               fnameWAC9600S-S(692331),
               fnameAP6750-10T(692332),
               fnameAP5760S-10(692333),
               fnameAC6508-B(692334),
               fnameAC6507S-B(692335),
               fnameAP5760-10(692336),
               fnameAirEngine9700-M(692337),
               fnameAirEngine9700D-M(692338),
               fnameAC650-32AP(692339),
               fnameAC650-64AP(692340),
               fnameAP210(692341),
               fnameAP230(692342),
               fnameAP310(692343),
               fnameAP330(692344),
               fnameAP350(692345),
               fnameAirEngine9700-M1(692346),
               fnameAirEngine6760-51EI(692355),
               fnameAirEngine6761-21T(692356),
               fnameAirEngine6761S-21T(692357),
               fnameAirEngine5761-21(692358),
               fnameAirEngine6761-21E(692359),
               fnameAirEngine5761S-21(692360),
               fnameAirEngine5761-11(692361),
               fnameAirEngine5761S-11(692362),
               fnameAirEngine5761-12W(692363),
               fnameAirEngine5761S-12W(692364),
               fnameAirEngine5761-11W(692365),
               fnameAirEngine5761S-11W(692366),
               fnameAirEngine5761-11WD(692367),
               fnameAirEngine6761-21(692368),
               fnameAirEngine5761R-11(692369),
               fnameAirEngine5761RS-11(692370),
               fnameAirEngine5761R-11E(692371),
               fnameAirEngine6761S-21(692372),
               fnameAirEngine5761S-12(692373),
               fnameAirEngine5761S-13(692374),
               fnameAirEngine5761-10W(692375),
               fnameAirEngine5761-10WD(692376),
               fnameAirEngine5761S-10W(692377),
               fnameAP5761S-10(692378),
               fnameAP5761S-10W(692379),
               fnameAirEngine5762-12SW(692380),
               fnameAirEngine5762S-12SW(692381),
               fnameAirEngine5762-12(692383),
               fnameAirEngine5762S-12(692384),
               fnameAirEngine5762S-11(692385),
               fnameAirEngine5762-15HW(692386),
               fnameAirEngine5762-13W(692387),
               fnameAirEngine5762S-13W(692388),
               fnameAirEngine5762S-11SW(692389),
               fnameAP163(692390),
               fnameAP165(692391),
               fnameAP263(692392),
               fnameAP363(692393),
               fnameAP365(692394),
               fnameAP9700D-M1(692395),
               fnameAirEngine6761-22T(692396),
               fnameAirEngine5761-12(692397),
               fnameAirEngine9701-L(692398),
               fnameAirEngine5761-11EI(692399),
               fnameAirEngine5762-16W(692400),
               fnameAirEngine9700-H(692401),
               fnameAP161(692402),
               fnameAP162(692403),
               fnameAP362(692404),
               fnameAirEngine9700D-S(692405),
               fnameAirEngine8761-X1(692406),
               fnameAirEngine5762-17W(692407),
               fnameAirEngine5762-10(692408),
               fnameAirEngine5762-10SW(692409),
               fnameAirEngine6761-23T(692410),
	           fnameAirEngine8771-X1T(692411),
	           fnameAirEngine5562-17W(692412),
	           fnameAirEngine5562-10(692413),
	           fnameAirEngine5562-10SW(692414),
               fnameAC650-128AP(692415),
               fnameAC650-256AP(692416),
	           fnameAirEngine3562-10(692417),
	           fnameAirEngine3562-10SW(692418),
               fnameAirEngine9701-L-T(692419),
	           fnameAirEngine9703-H(692420),	
               fnameAirEngine9703-S(692421),
               fnameAirEngine9703-H-T(692422), 	
               fnameAirEngine9703-S-T(692423),
               fnameAirEngine9500-LP(692424),
               fnameAirEngine5773-23HW(692425),
               fnameAirEngine5773-21(692426),
               fnameAirEngine6776-56TP(692427),
               fnameAirEngine6776-57T(692428),
               fnameAP661(692429),
               fnameAP761(692430),
	           fnameMAP3000C-CIh(692431),
               fnameMAP3000P-CIh(692432),
               fnameMAP3000P-CIs(692433),
               fnameMAP6000P-CIh(692434),
               fnameMAP6000P-CIa(692435),
	           fnameAirEngine5776-26(692436), 
	           fnameAirEngine5773-23H(692437),
               fnameAirEngine5773-22P (692438),
	           fnameAP160 (692439),
	           fnameAP361 (692440),
	           fnameAirEngine5561-12(692441),
	           fnameAirEngine5561R-11E(692442),
               fnameAirEngine5562-15HW(692443),
               fnameAirEngine6561-21T(692444),
	           fnameAirEngine9501-L(692445),
	           fnameAirEngine9500-L1P(692446),
	           fnameAirEngine6776I-X6TH(692447),
               fnameAirEngine5773-25HW(692448),
               fnameAirEngine5773-23WP(692449),
               fnameAirEngine5576-26(692450),
               fnameAirEngine6576-57T(692451),
               fnameAirEngine6776-58Ti(692452),
               fnameAirEngine5573-21(692453),
               fnameAirEngine3573-21(692454),
               fnameAirEngine6576-56TP(692455),
               fnameAP362E(692456),
               fnameAP265E(692458),
               fnameAP266(692459),
               fnameAP162E(692460),
               fnameAirEngine5763-11W(692461),
               fnameAirEngine9503-S(692462),
               fnameAC650-512AP(692463),
	           fnameAirEngine5573-23H(692464),
               fnameAirEngine5573-23HW(692465),
	           fnameAirEngine9701S-L(692466),
               fnameAP673(692467),
	           fnameAirEngine6776I-X7TH(692468),
               fnameAP371(692469),
			   fnameAirEngine5762C-10-V2(692470),
               fnameAirEngine5562-10-V2(692471),
               fnameAirEngine3562-10-M(692472),
               fnameAirEngine3562-10-T(692473),
               fnameAirEngine5762C-10SW-V2(692474),
               fnameAirEngine5562-10SW-V2(692475),
               fnameAirEngine3562-10SW-M(692476),
               fnameAirEngine3562-10SW-T(692477),
               fnameeKitEngine5763S-11(692478),
               fnameeKitEngine5763S-12(692479),
               fnameAP361E(692480),
               fnameeKitEngine5763S-12SW(692481),
               fnameeKitEngine6760S-56(692482),
			   fnameAirEngine5773-23W(692483),
               fnameAirEngine6776I-X6ETH(692484),
               fnameAirEngine5573-23W(692485),
               fnameAirEngine5576I-X6EH(692486),
               fnameeKitEngine5773S-21(692487),
               fnameeKitEngine5776RS-X6(692488),
               fnameAP673E(692489),
               fnameAP572(692490),
               fnameAP772(692491),
               fnameAP772E(692492),
               fnameAirEngine6776-X6H(692493),
               fnameAirEngine6776-X6ETH(692494),
               fnameAirEngine5776-56T(692495),
               fnameAirEngine5776I-X6H(692496),
               fnameAirEngine5776I-X6EH(692497),
               fnameAirEngine6776-58TI-K(692498),
               fnameAirEngine6776I-X6ETH-K(692499),
               fnameAirEngine5762C-17W-V2(692500),
               fnameAirEngine5562-17W-V2(692501),
	           fnameAirEngine5776I-X7H(692502),
               fnameAP761E(692503),            
               fnameAirEngine5776-57T(692504), 
               fnameAirEngine5776-57(692505), 
	           fnameAP271E(692506),
               fnameAirEngine5773H-21(692507),
               fnameAirEngine8776-X7ET-T(692508),
               fnameAirEngine8776-X7F-T(692509),
               fnameAirEngine8776-X7T-T(692510),
               fnameAirEngine8776-X6THP(692511),
               fnameAirEngine5776E-26(692512),   
               fnameAirEngine5773E-21(692513),
               fnameAirEngine6776-26HD(692514),
               fnameAirEngine6776-26HD-X773(692515),
               fnameAirEngine5773-21HW(692516),
               fnameAP771(692517),
               fnameAirEngine5773E-23W(692518), 
               fnameAirEngine5773E-25HW(692519), 
               fnameAirEngine5773E-23HW(692520), 
               fnameAirEngine5776I-X7TH(692521), 
               fnameAirEngine7070-01-M(692524),  
               fnameAirEngine7070I-01-M(692525), 
               fnameAirEngine7070I-01-MS(692526),
               fnameAirEngine5773I-21(692527),   
               fnameAirEngine3573I-21-M(692528), 
               fnameAirEngine3576-56TP-M(692529),
               fnameAirEngine5776I-X7EH(692532),
               fnameAirEngine8776I-X6ETHP-T(692534),
               fnameAirEngine8776-X5F-T(692536),
               fnameAirEngine6776-X7TH(692540),
               fnameAP673H(692545),
               fnameAP361H(692547),
               fnameAP362H(692548),
			   
-- T8010:      0x000AA200~0x000AA7FF(696832~698367)
               fnameBT81BP2HT8010(696832),   --Frame BT81BP2H of the T8010 bits device.
	       fnameBT82BP2HT8010(696833),   --Frame BT82BP2H of the T8010 bits device.

-- Frame Type for iODN products: range: 0x000B0000~0x000BFFFF  720,896~786,431
                fnameMPU3101B-AC-1U(720898),              --MPU3101B-AC-1U
                fnameMPU3101C-AC-1U(720899),              --MPU3101C-AC-1U
                fnameMPU3101D-AC-1U(720900),              --MPU3101D-AC-1U
                fnameMPU3101B-DC-1U(720901),              --MPU3101B-DC-1U
                fnameMPU3101C-DC-1U(720902),              --MPU3101C-DC-1U
                fnameMPU3101D-DC-1U(720903),              --MPU3101D-DC-1U
                fnameAF11FPUA(721153),                    --AF11FPUA
                fnameAF11FPUAT(721154),                   --AF11FPUAT
                fnameGPX147-iMODF-6U(721155),             --GPX147-iMODF-6U
                fnameAF11FATA(721156),                    --AF11FATA
                fnameAF11FATC(721409),                    --AF11FATC
                fnameAF11FATB(721410),                    --AF11FATB

                fnameGPX147-iODF3101(729089),             --GPX147-iODF3101
                fnameGXF147-iFDT3101(729090),             --GXF147-iFDT3101
                fnameGXF147-iFDT3101D(729091),            --GXF147-iFDT3101D
                fnameGXF147-FDT2107D(729092),             --GXF147-FDT2107D
                fnameGPX147-iFAT3101(729093),             --GPX147-iFAT3101
                fnameGPX147-iFAT3102-12(729094),          --GPX147-iFAT3102-12
                fnameGPX147-iFAT3102(729095),             --GPX147-iFAT3102
                fnameGPX147-ODF5101-CH2-1200mm(729096),   --GPX147-ODF5101-CH2-1200mm
                fnameGPX147-ODF5101-FH2-1200mm(729097),   --GPX147-ODF5101-FH2-1200mm
                fnameGPX147-ODF5101-CH2-900mm(729098),    --GPX147-ODF5101-CH2-900mm
                fnameGPX147-ODF5101-FH2-900mm(729099),    --GPX147-ODF5101-FH2-900mm
                fnameGPX147-ODF5101-CH9(729100),          --GPX147-ODF5101-CH9
                fnameGPX147-ODF5101-FH9(729101),          --GPX147-ODF5101-FH9
                fnameGXF147-iFDT3101D-A(729102),          --GXF147-iFDT3101D-A
                fnameGXF147-iFDT3103D-432(729104),        --GXF147-iFDT3103D-432
                fnameGPX147-iFAT3103T-16(729345),         --GPX147-iFAT3103T-16
                fnameGPX147-iFAT3103T-24(729346),         --GPX147-iFAT3103T-24
                fnameGPX147-iFAT3105T-32(729347),         --GPX147-iFAT3105T-32
                fnameGPX147-iFAT3105T-36(729348),         --GPX147-iFAT3105T-36
                fnameGPX147-iFAT3101TD-32(729349),        --GPX147-iFAT3101TD-32
                fnameGPX147-iFAT3101TD-36(729350),        --GPX147-iFAT3101TD-36
                fnameGPX147-iFAT3103TD-96-F(729351),      --GPX147-iFAT3103TD-96-F
                fnameGPX147-iFAT3103TD-96-P(729352),      --GPX147-iFAT3103TD-96-P

                fnameGPX147-SR5101-5U(737281),            --GPX147-SR5101-5U
                fnameGPX147-SR5101-5U-2(737282),          --GPX147-SR5101-5U-2
                fnameGPX147-SR5102-5U(737283),            --GPX147-SR5102-5U
                fnameGXF147-FAT5201T(737284),             --GXF147-FAT5201T
                fnameEDFABP21(737285),                    --EDFA3220D
 --hwRPS
                fnameCPF318(786432),               --The RPS's Power Frame backplane.
                fnameCFS01(786433),                --The RPS's Fan Frame.
                fnameCPF104(786434),               --The RPS's with BT-C Power Frame backplane.
                fnameCFS02(786435),                --The RPS's with BT-C Fan Frame.
                fnameETP4830-A1(786436),           --The RPS's with AC-DC System Frame.
                fnameETP4890-A2(786437),           --The RPS's with AC-DC System Frame.
                fnameETP48150-A3(786438),          --The RPS's with AC-DC System Frame.
                fnameRPF106(786439),               --The RPS's with RTF-V Power Frame backplane.


-- Frame Type for hs security products:   range: 0x00ff1000~0x00ff1fff  16715776~16719871
                fnameSU1Z21UHA(16715776),                   -- USG2200,SU1Z21UHA,USG2210 Host
                fnameSU1Z21UHB(16715777),                   -- USG2200,SU1Z21UHB,USG2220 Host
                fnameSU1Z21UHC(16715778),                   -- USG2200,SU1Z21UHC,USG2230 Host
                fnameSU1Z21UHD(16715779),                   -- USG2200,SU1Z21UHD,USG2250 Host
                fnameSU1Z22UHA(16715780),                   -- USG2200,SU1Z22UHA,USG2210 Host,HuaweiSymantec Overseas
                fnameSU1Z22UHB(16715781),                   -- USG2200,SU1Z22UHB,USG2220 Host,HuaweiSymantec Overseas
                fnameSU1Z22UHC(16715782),                   -- USG2200,SU1Z22UHC,USG2230 Host,HuaweiSymantec Overseas
                fnameSU1Z22UHD(16715783),                   -- USG2200,SU1Z22UHD,USG2250 Host,HuaweiSymantec Overseas
                fnameFWGZ21UHA(16715784),                   -- Quidway Eudemon,FWGZ21UHA,E200E-C Host
                fnameFWGZ21UHD(16715785),                   -- Quidway Eudemon,FWGZ21UHD,E200E-F Host
                fnameSRGZ2020(16715786),                    -- SRG20 Secure Routing Gateway,SRGZ2020,SRG20-20 AC Host
                fnameSRGZ2021(16715787),                    -- SRG20 Secure Routing Gateway,SRGZ2021,SRG20-21 AC Host
                fnameSRGZ2030(16715788),                    -- SRG20 Secure Routing Gateway,SRGZ2030,SRG20-30 AC Host
                fnameSRGZ2031(16715789),                    -- SRG20 Secure Routing Gateway,SRGZ2031,SRG20-31 AC Host
                fnameSRGZ2020IE(16715790),                      -- SRG20 Secure Routing Gateway,SRGZ2020IE,SRG20-20 AC Host
                fnameSRGZ2021IE(16715791),                      -- SRG20 Secure Routing Gateway,SRGZ2021IE,SRG20-21 AC Host
                fnameSRGZ2030IE(16715792),                      -- SRG20 Secure Routing Gateway,SRGZ2030IE,SRG20-30 AC Host
                fnameSRGZ2031IE(16715793),                      -- SRG20 Secure Routing Gateway,SRGZ2031IE,SRG20-31 AC Host
                fnameSU0Z11UHB(16715794),                       -- USG2100-SU0Z11UHB-USG2130 Host,HuaweiSymantec Overseas
                fnameSU0Z13UHB(16715795),                       -- USG2100-SU0Z13UHB-USG2160 Host,HuaweiSymantec Overseas
                fnameSRGZ23UHT(16715796),                       -- SRG3260,SRGZ23UHT,SRG3260 Host,with HS General Security Platform Software
                fnameSU2Z12UAH(16715797),                       -- USG5100,SU2Z12UAH,USG5120 AC Host,with HS General Security Platform Software
                fnameSU2Z12UDH(16715798),                       -- USG5100,SU2Z12UDH,USG5120 DC Host,with HS General Security Platform Software
                fnameSU2Z13UHT(16715799),                       -- USG5100,SU2Z13UHT,USG5150 Host,with HS General Security Platform Software
                fnameSU2Z22UAH(16715800),                       -- USG5100,SU2Z22UAH,USG5120BSR AC Host,with HS General Security Platform Software
                fnameSU2Z22UDH(16715801),                       -- USG5100,SU2Z22UDH,USG5120BSR DC Host,with HS General Security Platform Software
                fnameSU2Z23UHT(16715802),                       -- USG5100,SU2Z23UHT,USG5150BSR Host,with HS General Security Platform Software
                fnameSRGZ12UAH(16715803),                       -- SRG3230,SRGZ12UAH,SRG3230 AC Host,with HS General Security Platform Software
                fnameSRGZ22UAH(16715804),                       -- SRG3240,SRGZ22UAH,SRG3240 AC Host,with HS General Security Platform Software
                fnameSRGZ22UDH(16715805),                       -- SRG3240,SRGZ22UDH,SRG3240 DC Host,with HS General Security Platform Software
                fnameSRGZ13UHT(16715806),                       -- SRG3250,SRGZ13UHT,SRG3250 Host,with HS General Security Platform Software
                fnameSU1ZAH10FE(16715807),          -- USG2200,SU1ZAH10FE,USG2210 AC Basic Configuration,(2GE,10FE,with 2*5FE MIC),with HS General Security Platform Software
                fnameSU2Z42UAH(16715808),           -- USG5100,SU2Z42UAH,USG5120BSR AC Host,with HS General Security Platform Software
                fnameSU2Z43UHTO1(16715809),         -- USG5100,SU2Z43UHT,USG5150BSR Host,with HS General Security Platform Software  Label duplicated with fnameSU2Z43UHT(16715811) and add 'O1'
        fnameSU2Z43UHTO2(16715810),         -- USG5500 1U Frame Unit  Label duplicated with fnameSU2Z43UHT(16715811) and add 'O2'
        fnameSU2Z43UHT(16715811),           -- USG5500 3U Frame Unit
        fnameSUAB13UAC(16715812),               -- USG6600 SUAB13UAC  Frame Unit
        fnameNGFW1UL2(16715813),                    -- USG3600 L2 Frame Unit
        fnameNGFW1UL1(16715814),                    -- USG3600 L1 Frame Unit
        fnameNGFWSSM(16715815),                     -- NGFW SSM Frame Unit
		fnameNIP6860-DC (16715816),       --NIP6860 DC Basic Configuration(include X8 DC Chassis,2*SRU,1*SFU) (0x00ff1028)
		fnameNIP6800-X8-CHAS-DC (16715817),       --NIP6800 Integrated Chassis Components,14U(Including 4 DC Power)  (0x00ff1029)
-- CCU Frame of shelf Management: from 0xff2000 to 0x0xff3000
                fnameCCU(16719872),                            --CCU Frame

-- Virtuil Frame of Net Management: from 0X70000000
                fnameRF32(1879048192),                     --Virtuil Remote Frame,32 Slots
                fnameRF64(1879048193),                     --Virtuil Remote Frame,64 Slots
                fnamePTN6900-M2K(675945),                  --Quidway PTN6900-M2K FRAME for V8R11C00
                fname8090NE40E-M8A-AC(675946),             --Quidway NE40E-M8A-AC FRAME for V8R10C10
                fname8090NE40E-M8A-DC(675947),             --Quidway NE40E-M8A-DC FRAME for V8R10C10
                fname8090NE40E-M16A(675948),               --Quidway NE40E-M16A FRAME for V8R10C10
                fname8031CX600-M2K-B(675949),              --Quidway CX600-M2K-B FRAME for V8R11C00
                fname8090NE40E-M2K-B(675950),              --Quidway NE40E-M2K-B FRAME for V8R11C00
                fname8090CX6602-B(675951),                 --Quidway CX6602-B FRAME for V8R11C00
                fnamePTN6900-M2K-B(675952),                --Quidway PTN6900-M2K-B FRAME for V8R11C00
                fname8031CX600-F1A-14H24Q(675953),                --Quidway CX600-F1A-14H24Q FRAME for V8R11C00
                fname8090NE40E-F1A-14H24Q(675954),                --Quidway NE40E-F1A-14H24Q FRAME for V8R11C00
                fname8090CX6601-14H24Q(675955),                   --Quidway CX6601-14H24Q FRAME for V8R11C00
                fnamePTN6900-F1A-14H24Q(675956),                  --Quidway PTN6900-F1A-14H24Q FRAME for V8R11C00
                fname8031CX600-F1A-8H20Q(675964),                --Quidway CX600-F1A-8H20Q FRAME for V8R11C10
                fname8090NE40E-F1A-8H20Q(675965),                --Quidway NE40E-F1A-8H20Q FRAME for V8R11C10
                fname8090PTN6900-F1A-8H20Q(675966),              --Quidway PTN6900-F1A-8H20Q FRAME for V8R11C10
                fname8090CX600-X2-M16B(675957),            --Quidway CX600-M2K-B FRAME for V8R11C00
                fname8090NE40E-X2-M16B(675958),            --Quidway NE40E-X2-M16B FRAME for V8R11C00
                fname8090NE20E-S16B(675959),               --Quidway NE20E-S16B FRAME for V8R11C00
                fname8090PTN6900-2-M16B(675960),           --Quidway PTN6900-2-M16B FRAME for V8R11C00
                fname8031CX600-M2K-DC(580932),             --Quidway CX600-M2K-DC FRAME for V8R11C10
                fname8031CX600-M2K-B-DC(580940),           --Quidway CX600-M2K-B-DC FRAME for V8R11C10
                fnamePTN6900-M2K-DC(580936),               --Quidway PTN6900-M2K-DC FRAME for V8R11C10
                fnamePTN6900-M2K-B-DC(580944),             --Quidway PTN6900-M2K-B-DC FRAME for V8R11C10
                fname8090CX6602-B-DC(580946),              --Quidway CX6602-B-DC FRAME for V8R11C10
                fname8090CX6602-DC(580938),                --Quidway CX6602-DC FRAME for V8R11C10
                fname8090NE40E-M2K-B-DC(580942),           --Quidway NE40E-M2K-B-DC FRAME for V8R11C10
                fname8090NE40E-M2K-DC(580934),             --Quidway NE40E-M2K-DC FRAME for V8R11C10
                fnamePTN6900-M2K-AC(580935),               --Quidway PTN6900-M2K-AC FRAME for V8R11C10
                fname8031CX600-M2K-AC(580931),             --Quidway CX600-M2K-AC FRAME for V8R11C10
                fname8031CX600-M2K-B-AC(580939),           --Quidway CX600-M2K-B-AC FRAME for V8R11C10
                fname8090CX6602-AC(580937),                --Quidway CX6602-AC FRAME for V8R11C10
                fnamePTN6900-M2K-B-AC(580943),             --Quidway PTN6900-M2K-B-AC FRAME for V8R11C10
                fname8090NE40E-M2K-B-AC(580941),           --Quidway NE40E-M2K-B-AC FRAME for V8R11C10
                fname8090NE40E-M2K-AC(580933),             --Quidway NE40E-M2K-AC FRAME for V8R11C10
                fname8090CX6602-B-AC(580945),              --Quidway CX6602-B-AC FRAME for V8R11C10
                fname8031CX600-M2E-AC(580911),             --Quidway CX600-M2E-AC FRAME for V8R11C10
                fname8090NE40E-M2E-AC(580913),             --Quidway NE40E-M2E-AC FRAME for V8R11C10
                fnameNE20E-S2E-AC(580917),                 --Quidway NE20E-S2E-AC FRAME for V8R11C10
                fnamePTN6900-M2E-AC(580915),               --Quidway PTN6900-M2E-AC FRAME for V8R11C10
                fname8031CX600-M2E-DC(580912),             --Quidway CX600-M2E-DC FRAME for V8R11C10
                fname8090NE40E-M2E-DC(580914),             --Quidway NE40E-M2E-DC FRAME for V8R11C10
                fnameNE20E-S2E-DC(580918),                 --Quidway NE20E-S2E-DC FRAME for V8R11C10
                fnamePTN6900-M2E-DC(580916),               --Quidway PTN6900-M2E-DC FRAME for V8R11C10
                fname8031CX600-M2F-AC(580919),             --Quidway CX600-M2F-AC FRAME for V8R11C10
                fname8090NE40E-M2F-AC(580921),             --Quidway NE40E-M2F-AC FRAME for V8R11C10
                fnameNE20E-S2F-AC(580925),                 --Quidway NE20E-S2F-AC FRAME for V8R11C10
                fnamePTN6900-M2F-AC(580923),               --Quidway PTN6900-M2F-AC FRAME for V8R11C10
                fname8031CX600-M2F-DC(580920),             --Quidway CX600-M2F-DC FRAME for V8R11C10
                fname8090NE40E-M2F-DC(580922),             --Quidway NE40E-M2F-DC FRAME for V8R11C10
                fnameNE20E-S2F-DC(580926),                 --Quidway NE20E-S2F-DC FRAME for V8R11C10
                fnamePTN6900-M2F-DC(580924),               --Quidway PTN6900-M2F-DC FRAME for V8R11C10
                fname8031CX600-M2H-AC(580927),             --Quidway CX600-M2H-AC FRAME for V8R11C10
                fname8090NE40E-M2H-AC(580929),             --Quidway NE40E-M2H-AC FRAME for V8R11C10
                fname8031CX600-M2H-DC(580928),             --Quidway CX600-M2H-DC FRAME for V8R11C10
                fname8090NE40E-M2H-DC(580930),             --Quidway NE40E-M2H-DC FRAME for V8R11C10
                fname8090CX600-X1-M4-AC(537991),           --Quidway CX600-X1-M4-AC FRAME for V8R11C10
                fname8090CX600-X1-M4-DC(537992),           --Quidway CX600-X1-M4-DC FRAME for V8R11C10
                fname8090CX600-M4-AC(537993),              --Quidway CX600-M4-AC FRAME for V8R11C10
                fname8090CX600-M4-DC(537994),              --Quidway CX600-M4-DC FRAME for V8R11C10
                fname8090NE40E-X1-M4-AC(537995),           --Quidway NE40E-X1-M4-AC FRAME for V8R11C10
                fname8090NE40E-X1-M4-DC(537996),           --Quidway NE40E-X1-M4-DC FRAME for V8R11C10
                fnameNETENGINE-8000-M8-DC(537997),      --NETENGINE-8000-M8-DC (fnameNETENGINE-8000-M8-DC)
                fnameNETENGINE-8000-NTN(685653),      --NETENGINE-8000-NTN
                fnamePTN6900-2-M8C-DC(537998),               --PTN6900-2-M8C-DC(fnamePTN6900-2-M8C-DC)
                fnameNETENGINE-8000-F1A-8H20Q(688338),          --Quidway fnameNETENGINE-8000-F1A-8H20Q FRAME for V8R12C00
                fnameNETENGINE-8000E-F1A(688790),          --Quidway fnameNETENGINE-8000E-F1A FRAME for V8R24C10
                fnameNETENGINE-8000-F1A-8H20Q-AC(688336),          --Quidway fnameNETENGINE-8000-F1A-8H20Q-AC FRAME for V8R12C00
                fnameNETENGINE-8000-F1A-8H20Q-DC(688337),          --Quidway fnameNETENGINE-8000-F1A-8H20Q-DC FRAME for V8R12C00
                fnameNETENGINE-8000-F2C(688889),                 --Quidway fnameNETENGINE-8000-F2C  FRAME for V8R24C00
                fnameNETENGINE-8000E-F2C(688909),                 --Quidway fnameNETENGINE-8000E-F2C  FRAME for V8R24C00
                fnameNETENGINE-8000-F2D(688950),     --Quidway fnameNETENGINE-8000-F2D  FRAME for V8R25C00
                fnameNETENGINE-8000E-F2D(688951),     --Quidway fnameNETENGINE-8000E-F2D  FRAME for V8R25C00
                fnameNETENGINE-XH871(688921),        --Quidway fnameNETENGINE-XH871  FRAME for V8R25C10
                fnameNETENGINE-8000-F2C-P(688961),   --Quidway fnameNETENGINE-8000-F2C-P  FRAME for V8R25C10
                fnameNETENGINE-8000E-F2C-P(688962),  --Quidway fnameNETENGINE-8000E-F2C-P  FRAME for V8R25C10
                fnameNETENGINE-8000-F1A-8H20Q-E(688589),         --Quidway fnameNETENGINE-8000-F1A-8H20Q-E FRAME for V8R13C00
                fnameNETENGINE-8000-F2A-8K36H(688643),            --Quidway fnameNETENGINE-8000-F2A-8K36H FRAME for V8R21C00
                fnameNETENGINE-8000-F2A-8K36H-AC(688644),         --Quidway fnameNETENGINE-8000-F2A-8K36H-AC FRAME for V8R21C00
                fnameNETENGINE-8000-F2A-8K36H-DC(688645),         --Quidway fnameNETENGINE-8000-F2A-8K36H-DC FRAME for V8R21C00
                fnameNETENGINE-8000-F8(688437),           -- Quidway fnameNETENGINE-8000-F8 FRAME for V8R22C00
                fnameNETENGINE-8000E-F8(688438),          -- Quidway fnameNETENGINE-8000E-F8 FRAME for V8R22C00
				fnameNETENGINE-8000E-F8A(688700),         -- Quidway fnameNETENGINE-8000E-F8A FRAME for V8R24C10
                fnameNETENGINE-8000E-F8-Z(688439),        -- Quidway fnameNETENGINE-8000E-F8-Z FRAME for V8R22C00
                fnameNETENGINE-8000-F1A-C(688778),         --Quidway fnameNETENGINE-8000-F1A-C FRAME for V8R23C10
                fnameNETENGINE-8000E-F1A-C(688791),         --Quidway fnameNETENGINE-8000E-F1A-C FRAME for V8R24C10
                fnameNETENGINE-8000-M14-AC(688339),         --Quidway fnameNETENGINE-8000-M14-AC FRAME for V8R12C00
                fnameNETENGINE-8000-M14-DC(688340),         --Quidway fnameNETENGINE-8000-M14-DC FRAME for V8R12C00
                fnameNETENGINE-8000-M14-2AC(688343),        --Quidway fnameNETENGINE-8000-M14-2AC FRAME for V8R12C10
                fnameNETENGINE-8000-M14-2AC-L(688377),        --Quidway fnameNETENGINE-8000-M14-2AC-L FRAME for V8R13C00
                fnameNETENGINE-8000-M14-2AC-R(688378),        --Quidway fnameNETENGINE-8000-M14-2AC-R FRAME for V8R13C00
                fnameNETENGINE-8000-M14-4AC(688344),        --Quidway fnameNETENGINE-8000-M14-4AC FRAME for V8R12C10
                fnameNETENGINE-XH16000-M14-DC(688914),       --Quidway fnameNETENGINE-XH16000-M14-DC FRAME for V8R24C10
                fnameNETENGINE-XH16000-M14-2AC(688915),      --Quidway fnameNETENGINE-XH16000-M14-2AC FRAME for V8R24C10
                fnameNETENGINE-XH16100-M14-DC(690000),       --Quidway fnameNETENGINE-XH16100-M14-DC FRAME for V8R25C00
                fnameNETENGINE-XH16100-M14-2AC(690001),       --Quidway fnameNETENGINE-XH16100-M14-2AC FRAME for V8R25C00
                fnameNETENGINE-XH16200-M14-DC(690002),       --Quidway fnameNETENGINE-XH16200-M14-DC FRAME for V8R25C00
                fnameNETENGINE-XH16200-M14-2AC(690003),       --Quidway fnameNETENGINE-XH16200-M14-2AC FRAME for V8R25C00
                fnameNETENGINE-XH16000E-M14-DC(210014),      --Quidway fnameNETENGINE-XH16000E-M14-DC FRAME for V8R25C00
                fnameNETENGINE-XH16000E-M14-2AC(210015),      --Quidway fnameNETENGINE-XH16000E-M14-2AC FRAME for V8R25C00
                fnameNETENGINE-8000-M8-AC(538022),          --NETENGINE-8000-M8-AC (fnameNETENGINE-8000-M8-AC)
                fnamePTN6900-2-M8C-AC(538023),              --PTN6900-2-M8C-AC(fnamePTN6900-2-M8C-AC)
                fnameNETENGINE-8000-M1A-AC(688341),         --Quidway fnameNETENGINE-8000-M1A-AC FRAME for V8R12C00
                fnameNETENGINE-8000-M1A-DC(688342),         --Quidway fnameNETENGINE-8000-M1A-DC FRAME for V8R12C00
                fnameNETENGINE-8000-M1C-AC(226115),        --Quidway fnameNETENGINE-8000-M1C-AC FRAME for V8R13C00
                fnameNETENGINE-8000-M1C-DC(226114),        --Quidway fnameNETENGINE-8000-M1C-DC FRAME for V8R13C00
                fnameNETENGINE-8000E-M1A-AC(688710),         --Quidway fnameNETENGINE-8000-M1A-AC FRAME for V8R24C00
                fnameNETENGINE-8000E-M1A-DC(688711),         --Quidway fnameNETENGINE-8000-M1A-DC FRAME for V8R24C00
                fnameNETENGINE-8000E-M1C-AC(688712),         --Quidway fnameNETENGINE-8000-M1C-AC FRAME for V8R24C00
                fnameNETENGINE-8000E-M1C-DC(688713),         --Quidway fnameNETENGINE-8000-M1C-DC FRAME for V8R24C00
                fnameNETENGINE-8000E-M1D-AC(688714),         --Quidway fnameNETENGINE-8000-M1D-AC FRAME for V8R24C00
                fnameNETENGINE-8000E-M1D-DC(688715),         --Quidway fnameNETENGINE-8000-M1D-DC FRAME for V8R24C00
                fnameNETENGINE-6000-X4-DC(688716),           --Quidway fnameNETENGINE-6000-X4-DC FRAME for V8R25C00
                fnameNETENGINE-6000-X4-HVDC(688717),         --Quidway fnameNETENGINE-6000-X4-HVDC FRAME for V8R25C00
                fnameNETENGINE-6000-X8-DC(688718),           --Quidway fnameNETENGINE-6000-X8-DC FRAME for V8R25C00
                fnameNETENGINE-6000-X8-HVDC(688719),         --Quidway fnameNETENGINE-6000-X8-HVDC FRAME for V8R25C00
                fnameNE40E-X2-M14-AC(688351),         --Quidway fnameNE40E-X2-M14-AC FRAME for V8R12C00
                fnameNE40E-X2-M14-DC(688352),         --Quidway fnameNE40E-X2-M14-DC FRAME for V8R12C00
                fnamePTN6900-2-M14-AC(688353),         --Quidway fnamePTN6900-2-M14-AC FRAME for V8R12C00
                fnamePTN6900-2-M14-DC(688354),         --Quidway fnamePTN6900-2-M14-DC FRAME for V8R12C00
                fnameNETENGINE-8000-X4-HVDC(688355),         --Quidway fnameNETENGINE-8000-X4-HVDC FRAME for V8R12C00
                fnameNETENGINE-8000-X4-DC(688356),         --Quidway fnameNETENGINE-8000-X4-DC FRAME for V8R12C00
                fnameNETENGINE-8000-X8-HVDC(688357),         --Quidway fnameNETENGINE-8000-X8-HVDC FRAME for V8R12C00
                fnameNETENGINE-8000-X8-DC(688358),         --Quidway fnameNETENGINE-8000-X8-DC FRAME for V8R12C00
				fnameNETENGINE-XH16000-X8-DC(688689),      -- Quidway fnameNETENGINE-XH16000-X8-DC for V8R24C00
                fnameNETENGINE-XH16000-X8-HVDC(688690),    -- Quidway fnameNETENGINE-XH16000-X8-HVDC for V8R24C00
                fnameNETENGINE-XH16000E-X8-DC(688687),      -- Quidway fnameNETENGINE-XH16000E-X8-DC for V8R24C00
                fnameNETENGINE-XH16000E-X8-HVDC(688688),    -- Quidway fnameNETENGINE-XH16000E-X8-HVDC for V8R24C00
                fnameNETENGINE-XH16100-X8-DC(688720),   -- Quidway fnameNETENGINE-XH16100-X8-DC FRAME for V8R25C00
                fnameNETENGINE-XH16100-X8-HVDC(688721), -- Quidway fnameNETENGINE-XH16100-X8-HVDC FRAME for V8R25C00
                fnameNETENGINE-XH16200-X8-DC(688722),   -- Quidway fnameNETENGINE-XH16200-X8-DC FRAME for V8R25C00
                fnameNETENGINE-XH16200-X8-HVDC(688723), -- Quidway fnameNETENGINE-XH16200-X8-HVDC FRAME for V8R25C00
                fnameNE40E-X2-M14-2AC(688359),     -- Quidway fnameNE40E-X2-M14-2AC FRAME for V8R21C00
                fnameNE40E-X2-M14-2AC-L(688379),     -- Quidway fnameNE40E-X2-M14-2AC-L FRAME for V8R13C00
                fnameNE40E-X2-M14-2AC-R(688380),     -- Quidway fnameNE40E-X2-M14-2AC-R FRAME for V8R13C00
                fnameNE40E-X2-M14-4AC(688360),     -- Quidway fnameNE40E-X2-M14-4AC FRAME for V8R21C00
                fnamePTN6900-2-M14-2AC(688361),     -- Quidway fnamePTN6900-2-M14-2AC FRAME for V8R21C00
                fnamePTN6900-2-M14-2AC-L(688381),     -- Quidway fnamePTN6900-2-M14-2AC FRAME for V8R13C00
                fnamePTN6900-2-M14-2AC-R(688382),     -- Quidway fnamePTN6900-2-M14-2AC FRAME for V8R13C00
                fnamePTN6900-2-M14-4AC(688362),     -- Quidway fnamePTN6900-2-M14-4AC FRAME for V8R21C00
                fnameNETENGINE-8000-X16(688393),           --Quidway fnameNETENGINE-8000-X16 FRAME for V8R13C00
                fnameNETENGINE-8000-X16-DC(688394),        --Quidway fnameNETENGINE-8000-X16-DC FRAME for V8R13C00
                fnameNETENGINE-8000-X16-HVDC(688395),      --Quidway fnameNETENGINE-8000-X16-HVDC FRAME for V8R13C00
                fnameNETENGINE-8000E-X4-DC(688558),        --Quidway fnameNETENGINE-8000E-X4-DC for V8R13C00
                fnameNETENGINE-8000E-X4-HVDC(688559),      --Quidway fnameNETENGINE-8000E-X4-DC for V8R13C00
                fnameNETENGINE-8000E-X8-DC(688560),        --Quidway fnameNETENGINE-8000E-X4-HVDC for V8R13C00
                fnameNETENGINE-8000E-X8-HVDC(688561),      --Quidway fnameNETENGINE-8000E-X4-HVDC for V8R13C00
				fnameNETENGINE-8000E-X16-DC(688566),        --Quidway fnameNETENGINE-8000E-X16-DC for V1R21C10
				fnameNETENGINE-8000E-X16-HVDC(688567),      --Quidway fnameNETENGINE-8000E-X16-HVDC for V1R21C10
                fnameNETENGINE-8000S-X4-DC(688562),        --Quidway fnameNETENGINE-8000E-X8-DC for V8R13C00
                fnameNETENGINE-8000S-X4-HVDC(688563),      --Quidway fnameNETENGINE-8000E-X8-DC for V8R13C00
                fnameNETENGINE-8100-X8-DC(688564),        --Quidway fnameNETENGINE-8100-X8-HVDC for V8R13C00
                fnameNETENGINE-8100-X8-HVDC(688565),      --Quidway fnameNETENGINE-8100-X8-HVDC for V8R13C00
				fnameNETENGINE-8100-X8-12T8-DC(689564),   --Quidway fnameNETENGINE-8100-X8-12T8-DC for V8R24C00
				fnameNETENGINE-8800-X4-DC(688701),      --Quidway fnameNETENGINE-8800-X4-DC for V8R23C10
                fnameNETENGINE-8800-X8-DC(688702),      --Quidway fnameNETENGINE-8800-X8-DC for V8R23C10
                fnameNETENGINE-8800-X16-DC(688703),      --Quidway fnameNETENGINE-8800-X16-DC for V8R23C10
                fnameNETENGINE-8800-X4-HVDC(688704),      --Quidway fnameNETENGINE-8800-X4-HVDC for V8R23C10
                fnameNETENGINE-8800-X8-HVDC(688705),      --Quidway fnameNETENGINE-8800-X8-HVDC for V8R23C10
                fnameNETENGINE-8800-X16-HVDC(688706),      --Quidway fnameNETENGINE-8800-X16-HVDC for V8R23C10
                fnameNETENGINE-8000-M6(225352),          --Quidway fnameNETENGINE-8000-M6 FRAME for V8R12C10
                fnameNETENGINE-8000-M6-AC(225353),          --Quidway fnameNETENGINE-8000-M6-AC FRAME for V8R12C00
                fnameNETENGINE-8000-M6-DC(225354),          --Quidway fnameNETENGINE-8000-M6-DC FRAME for V8R12C00
				fnameNETENGINE-8000E-M6-AC(225356),     -- Quidway fnameNETENGINE-8000E-M6-AC FRAME for V8R24C00
                fnameNETENGINE-8000E-M6-DC(225357),     -- Quidway fnameNETENGINE-8000E-M6-DC FRAME for V8R24C00
                fnameNETENGINE-8000-M14K-4AC(688400),       -- NETENGINE-8000-M14K-4AC (fnameNETENGINE-8000-M14K-4AC)
                fnameNETENGINE-8000-M14K-DC(688401),    -- NETENGINE-8000-M14K-DC (fnameNETENGINE-8000-M14K-DC)
                fnameNETENGINE-8000-M14K-2AC(688402),    -- NETENGINE-8000-M14K-2AC (fnameNETENGINE-8000-M14K-2AC)
                fnameNETENGINE-XH12000-X16-DC(688788),      -- Quidway fnameNETENGINE-XH12000-X16-DC for V8R24C10
				fnameNETENGINE-XH12000-X16-HVDC(688789),    -- Quidway fnameNETENGINE-XH12000-X16-HVDC for V8R24C10
                fnameNETENGINE-8000-M8K(688403),        -- NETENGINE-8000-M8K (fnameNETENGINE-8000-M8K)
                fnameNETENGINE-8000-M8K-DC(688404),     -- NETENGINE-8000-M8K-DC (fnameNETENGINE-8000-M8K-DC)
                fnameNETENGINE-8000-M8K-AC(688405),     -- NETENGINE-8000-M8K-AC (fnameNETENGINE-8000-M8K-AC)
                fnameNETENGINE-8000E-M8(688880),        -- NETENGINE-8000E-M8 (fnameNETENGINE-8000E-M8)
                fnameNETENGINE-8000E-M8-AC(688882),     -- NETENGINE-8000E-M8-AC (fnameNETENGINE-8000E-M8-AC)
                fnameNETENGINE-8000E-M8-DC(688881),     -- NETENGINE-8000E-M8-DC (fnameNETENGINE-8000E-M8-DC)
                fnameNETENGINE-8000E-M14(688883),       -- NETENGINE-8000E-M14 (fnameNETENGINE-8000E-M14)
                fnameNETENGINE-8000E-M14-2AC(688884),    -- NETENGINE-8000E-M14-2AC (fnameNETENGINE-8000E-M14-2AC)
                fnameNETENGINE-8000E-M14-DC(688885),    -- NETENGINE-8000E-M14-DC (fnameNETENGINE-8000E-M14-DC)
                fnameNETENGINE-8000E-M14-4AC(688899),  -- NETENGINE-8000E-M14-4AC (fnameNETENGINE-8000E-M14-4AC)
                fnameNETENGINE-8000E-M14-Z(688886),      -- NETENGINE-8000E-M14-Z (fnameNETENGINE-8000E-M14-Z)
                fnameNETENGINE-8000E-M14-Z-DC(688887),  -- NETENGINE-8000E-M14-Z-DC (fnameNETENGINE-8000E-M14-Z-DC)
                fnameNETENGINE-8000E-M14-Z-2AC(688888),  -- NETENGINE-8000E-M14-Z-2AC (fnameNETENGINE-8000E-M14-Z-2AC)
                fnameNETENGINE-8000E-M14-Z-4AC(688903),  -- NETENGINE-8000E-M14-Z-4AC (fnameNETENGINE-8000E-M14-Z-4AC)
                fnamePTN6900-2-M4-DC(688839),            -- PTN6900-2-M4-DC (fnamePTN6900-2-M4-DC)
                fnamePTN6900-2-M4-AC(688849),            -- PTN6900-2-M4-AC (fnamePTN6900-2-M4-AC)
                fnameNETENGINE-8100-M8(688890),        -- NETENGINE-8100-M8 (fnameNETENGINE-8100-M8)
                fnameNETENGINE-8100-M8-AC(688892),     -- NETENGINE-8100-M8-AC (fnameNETENGINE-8100-M8-AC)
                fnameNETENGINE-8100-M8-DC(688891),     -- NETENGINE-8100-M8-DC (fnameNETENGINE-8100-M8-DC)
                fnameNETENGINE-8100-M14(688893),       -- NETENGINE-8100-M14 (fnameNETENGINE-8100-M14)
                fnameNETENGINE-8100-M14-4AC(688894),    -- NETENGINE-8100-M14-4AC (fnameNETENGINE-8100-M14-4AC)
                fnameNETENGINE-8100-M14-2AC(688902),    -- NETENGINE-8100-M14-2AC (fnameNETENGINE-8100-M14-2AC)
                fnameSIG16000-X4-DC(688910),       -- Quidway fnameSIG16000-X4-DC for V8R24C10
                fnameSIG16000-X4-HVDC(688911),     -- Quidway fnameSIG16000-X4-HVDC for V8R24C10
                fnameSIG16000-X8-DC(688912),       -- Quidway fnameSIG16000-X8-DC for V8R24C10
                fnameSIG16000-X8-HVDC(688913),     -- Quidway fnameSIG16000-X8-HVDC for V8R24C10
                fnameNETENGINE-8100-M14-DC(688895),    -- NETENGINE-8100-M14-DC (fnameNETENGINE-8100-M14-DC)
				fnameNETENGINE-8000-M4(688896),        -- NETENGINE-8000-M4 (fnameNETENGINE-8000-M4)
				fnameNETENGINE-8000-M4-AC(688897),     -- NETENGINE-8000-M4-AC (fnameNETENGINE-8000-M4-AC)
				fnameNETENGINE-8000-M4-DC(688898),     -- NETENGINE-8000-M4-DC (fnameNETENGINE-8000-M4-DC)
                fnameNETENGINE-8000E-M4-AC(688916),     -- V8R24C10 NETENGINE-8000E-M4-DC (fnameNETENGINE-8000E-M4-DC)
                fnameNETENGINE-8000E-M4-DC(688917),     -- V8R24C10 NETENGINE-8000E-M4-DC (fnameNETENGINE-8000E-M4-DC)
                fnameNETENGINE-8000-M6K(226355),        -- Quidway fnameNETENGINE-8000-M6K FRAME for V8R12C10
                fnameNETENGINE-8000-M6K-AC(226356),     -- Quidway fnameNETENGINE-8000-M6K-AC FRAME for V8R12C10
                fnameNETENGINE-8000-M6K-DC(226357),     -- Quidway fnameNETENGINE-8000-M6K-DC FRAME for V8R12C10
                fnameNETENGINE-8000-M1D-DC(226359),     -- Quidway fnameNETENGINE-8000-M1D-AC FRAME for V8R12C10 
               fnameNETENGINE-8000-M1D-AC(226360),     -- Quidway fnameNETENGINE-8000-M1D-AC FRAME for V8R12C10
               fnameNETENGINE-XH861-AC(336971),        -- Quidway fnameNETENGINE-XH861-AC FRAME for V8R24C10
                fnameNETENGINE-XH861-DC(336972),        -- Quidway fnameNETENGINE-XH861-DC FRAME for V8R24C10
                fnameNETENGINE-XH861(336973),           -- Quidway fnameNETENGINE-XH861 FRAME for V8R24C10(AC+DC)
                fnameNETENGINE-XH861-E-AC(210004),      -- Quidway fnameNETENGINE-XH861-E-AC FRAME for V8R25C00
                fnameNETENGINE-XH861-E-DC(210002),      -- Quidway fnameNETENGINE-XH861-E-DC FRAME for V8R25C00
                fnameNETENGINE-XH861-E(210003),         -- Quidway fnameNETENGINE-XH861-E FRAME for V8R25C00(AC+DC)
                fname8031CX600-X3A-E(532051),          -- Quidway CX600-3A PRO Carrier Switch
                fname8031CX600-X3ADO-E(532052),        -- Quidway CX600-3ADO PRO Carrier Switch
                fname8090NE40E-X3A-E(562050),          -- Quidwy Ne40E-3A PRO FRAME,
                fnameME60-X3A-E(159788),               -- Quidway ME60-X3A-400G FRAME
                fnamePTN6900-3A-E(229410),             --Integrated Chassis Components (PTN 6900-3A-400G)
               fnameNETENGINE-A820-AC(226371),             --NETENGINE-A820-AC for V8R21C00
               fnameNETENGINE-A810-AC(226373),             --NETENGINE-A810-AC for V8R21C00
               fnameNETENGINE-NE20-X3(229690),        -- V8R22C00 for NETENGINE-NE20-X3 chassis
               fnameNETENGINE-A820-M-AC(229518),       -- V8R21C00 for NETENGINE-A820-M chassis
                fnameNETENGINE-A811-M-AC(229516),       -- V8R21C00 for NETENGINE-A811-M-AC chassis
                fnameNETENGINE-A820-M(229517),       -- V8R21C00 for NETENGINE-A820-M chassis
                fnameNETENGINE-A811-AC(229519),       -- V8R21C00 for NETENGINE-A811 chassis
                fnameHG-FM-CPE-02-AC(229521),         -- V8R21C00 for HG-FM-CPE-02 chassis
                fnameNETENGINE-A821-AC(226372),       -- V8R21C10 for NETENGINE-A821-AC chassis
                fnameNETENGINE-A821-E-AC(226374),     -- V8R21C10 for NETENGINE-A821-E-AC chassis
                fnameNETENGINE-XH821-AC(154341),       -- V8R24C00 for NETENGINE-XH-A821-AC chassis
                fnameNETENGINE-XH821-E-AC(154351),     -- V8R24C00 for NETENGINE-XH-A821-E-AC chassis
               fnameHG-FM-CPE-03-AC(229524), -- V8R22C00 for HG-FM-CPE-03 chassis
               fnameATN910D-C-AC(229685),  -- ATN910DCCHASSIS, AC Power
               fnameATN910D-C-DC(229686),  -- ATN910DCCHASSIS, DC Power
               fname910E-F(225430), -- 910E-F
               fnameNETENGINE-A850-M-AC(229525), -- V8R22C00 for NETENGINE-A850-M-AC chassis
               fnameHG-FM-CPE-01-AC(229526), -- V8R22C00 for HG-FM-CPE-01-AC chassis
               fnameNETENGINE-A813-M-AC(229527), -- V8R22C00 for NETENGINE-A813-M-AC chassis
               fnamePTN91A-F-AC(229528), -- V8R22C00 for PTN91A-F-AC chassis
			   fnameNETENGINE-A813-AC(229661), -- V8R22C00 for NetEngine-A813-AC chassis
               fnameNETENGINE-A813-E-AC(229662), -- V8R22C00 for NetEngine-A813-E-AC chassis
               fnameHG-FM-CPE-02-S-AC(229722),         -- V8R24C00 for HG-FM-CPE-02-S chassis
               fnameSPNA907-S-AC(229723),            -- V8R25C10 for OptiX SPN A907-S chassis
               fnameATN905-S-AC(229663), -- V8R22C00 for ATN905-S-AC chassis
               fnameNETENGINE-A822-E-AC(229664), -- V8R22C00 for NetEngine-A822-E-AC chassis
-- Added by USG  USG fname from 0x00ff0000~0x00ffffff
-- USG V6R6 Frame of ARM desk
               fnameUSG6331E(16715818),                    --0x00ff102a
               fnameUSG6530E(16715819),                    --0x00ff102b
               fnameUSG6311E(16715820),                    --0x00ff102c
               fnameUSG6307E(16715821),                    --0x00ff102d
               fnameUSG6510E(16715822),                    --0x00ff102e
               fnameUSG6311E-POE(16715823),                --0x00ff102f
               fnameUSG6510E-POE(16715824),                --0x00ff1030

-- USG V6R6 Frame of 8G
               fnameUSG6380E(16715825),                    --0x00ff1031
               fnameUSG6306E(16715826),                    --0x00ff1032
               fnameUSG6308E(16715827),                    --0x00ff1033
               fnameUSG6312E(16715828),                    --0x00ff1034
               fnameUSG6322E(16715829),                    --0x00ff1035
               fnameUSG6332E(16715830),                    --0x00ff1036
               fnameUSG6350E(16715831),                    --0x00ff1037
               fnameUSG6360E(16715832),                    --0x00ff1038
               fnameUSG6515E(16715833),                    --0x00ff1039
               fnameUSG6550E(16715834),                    --0x00ff103a
               fnameUSG6560E(16715835),                    --0x00ff103b
               fnameUSG6580E(16715836),                    --0x00ff103c
               fnameNIP6305E(16715837),                    --0x00ff103d
               fnameNIP6310E(16715838),                    --0x00ff103e
               fnameNIP6510E(16715839),                    --0x00ff103f
               fnameEudemon200E-G8(16715840),              --0x00ff1040
               fnameEudemon200E-G8-DC(16715841),           --0x00ff1041
fnameUSG6385E(16715873),	--0x00ff1061
fnameUSG6305E(16715874),	--0x00ff1062
fnameUSG6309E(16715875),	--0x00ff1063
fnameUSG6315E(16715876),	--0x00ff1064
fnameUSG6325E(16715877),	--0x00ff1065
fnameUSG6335E(16715878),	--0x00ff1066
fnameUSG6355E(16715879),	--0x00ff1067
fnameUSG6365E(16715880),	--0x00ff1068
fnameUSG6525E(16715881),	--0x00ff1069
fnameUSG6555E(16715882),	--0x00ff106a
fnameUSG6565E(16715883),	--0x00ff106b
fnameUSG6585E(16715884),	--0x00ff106c
fnameEudemon200E-G85-AC(16715885),	--0x00ff106d
fnameEudemon200E-G85-DC(16715886),	--0x00ff106e
fnameIPS6309E-AC(16715902),	--0x00ff107e
fnameIPS6315E-AC(16715903),	--0x00ff107f
fnameIPS6515E-AC(16715904),	--0x00ff1080

-- USG V6R6 Frame of 40G
               fnameUSG6650E(16715842),                    --0x00ff1042
               fnameUSG6630E(16715843),                    --0x00ff1043
               fnameUSG6630E-DC(16715844),                 --0x00ff1044
               fnameEudemon1000E-G3(16715845),             --0x00ff1045
               fnameEudemon1000E-G3-DC(16715846),          --0x00ff1046
               fnameEudemon1000E-G5(16715847),             --0x00ff1047
               fnameEudemon1000E-G5-DC(16715848),          --0x00ff1048
               fnameNIP6550E(16715863),                    --0x00ff1057
               fnameAntiDDos1820(16715864),                --0x00ff1058
			   fnameAntiDDoS1820-N(16715872),              --0x00ff1060
fnameUSG6635E-AC(16715894),	--0x00ff1076
fnameUSG6635E-DC(16715895),	--0x00ff1077
fnameUSG6655E(16715896),	--0x00ff1078
fnameAntiDDoS1825(16715897),	--0x00ff1079
fnameEudemon1000E-G35-AC(16715898),	--0x00ff107a
fnameEudemon1000E-G35-DC(16715899),	--0x00ff107b
fnameEudemon1000E-G55-AC(16715900),	--0x00ff107c
fnameEudemon1000E-G55-DC(16715901),	--0x00ff107d
fnameIPS6555E-AC(16715905),	--0x00ff1081
fnameIPS6555ED-AC(16715906),	--0x00ff1082
-- USG V6R6 Frame of 80G
               fnameUSG6680E(16715849),                    --0x00ff1049
               fnameEudemon1000E-G8(16715850),             --0x00ff104a
               fnameEudemon1000E-G8-DC(16715851),          --0x00ff104b
-- USG V6R6 Frame of 160G
               fnameNIP6610E(16715852),                    --0x00ff104c
               fnameNIP6610ED(16715853),                   --0x00ff104d
               fnameUSG6716E(16715854),                    --0x00ff104e
               fnameUSG6712E(16715855),                    --0x00ff104f
               fnameEudemon1000E-G12(16715856),            --0x00ff1050
               fnameEudemon1000E-G12-DC(16715857),         --0x00ff1051
               fnameEudemon1000E-G16(16715858),            --0x00ff1052
               fnameEudemon1000E-G16-DC(16715859),         --0x00ff1053
               fnameNIP6620E(16715860),                    --0x00ff1054
               fnameNIP6620ED(16715861),                   --0x00ff1055
               fnameAntiDDos1880(16715862),                --0x00ff1056
-- USG V6R7 Frame of 20G
			   fnameUSG6391E-AC(16715865),                  --0x00ff1059
			   fnameUSG6610E-AC(16715866),				    --0x00ff105a
			   fnameUSG6620E-AC(16715867),                  --0x00ff105b
			   fnameEudemon1000E-G1-AC(16715868),           --0x00ff105c
			   fnameEudemon1000E-G1-DC(16715869),           --0x00ff105d
			   fnameEudemon1000E-G2-AC(16715870),           --0x00ff105e
			   fnameEudemon1000E-G2-DC(16715871),           --0x00ff105f
fnameUSG6395E(16715887),	--0x00ff106f
fnameUSG6615E(16715888),	--0x00ff1070
fnameUSG6625E(16715889),	--0x00ff1071
fnameEudemon1000E-G15-AC (16715890),	--0x00ff1072
fnameEudemon1000E-G15-DC(16715891),	--0x00ff1073
fnameEudemon1000E-G25-AC(16715892),	--0x00ff1074
fnameEudemon1000E-G25-DC(16715893),	--0x00ff1075
-- USG 12000
fnameUSG12004-AC-CHAS     (16715907),  --0x00ff1083
fnameUSG12004-AC-CHAS-OVS (16715908),  --0x00ff1084
fnameUSG12004-DC-CHAS     (16715909),  --0x00ff1085
fnameUSG12004-DC-CHAS-OVS (16715910),  --0x00ff1086
fnameUSG12008-AC-CHAS     (16715911),  --0x00ff1087
fnameUSG12008-AC-CHAS-OVS (16715912),  --0x00ff1088
fnameUSG12008-DC-CHAS     (16715913),  --0x00ff1089
fnameUSG12008-DC-CHAS-OVS (16715914),  --0x00ff108a
fnameE9000E-X4-AC-CHAS    (16715915),  --0x00ff108b
fnameE9000E-X4-AC-CHAS-OVS(16715916),  --0x00ff108c
fnameE9000E-X4-DC-CHAS    (16715917),  --0x00ff108d
fnameE9000E-X4-DC-CHAS-OVS(16715918),  --0x00ff108e
fnameE9000E-X8-AC-CHAS    (16715919),  --0x00ff108f
fnameE9000E-X8-AC-CHAS-OVS(16715920),  --0x00ff1090
fnameE9000E-X8-DC-CHAS    (16715921),  --0x00ff1091
fnameE9000E-X8-DC-CHAS-OVS(16715922),  --0x00ff1092
fnameAntiDDoS12004-AC-CHAS(16715923),  --0x00ff1093
fnameAntiDDoS12004-DC-CHAS(16715924),  --0x00ff1094
fnameAntiDDoS12008-AC-CHAS(16715925),  --0x00ff1095
fnameAntiDDoS12008-DC-CHAS(16715926),  --0x00ff1096
fnameIPS6555E-DC        (16715927),   --0x00FF1097
fnameUSG6575E-B-AC        (16715928), --0x00FF1098
fnameUSG6605E-B-AC        (16715929), --0x00FF1099
fnameUSG6502E-C        (16715930),    --0x00FF109A
fnameUSG6503E-C        (16715931),    --0x00FF109B
fnameUSG6302E-C        (16715932),    --0x00FF109C
fnameUSG6303E-C        (16715933),    --0x00FF109D
fnameUSG6306E-AC        (16715934),   --0x00FF109E
fnameUSG6316E-AC        (16715935),   --0x00FF109F
fnameUSG6326E-AC        (16715936),   --0x00FF10A0
fnameUSG6501E-C        (16715937),    --0x00FF10A1
fnameUSG6301E-C        (16715938),    --0x00FF10A2
fnameUSG6510E-DK-AC        (16715939),--0x00FF10A3
fnameUSG6520E-K-AC        (16715940), --0x00FF10A4
fnameUSG6560E-K-AC        (16715941), --0x00FF10A5
fnameUSG6590E-K-AC        (16715942), --0x00FF10A6
fnameUSG6620E-K-AC        (16715943), --0x00FF10A7
fnameUSG6640E-K-AC        (16715944), --0x00FF10A8
fnameIPS6520E-K-AC        (16715945), --0x00FF10A9
fnameIPS6610E-K-AC        (16715946), --0x00FF10AA
fnameIPS6610ED-K-AC        (16715947),--0x00FF10AB
fnameIPS6515E-B-AC        (16715948), --0x00FF10AC
fnameIPS6525E-AC        (16715949),   --0x00FF10AD
fnameIPS6535E-AC        (16715950),   --0x00FF10AE
fnameIPS12004-AC        (16715951),   --0x00FF10AF
fnameIPS12004-DC        (16715952),   --0x00FF10B0
fnameIPS12008-AC        (16715953),   --0x00FF10B1
fnameIPS12008-DC        (16715954),   --0x00FF10B2
fnameUSG6615F        (16715955),   --0x00FF10B3
fnameUSG6625F        (16715956),   --0x00FF10B4
fnameUSG6635F        (16715957),   --0x00FF10B5
fnameUSG6655F        (16715958),   --0x00FF10B6
fnameEudemon1000E-F15   (16715959),    --0x00FF10B7
fnameEudemon1000E-F25   (16715960),    --0x00FF10B8
fnameAntiDDoS1905       (16715961),    --0x00FF10B9
fnameIPS6585F           (16715962),    --0x00FF10BA
fnameIPS6615F           (16715963),    --0x00FF10BB
fnameEudemon1000E-F35   (16715964),    --0x00FF10BC
fnameEudemon1000E-F55   (16715965),    --0x00FF10BD
fnameIPS6625F           (16715966),    --0x00FF10BE
fnameUSG6501E-C-O      (16715967),    --0x00FF10BF
fnameUSG6502E-C-O      (16715968),    --0x00FF10C0
fnameUSG6503E-C-O      (16715969),    --0x00FF10C1
fnameUSG6585E-O-AC      (16715970),    --0x00FF10C2
fnameUSG6575E-B-O-AC      (16715971),    --0x00FF10C3
fnameUSG6603F-C      (16715972),    --0x00FF10C4
fnameUSG6620F-K-AC        (16715973),    --	00FF10C5
fnameAntiDDoS1905-K-AC        (16715974),    --	00FF10C6
fnameUSG6650F-K-AC        (16715975),    --	00FF10C7
fnameIPS6610FD-K-AC        (16715976),    --	00FF10C8
fnameUSG12004-K-AC        (16715977),    --	00FF10C9
fnameUSG6725F        (16715978),    --00FF10CA
fnameIPS6655F        (16715979),    --00FF10CB
fnameAntiDDoS1908        (16715980),    --00FF10CC
fnameUSG6715F        (16715981),    --00FF10CD
fnameUSG6710F-K        (16715982),    --00FF10CE
fnameEudemon1000E-F125        (16715983),    --00FF10CF
fnameUSG6685F        (16715985),    --00FF10D1
fnameEudemon1000E-F85        (16715986),    --00FF10D2
fnameIPS6620F-K        (16715992),    --00FF10D8
fnameUSG12004-F        (16715993),    --00FF10D9
fnameEudemon9000E-F4        (16715994),    --00FF10DA
fnameAntiDDoS12004-F        (16715995),    --00FF10DB
fnameIPS12004-F        (16715996),    --00FF10DC
fnameUSG12008-F        (16715997),    --00FF10DD
fnameEudemon9000E-F8        (16715998),    --00FF10DE
fnameAntiDDoS12008-F        (16715999),    --00FF10DF
fnameIPS12008-F        (16716000),    --00FF10E0
fnameEudemon1000E-F205        (16716001),    --00FF10E1
fnameUSG6000E-E03        (16716003),    --00FF10E3
fnameUSG6000E-E07        (16716004),    --00FF10E4
fnameUSG6000E-E10        (16716005),    --00FF10E5
fnameEudemon1000E-C5        (16716006),    --00FF10E6
fnameEudemon1000E-C8        (16716007),    --00FF10E7
fnameAntiDDoS1908-K        (16716008),    --00FF10E8
fnameUSG6710F        (16716009),    --00FF10E9
fnameUSG6308E-B        (16716010),    --00FF10EA
fnameUSG6318E-B        (16716011),    --00FF10EB
fnameUSG6338E-B        (16716012),    --00FF10EC
fnameUSG6358E-B        (16716013),    --00FF10ED
fnameUSG6378E-B        (16716014),    --00FF10EE
fnameUSG6388E-B        (16716015),    --00FF10EF
fnameUSG6398E-B        (16716016),    --00FF10F0
fnameUSG6000F-E20        (16716017),    --00FF10F1
fnameUSG6000F-E15        (16716018),    --00FF10F2
fnameUSG6000F-E12        (16716019),    --00FF10F3
fnameUSG6000F-E09        (16716020),    --00FF10F4
fnameUSG6000F-E07        (16716021),    --00FF10F5
fnameUSG6000F-E05        (16716022),    --00FF10F6
fnameUSG6000F-E03        (16716023),    --00FF10F7
fnameUSG6000F-E01        (16716024),    --00FF10F8
fnameProbe1005        (16716025),    --00FF10F9
fnameProbe1010        (16716026),    --00FF10FA
fnameProbe1020        (16716027),    --00FF10FB
fnameProbe1030        (16716028),    --00FF10FC
fnameEudemon1000E-C1        (16716029),    --00FF10FD
fnameEudemon1000E-S1        (16716030),    --00FF10FE
fnameEudemon1000E-S5        (16716031),    --00FF10FF
fnameEudemon1000E-S8        (16716032),    --00FF1100
fnameEudemon1000E-M1        (16716033),    --00FF1101
fnameEudemon1000E-M2        (16716034),    --00FF1102
fnameEudemon1000E-M3        (16716035),    --00FF1103
fnameEudemon1000E-M5        (16716036),    --00FF1104
fnameAntiDDoS1905-N        (16716037),    --00FF1105
fnameASG5303        (16716038),    --00FF1106
fnameASG5305        (16716039),    --00FF1107
fnameASG5308        (16716040),    --00FF1108
fnameASG5310        (16716041),    --00FF1109
fnameASG5315        (16716042),    --00FF110A
fnameASG5320        (16716043),    --00FF110B
fnameASG5505        (16716044),    --00FF110C
fnameASG5510        (16716045),    --00FF110D
fnameASG5520        (16716046),    --00FF110E
fnameASG5530        (16716047),    --00FF110F
fnameASG5550        (16716048),    --00FF1110
fnameASG5610        (16716049),    --00FF1111
fnameASG5000-S1050        (16716050),    --00FF1112
fnameASG5000-S1055        (16716051),    --00FF1113
fnameASG5000-D1060        (16716052),    --00FF1114
fnameASG5000-S1100        (16716053),    --00FF1115
fnameASG5000-E1108        (16716054),    --00FF1116
fnameASG5000-D1120        (16716055),    --00FF1117
fnameASG5000-S1220        (16716056),    --00FF1118
fnameASG5000-D1300        (16716057),    --00FF1119
fnameASG5000-E1400        (16716058),    --00FF111A
fnameASG5000-S1460        (16716059),    --00FF111B
fnameASG5000-D1500        (16716060),    --00FF111C
fnameASG5000-E2100        (16716061),    --00FF111D
fnameASG5000-D2100        (16716062),    --00FF111E
fnameASG5000-D2250        (16716063),    --00FF111F
fnameASG5000-D2500        (16716064),    --00FF1120
fnameASG5000-D3100        (16716065),    --00FF1121
fnameUSG6505F-C        (16716067),    --00FF1123
fnameUSG6606F-C        (16716068),    --00FF1124
fnameIPS6525F        (16716069),    --00FF1125
fnameIPS6525FD        (16716070),    --00FF1126
fnameIPS6585FD        (16716071),    --00FF1127
fnameIPS6615FD        (16716072),    --00FF1128
fnameIPS6625FD        (16716073),    --00FF1129
fnameUSG6510F-D        (16716078),    --00FF112E
fnameUSG6530F-D        (16716079),    --00FF112F
fnameUSG6510F-DK        (16716080),    --00FF1130
fnameUSG6510F-DL        (16716081),    --00FF1131
fnameUSG6530F-DL        (16716082),    --00FF1132
fnameUSG6525F        (16716093),    --00FF113D
fnameUSG6555F        (16716094),    --00FF113E
fnameUSG6565F        (16716095),    --00FF113F
fnameUSG6585F        (16716096),    --00FF1140
fnameUSG6520F-K        (16716097),    --00FF1141
fnameUSG6560F-K        (16716098),    --00FF1142
fnameUSG6590F-K        (16716099),    --00FF1143
fnameIPS6520F-K        (16716100),    --00FF1144
fnameEudemon1000E-F08        (16716101),    --00FF1145
fnameUSG6502F-C        (16716103),    --00FF1147
fnameUSG6303E        (16716106),    --00FF114A
fnameEudemon9000E-X16        (16716107),    --00FF114B
fnameUSG12016        (16716108),    --00FF114C
fnameAntiDDoS12016        (16716109),    --00FF114D
fnameEudemon1000E-T1        (16716110),    --00FF114E
fnameUSG6621F-O        (16716111),    --00FF114F
fnameUSG6620F-O        (16716112),    --00FF1150
fnameUSG6510F-DPL        (16716113),    --00FF1151
fnameUSG6530F-DPL        (16716114),    --00FF1152
fnameEudemon1000E-C1A        (16716116),    --00FF1154
fnameEudemon1000E-M1A        (16716119),    --00FF1157
fnameEudemon1000E-M2A        (16716120),    --00FF1158
fnameEudemon1000E-S1A        (16716123),    --00FF115B
fnameEudemon1000E-T1A        (16716126),    --00FF115E
fnameProbe1001F        (16716130),    --00FF1162
fnameEudemon1000E-F01        (16716131),    --00FF1163
fnameEudemon1000E-F05        (16716132),    --00FF1164
fnameUSG6680E-ACC        (16716133),    --00FF1165
fnameEudemon1000E-M55        (16716139),    --00FF117A
fnameEudemon1000E-M10        (16716140),    --00FF117B
fnameEudemon1000E-S10        (16716141),    --00FF117C
fnameEudemon1000E-C10        (16716142),    --00FF117D
fnameUSG6585F-B        (16716143),    --00FF116F
fnameEudemon1000E-C5A        (16716146),    --00FF1172
fnameEudemon1000E-C8A        (16716147),    --00FF1173
fnameEudemon1000E-M3A        (16716148),    --00FF1174
fnameEudemon1000E-M5A        (16716149),    --00FF1175
fnameEudemon1000E-S5A        (16716150),    --00FF1176
fnameEudemon1000E-S8A        (16716151),    --00FF1177
fnameEudemon1000E-T3A        (16716152),    --00FF1178
fnameEudemon1000E-T5A        (16716153),    --00FF1179
fnameEudemon1000E-C10A        (16716154),    --00FF117A
fnameEudemon1000E-S10A        (16716155),    --00FF117B
fnameEudemon1000E-M10A        (16716156),    --00FF117C
fnameEudemon1000E-T10A        (16716157),    --00FF117D
fnameEudemon9000E-H        (16716158),    --00FF117E
fnameEudemon1000E-C1A-PL        (16716165),    --00FF1185
fnameEudemon1000E-M1A-PL        (16716166),    --00FF1186
fnameEudemon1000E-S1A-PL        (16716167),    --00FF1187
fnameEudemon1000E-T1A-PL        (16716168),    --00FF1188
fnameEudemon1000E-F10        (16716169),    --00FF1189
fnameEudemon1000E-F03-D        (16716170),    --00FF118A
fnameEudemon1000E-F03-DL        (16716171),    --00FF118B
fnameUSG6000F-S30   (16716181),    --00FF1195
fnameUSG6000F-S50   (16716182),    --00FF1196
fnameUSG6000F-S150   (16716183),    --00FF1197
fnameUSG6000F-S160   (16716184),    --00FF1198
fnameUSG6000F-S180   (16716185),    --00FF1199
fnameUSG6000F-S200   (16716186),    --00FF119A
fnameUSG6000F-S230   (16716187),    --00FF119B
fnameUSG6000F-S260   (16716188),    --00FF119C
fnameIPS6000F-S110   (16716189),    --00FF119D
fnameIPS6000F-S120   (16716190),    --00FF119E
fnameXH6655          (16716191),    --00FF119F
fnameUSG12000-H6          (16716192),    --00FF11A0
fnameAntiDDoS12000-H6          (16716193),    --00FF11A1
fnameIPS12000-H6          (16716194),    --00FF11A2
fnameEudemon1000E-C0    (16716195),    --00FF11A3
fnameEudemon1000E-M0    (16716196),    --00FF11A4
fnameEudemon1000E-S0    (16716197),    --00FF11A5
fnameUSG6636F        (16716198),      --00FF11A6
fnameUSG6656F        (16716199),      --00FF11A7
fnameUSG6686F        (16716200),      --00FF11A8
fnameMPUA-USG6000F-S115        (16716201),      --00FF11A9
fnameMPUA-USG6000F-S125        (16716202),      --00FF11AA
fnameMPUA-USG6560F-D        (16716203),      --00FF11AB
fnameMPUA-Eudemon1000E-F06-D        (16716204),      --00FF11AC
fnameUSG6000F-E06-D          (16716205),    --00FF11AD
fnameUSG6000F-E12-D          (16716206),    --00FF11AE
fnameUSG6000F-E06-DL          (16716207),    --00FF11AF
fnameUSG6000F-S112        (16716208),      --00FF11B0
fnameUSG6000F-S330        (16716209),      --00FF11B1
fnameUSG6000F-S500        (16716210),      --00FF11B2
fnameUSG6000F-S55L        (16716211),      --00FF11B3
fnameUSG6000F-S530        (16716212),      --00FF11B4
fnameUSG6000F-S600        (16716213),      --00FF11B5
fnameUSG6000F-S12        (16716218),      --000FF11BA
fnameUSG6000F-S13        (16716219),      --000FF11BB
fnameUSG6855G        (16716220),      --000FF1158
fnameUSG6875G        (16716221),      --000FF1159
fnameUSG6885G        (16716222),      --000FF115A
fnameEudemon1000E-W855        (16716223),      --000FF115B
fnameEudemon1000E-W875        (16716224),      --000FF115C
fnameEudemon1000E-W885        (16716225),      --000FF115D
fnameAntiDDoS1907        (16716226),      --000FF11C2


               fnameNETENGINE-A831-E-DC(229665),    -- V8R22C00 for CP8PHST2EA10(SBOM) NetEngine-A831-E-DC chassis
               fnamePTN910D-F-AC(229540),           -- V8R22C00 for PTN910D-F-AC chassis
               fnamePTN910D-F-DC(229542),           -- V8R22C00 for PTN910D-F-DC chassis
               fnameSPNA907-AC(229547), -- V8R22C10 for PTN907-AC chassis
               fnameSPNA907-I-AC(229574), -- V8R24C10 for SPNA907-I-AC chassis
               fnameHG-FM-CPE-03-A-AC(229548), -- V8R23C00 for HG-FM-CPE-03-A chassis
               fnameATN910D-B-AC(229666),           -- V8R22C00 for ATN910D-B AC chassis
               fnameATN910D-B-DC(229667),           -- V8R22C00 for ATN910D-B DC chassis
               fnameNETENGINE-8000-M1D-B-AC(229668), -- V8R22C00 for NetEngine-8000-M1D-B-AC chassis
               fnameNETENGINE-8000-M1D-B-DC(229669), -- V8R22C00 for NetEngine-8000-M1D-B-DC chassis
               fnameNETENGINE-8000E-M1E-B-DC(210125),  -- V8R25C10 for NetEngine-8000E-M1E-B-DC chassis
               fnameNETENGINE-8000E-M1E-B-AC(210127),  -- V8R25C10 for NetEngine-8000E-M1E-B-AC chassis
               fnameNETENGINE-A815-T-AC(229680), -- V8R22C00 for NetEngine-A815-T-AC chassis
               fnameNETENGINE-A825-T-DC(229681), -- V8R22C00 for NetEngine-A825-T-DC chassis
               fnameNETENGINE-A825-T-AC(229682), -- V8R22C00 for NetEngine-A825-T-AC chassis
               fnameNETENGINE-A835-T-DC(229683), -- V8R22C00 for NetEngine-A835-T-DC chassis
               fnameNETENGINE-A835-T-AC(229684), -- V8R22C00 for NetEngine-A835-T-AC chassis
               fnameATN910D-H-AC(229687),           -- V8R23C10 for ATN-910D-H-AC chassis
               fnameATN910D-H-DC(229688),           -- V8R23C10 for ATN-910D-H-DC chassis
               fnameATN910E-A-DC(210012),          -- V8R25C00 for ATN910E-A DC chassis
               fnameNETENGINE-A812-E-S-DC(229689), -- V8R23C10 for NetEngine-A812-E-S-DC chassis
               fnameNETENGINE-A822-AC(229691),      -- V8R23C10 for NetEngine-A822-AC chassis
               fnameNETENGINE-A817-AC(210008),      -- V8R25C00 for NetEngine-A817-AC chassis
               fnameNetEngineA816-E-AC(229701),      -- V8R24C00 for NetEngineA816-E-AC chassis
               fnameATN905-L-AC(229711),      -- V8R24C00 for ATN905-L-AC chassis
               fnameNetEngineA816-AC(229721),      -- V8R24C00 for NetEngineA816-AC chassis


-- Ended by USG  USG fname from 0x00ff0000~0x00ffffff

-- FutureMatrix: 0x000AF000~0x000AFFFF(716800~720895)
                fnameFM12804(716800),
                fnameFM12808(716801),
                fnameFM12816(716802),
                fnameFM98604CEI(716803),
                fnameFM885032CQEI(716804),
				fnameFM885064CQEI(716805),
                fnameFM88614CEI(716806),
                fnameFM685748S6CQEI(716807),
                fnameFM686548S8CQEI(716808),
                fnameFM687048S6CQEI(716809),
                fnameFM687048T6CQEI(716810),
				fnameFM5855E48T4S2Q(716811),
				fnameFM6857E48S6CQ(716812),
				fnameFM6857E48T6CQ(716813),
				fnameFM686548S8CQSI(716814),
				fnameFM6865E48S8CQ(716815),
				fnameFM88684CEI(716816),
				fnameFM8850E32CQEI(716817),
				fnameFM5855S8T4S2Q(716818),
				fnameFM6857S8S6CQ(716819)
                }


        HWPCBType ::= TEXTUAL-CONVENTION
            STATUS current
            DESCRIPTION
                "This data type is used as the syntax of the
                hwSlotType object in the definition of
                HUAWEI-DEVICE-MIBs hwSlotTable.

                The definition of this textual convention with the
                addition of newly assigned values is published
                periodically by the Huawei MIB Criterion Group, every
                value indicate a PCB produced by Huawei.

                "
            SYNTAX INTEGER
                {
-- MD 5500
                bnameUnknown(1),
                bnameH511Mmxa(2),               -- MMXA board, mainboard of MA5100V1
                bnameH511Mmxb(3),               -- MMXB board, mainboard of MA5100V1 with APON sub-board
                bnameH511Mmxc(4),               -- MMXC board, mainboard of MA5100V2 with V5 characteritics etc.
                bnameH511Asxa(5),               -- ASXA board, mainboard of MD5500, with ASX chip on board for 8x622M switch
                bnameH511Aica(6),               -- ATM Interface Card, service board of MD5500, support STM-1 and STM-4
                bnameH511Lanc(7),               -- 8 Port FE service board of MD/MA,
                                                -- for ethernet service access, support 64 VLAN
                bnameH512Lanc(8),               -- Update version of H511LANC, support 32/2K VLAN, and region VLAN (IPDSLAM)
                bnameH512Land(9),               -- Update version of H512LANC, support 32/256/2K VLAN (IPDSLAM),
                                                -- and 8FE/4FE/8Optic/4Optic/1GE subboard
                bnameH511Adlb(10),
                bnameH511Adlc(11),              -- 16 Port ADSL board
                bnameH511Adld(12),              -- 32 Port ADSL board
                bnameH512Adld(13),              -- 32 Port ADSL board, use another chipset contrast to H511ADLD
                bnameH511Cesc(14),              -- 16 E1 Port CES board, not support TDM, with 2 E1 subboard
                bnameH511Cesd(15),              -- 8 V35 Port CES board, with 3 V35 subboard
                bnameH511Cese(16),              -- 8 E1 Port CES board, not support TDM, with 1 E1 subboard
                bnameH511Cesf(17),              -- No subboard, for TDM use
                bnameH511Cesh(18),              -- 16 E1 port CES board, with 2 E1 subboard, support TDM
                bnameH512Cesh(19),              -- Same as H511CESH, diffrent from chipset
                bnameH511Ea16(20),              -- Same as H511CESC, diffrent from chipset
                bnameH511Ce8(21),               -- Same as H511CESE, diffrent from chipset
                bnameH511Ce8V(22),              -- Same as H511CESD, diffrent from chipset
                bnameH511Dt16(23),              -- 16 E1 Port CES board, only support TDM mode
                bnameH511Dn16(24),              -- 16 E1 Port CES board, only support TDM mode, support DDN clock
                bnameH511Frca(25),              -- 8 E1 Port FR board
                bnameH511Frcb(26),              -- 8 V35 Port FR board
                bnameH511Slfa(27),              -- 8 G.SHDSL port FR board, work in E1 mode
                bnameH511Slfb(28),              -- 8 G.SHDSL port FR board, work in V35 mode
                bnameH511Slca(29),              -- 8 G.SHDSL port CES board, work in E1 mode, not support TDM
                bnameH511Slcb(30),              -- 8 G.SHDSL port CES board, work in V35 mode
                bnameH511Splb(31),              -- 16 port split board word with H511ADLC
                bnameH511Splc(32),              -- 32 port split board word with H511ADLD/H512ADLD
                bnameH511Pots(33),              -- 32 Port Pots board
                bnameH511Aiua(34),              -- ATM Interface Unit, can work with STM-1/IMA/E3 subboard, use the same PCB as MMXA
                bnameH511Aiub(35),              -- ATM Interface Unit, can work with STM-1/IMA/E3/APON/STM-4 subboard, use the same PCB as MMXA
                bnameH511Aiuc(36),              -- ATM Interface Unit, can work with STM-1/IMA/E3/APON/STM-4 subboard, use the same PCB as MMXC
                bnameH511Ipuo(37),              -- Optic interface IP process board
                bnameH511Epue(38),              -- Electric Interface IP process board
                bnameH511Ipue(39),              -- Electric interface ehternet process board
                bnameH511Epuo(40),              -- Optic interface ehternet process board
                bnameH511Vspd(41),              -- VoDSL process board
                bnameH511Msua(42),              -- 2 Port STM-1(with 2M structure) access board
                bnameH511Imua(43),              -- 32 port IMA interface access board
                bnameH511Smxa(44),              -- main board in slave frame for DSLAM use, use the same PCB as MMXA
                bnameH511Smxb(45),              -- main board in slave frame for DSLAM use, use the same PCB as MMXB
                bnameH511Sepa(46),              -- Board used to connect slave frame for DSLAM use
                bnameEsc(47),                   -- For HONET
                bnameRsp(48),                   -- For HONET
                bnamePv8(49),                   -- For HONET
                bnameApru(50),                  -- For HONET
                bnameAprx(51),                  -- For HONET
                bnameAsl(52),                   -- For HONET
                bnameA32(53),                   -- For HONET
                bnameDsl(54),                   -- For HONET
                bnameMlc(55),                   -- For HONET
                bnameIdla(56),                  -- For HONET
                bnameCdi(57),                   -- For HONET
                bnameAti(58),                   -- For HONET
                bnameTss(59),                   -- For HONET
                bnamePwx3(60),                 -- For HONET
                bnamePwxA(61),                 -- For HONET
                bnameEmu(62),                   -- For HONET
                bnameHwc(63),                   -- For HONET
                bnameVfb(64),                   -- For HONET
                bnamePvu(65),                   -- For HONET

                bnameH511Shla(66),              -- 32-port ATM G.SHDSL service board, a new service board for the masters Frame in 51V2
                bnameH511Adle(67),              -- 32-port integrated service board of ADL and SPL, a new service board for the master Frame in 51V2
                bnameMD5500H511BTSA(68),        -- H511BTSA (broadband and narrowband test board)
                bnameh511Land(69),              -- H511lLAND board

                bnameH601Apma(70),              -- New control board for the master Frame of the UA3000
                bnameH601Apsa(71),              -- New control board for the slave Frame of the UA3000
                bnameH601Apfa(72),              -- New control board for the master Frame of the UA3000, with the front-access line
                bnameH601CSL(73),              -- New service board of the UA3000
                bnameH601Cslf(74),              -- New service board of the UA3000, with the front-access line
                bnameH601ADL(75),              -- New service board of the UA3000
                bnameH512Adle(76),              -- 32-port integrated service board of ADL and SPL, a new service board for the master Frame in 51V2
                bnameH512Adli(77),              -- 32-port ISDN ADL service board, a new service board for the master Frame in 51V2
                bnameH531BASA(78),              -- New service board of the MA5300
                bnameH531BASE(79),              -- New service board of the MA5300

-- MUSA
                bnameSmb(80),                   -- Control board
                bnameHrb(81),                   -- Uplink board
                bnameHab(82),                   -- Uplink board

-- MA5200
                bnameNat(83),
                bnameCts(84),

                bnameH511BTSB(85),              -- For MA5100&MD5300, Broad test card B , providing test for broad subscribers

-- AG
                bnamePvm(90),

                bnameSdl(100),                  -- SDL (Narrowband service board, which provides 4 E1 ports and 4 G.SHDSL ports)
                bnameH511Msuc(101),             -- MSUC board, which supports 2 optical ports and 126[LU1] E1 ports
                bnameH511AsxB(102),             -- Control board ASXB

-- Board types of A8010
                bnamVspNas(110),                -- VSPNAS board, whose number is AS31VSPA03032106
                bnamVspIpp(111),                -- VSP IPP board, whose number is HSPAS31VSPA03032106
                bnamVspHsp(112),                -- VSP HSP board, whose number is AS31VSPA03032106
                bnamVspAnyport(113),            -- VSP AnyPort board, whose number is AS31VSPA03032106
                bnamVsu(114),                   -- The number of this board is AS31VSUA03033127 or AS31HSPA.
                bnamHsp(115),                   -- The number of this board is AS31MSTU03032762.
                bnamFrb(116),                   -- The number of this board is AS31FRBA03034101 or AS31FRBB03034102.
                bnamMstu(117),                  -- The number of this board is AS31MSTU03032762.
-- ESR board type
                bnameMpua(130) ,                -- BS21MPUA
                bnameMpub(131) ,                -- BS22MPUB
                bnameNeta(132) ,                -- BS21NETA
                bnameNetb(133) ,                -- BS22NETB
                bnameSFCA(134) ,                -- BS21NETA
                bnameLpua(135) ,                -- BS21LPUA
                bnameLpub(136) ,                -- BS22LPUB
                bnameLpuc(137) ,                -- BS22LPUC
                bnameLpud(138) ,                -- BS22LPUD
-- ESR boards that have same hardware but different software
                bnameSpubBas(139) ,             -- SN01SPUB
                bnameSpubSerm(140) ,            -- SN01SPUB
                bnameLpui(141) ,                -- SN01LPUI
                bnameLpuh(142) ,                -- SN01LPUH
                bnameO2CC(143) ,                -- BS2202CC
-- MA5105
                bnameMa5105e1(200),             -- E1
                bnameMa5105fe(201),             -- FE
                bnameMa5105adsl(202),           -- ADSL
                bnameMa5105ima(203),            -- IMA
-- MD5500
                bnameMD5500Hsl(204),            -- HSL (narrowband service board, which provides two E1 ports and two V35 ports)
                bnameMD5500PV4(205),            -- PV4 (narrowband master node board, which provides four less E1 ports than PV8)
-- MA5300
                bnameMa5300ESM(206),            -- Ethernet switching control board of the MA5300. Its BOM is 03033569.
                bnameMa5300VDSL16(207),         -- 16-port Ethernet access VDSL service board of the MA5300. Its BOM is 03033632.
                bnameMa5300VDSL24(208),         -- 24-port Ethernet access VDSL service board of the MA5300. Its BOM is 03035806.
                bnameMa5300ADSL(209),           -- 48-port ADSL service board of the MA5300
-- UA5000
                 bnameH601Aiua(210),            -- ATM service board of the UA5000
-- MD5500
                bnameH511IMUB(211),             -- 16-port IMA service board of the MD5500
                bnameH511IMUD(212),             -- 32-port IMA service board of the MD5500
                bnameH531EADL(213),             -- 24-port ADSL service board
                bnameH531EVDB(214),             -- 24-port VDSL service board that supports the band plans of 10BASE-S and PLAN9998
                bnameH533ESHA(215),             -- 24-port G.SHDSL board of the MA5300
                bnameH531ETHA(216),             -- Ethernet access board of the MA5300. This board provides eight FE ports and one subslot.
                bnameH533EADB(217),             -- 48-port ADSL2+ service board of the MA5300

-- UA5000
                bnameH601SDL(220),             -- 16-port G.SHDSL board of the UA5000
                bnameH601DEHA(221),             -- UA5000's 16-port board that supports E1 transparent transmission
                bnameH601VDL(222),             -- 16-port VDSL board of the UA5000
                bnameH601IPMA(264),             -- UA5000's control board that forwards the service upstream to the IP network
                bnameH602ADM(265),             -- 16-port ADSL2+ full-broadband board of the UA5000
-- MA5100
                bnameH512ADLC(230),             -- 16-port ADSL service board
                bnameH513ADLD(231),             -- 32-port ADSL service board
                bnameH513ADLE(232),             -- 32-port ADSL board of the MA5100. This board provides a maximum downstream rate of 8 Mbit/s.
                bnameH513ADLF(233),             -- 32-port ADSL board of the MA5100. This board provides a maximum downstream rate of 25 Mbit/s.
                bnameH513ADLI(234),             -- 32-port ISDN ADL service board
                bnameH514ADLD(235),             -- 32-port ADSL service board
                bnameH515ADLD(236),             -- 32-port ADSL service board
                bnameH516ADLD(237),             -- 32-port ADSL service board
                bnameH517ADLD(238),             -- 32-port ADSL service board
                bnameH518ADLD(239),             -- 32-port ADSL service board
                bnameH519ADLD(240),             -- 32-port ADSL service board
                bnameH514ADLE(241),             -- 32-port ADSL board of the MA5100. This board provides a maximum downstream rate of 8 Mbit/s.
                bnameH515ADLE(242),             -- 32-port ADSL board of the MA5100. This board provides a maximum downstream rate of 8 Mbit/s
                bnameH516ADLE(243),             -- 32-port ADSL board of the MA5100. This board provides a maximum downstream rate of 8 Mbit/s.
                bnameH517ADLE(244),             -- 32-port ADSL board of the MA5100. This board provides a maximum downstream rate of 8 Mbit/s.
                bnameH518ADLE(245),             -- 32-port ADSL board of the MA5100. This board provides a maximum downstream rate of 8 Mbit/s.
                bnameH519ADLE(246),             -- 32-port ADSL board of the MA5100. This board provides a maximum downstream rate of 8 Mbit/s.
                bnameH511Spli(247),             -- split board word with ADLI
                bnameSepl(248),                 -- SEP subtend board
                bnameSmxl(249),                 -- SEP subtend board
-- MA5105
                bnameMa5105shdsl(250),          -- 16-port SHDSL board
                bnameMa5105fc(251),             -- FE subtend board
-- MA5105 N2B
                bnameN2Be1(252),                -- N2B board that provides the E1 port
                bnameN2Bfe(253),                -- N2B board that provides the FE port
                bnameN2Bima(254),               -- N2B board that provides the IMA port
                bnameN2Badslb08(255),           -- N2B board that provides 8 ADSL ports
                bnameN2Badslbsl(256),           -- N2B board that provides 16 ADSL ports
                bnameN2Bshdslb08(257),          -- N2B board that provides 8 SHDSL ports
                bnameN2Bshdslbsl(258),          -- N2B board that provides 16 SHDSL ports
-- MA5100
                -- bnameH601IPMA(264),              UA5000's control board that forwards the service upstream to the IP network
                -- bnameH602ADMB(265),              UA5000 ADSL2+ board
                bnameH511TSBA(266),             -- H511TSBA board for routing the passive test bus
                bnameH511VDLA(267),             -- VDSL board of the MA5100
                bnameVPU(268),                  -- VPU board of the MD
--S3026V
                bnameH523VDLA(269),

-- MA5105
                bnameMa5105adli(270),           -- ADLI board, which provides 16 ports
                bnameMa5105adlh(271),           -- ADLH board, which provides 16 ports
                bnameMa5105adce(272),           -- 16-port ADSL2+ board
                bnameMa5105adch(273),           -- 16-port ADSL2+ board
                bnameMa5105adid(274),           -- 16-port ADSL2+ Over ISDN board
                bnameH601ADLB(275),             -- 16-port ADSL board with a built-in splitter (TI AC5 chipset + 7350) (no relay)
                bnameH601CSLB(276),             -- 16-port ADSL and POTS combo service board with a built-in splitter (TI AC5 chipset + 7350) (no relay)
                bnameH601SDLB(277),             -- 16-port ATM G.SHDSL service board (GSV chipset + 7350/250 + high-rate connector + four-wire feature)
                bnameH602ADMC(278),             -- 16-port ADSL/ADSL2+ service board with a built-in splitter (GSV chipset + 7350/250 + high-rate connector)(two relays)
--S3026V

                bnameH523VDLAVDSA(279),

-- UA5000
                bnameH601AIUB(280),             -- UA IMA, E3, or ATM 155M upstream service board
                bnameH601CSLI(281),             -- UA CSLI board, a 16-port ADSL full-broadband board
                bnameH601VDLB(282),             -- UA VDLB board, a 16-port QAM VDSL board, which supports board N+1 backup
                bnameH602ADMI(283),             -- UA ADMI board, a 16-port ADSL2+ board with a built-in BT splitter
                bnameH601CSLC(284),             -- UA CSLC board, a 16-port ADSL broadband and narrowband combo board
                bnameH523mfce(299),             -- H523MFCE
-- HONET board type, for iManager N2000 BMS HV20 integrate management
                bnameHV20ASL(300),              -- For HONET, analog subscriber board of HONET SIPP II/III system,
                                                --having 16 paths of subscriber lines on each board.
                bnameHV20DRV(301),              --For HONET, dual-tone number receiving board of HONET SIPP II/III.
                                                --Each board configures 16 dual-tone number receivers. Meanwhile,
                                                --DRV board also provides the function of level switch between
                                                --difference level and TTL level.
                bnameHV20RSA(302),              -- For HONET, a main board, usually used in remote subscriber Frame.
                bnameHV20DTM(303),              -- For HONET, digital trunk board of HONET SIPP II/III system.
                                                -- Each board provides 2 E1 interfaces.
                bnameHV20DSL(304),              -- For HONET, digital subscriber board of HONET SIPP II/III system.
                                                -- Each board configures 8 paths of digital subscriber lines.
                bnameHV20DDU(305),              -- For HONET, digital interface board of HONET SIPP II/III system.
                                                -- Each board performs the switch between 2 paths 64K bit/s signal and V35, V24 signals.
                bnameHV20TSS(306),              -- For HONET, test board of HONET SIPP II/III system,
                                                -- providing test for analog subscribers and digital subscribers.
                bnameHV20TSI(307),              -- For HONET, test board used in digital subscriber testing. This is no longer in use.
                bnameHV20AV5(308),              -- For HONET, master control board of HONET SIPP II/III system,
                                                -- responsible f or the protocol processing, equipment management, and network exchanging.
                bnameHV20PWC(309),              -- For HONET, power supply board of HONET SIPP II/III system.
                                                -- PWC board does not provide 48V generator,
                                                -- and is only used in the master control Frame of the SIPP II system.
                bnameHV20PWX(310),              -- For HONET, power supply board of HONET SIPP II/III system.
                                                -- PWX board provides 48V generator, which is used in various shelves.
                bnameHV20DM4(311),              -- For HONET, tributary interface board. Each board provides the 4 paths
                                                -- of switch between sub-synchronous PCM lines and 2112Kbit/s synchronous code,
                                                -- and 4 paths of inversion. It also determines the direction of receiving and
                                                -- sending of the 4 paths of signals, which realizes the function of self-healing switch.
                bnameHV20TIU(312),              -- For HONET, optical interface board of OLT terminal station.
                                                -- The function of a TIU board is to multiplex the 28 paths of 2112 kbit/s tributary
                                                -- signals sent by 7 DM4, and then send them back to the 7 DM4.
                bnameHV20NMI(313),              -- For HONET, used in OLT, ONU-512, ONU-128, ONU-1000A of the HONET system,
                                                -- functioning as maintenance of the optical transmission equipment,
                                                -- environment monitoring and equipment management.
                bnameHV20FIU(314),              -- For HONET, optical interface in the trunk ONU,
                                                --providing simultaneously two pairs of optical interfaces.
                bnameHV20EIU(315),              -- For HONET, used in the E1 interface of ONU-128.
                                                -- EIU card completes the justification and restoration of two 2M signals.
                bnameHV20BIU(316),              -- For HONET, optical interface card used in triburary ONU,
                                                -- accepting 2 to 6 2M point to point transmission.
                bnameHV20ILM(317),              -- For HONET, InfoLink management card of CATV subscriber shelf.
                bnameHV20ESC(318),              -- For HONET, environment monitor interface board of HONET SIPP II/III system,
                                                -- providing the environment quantity of the remote ONU and monitoring the operation of the power supply.
                bnameHV20PWH(319),              -- For HONET, power supply board of PHD optical transmission system, used in various transmission shelves.
                bnameHV20ILR(320),              -- For HONET, InfoLink optical receiving board of CATV subscriber Frame.
                bnameHV20ILT(321),              -- For HONET, InfoLink optical sending board of CATV subscriber Frame.
                bnameHV20PV8(322),              -- For HONET, the master control board of HONET SIPP II/III system, responsible for protocol handling,
                                                -- equipment management, and network switch. The only difference between PV8 board and PV4 board is that
                                                -- the former has 8 paths of standard E1 interfaces while the latter has only 4.
                bnameHV20PV4(323),              -- For HONET, the master control board of HONET SIPP II/III system, responsible for protocol handling,
                                                -- equipment management, and network switch. The only difference between PV8 board and PV4 board is that
                                                -- the former has 8 paths of standard E1 interfaces while the latter has only 4.
                bnameHV20RSP(324),              -- For HONET, a new-type remote RSA board of HONET SIPP II/III system whose convergence rate can be adjusted,
                                                -- connecting to remote ONU subscribers collaboratively with digital trunk cards.
                                                -- Each RSP board may configure at most 4 2M PCM links, and can realize 1:1, 1:2, and 1:4 convergence rates.
                bnameHV20HSL(325),              -- For HONET, N*64 super rate board (N=1~31), of HONET SIPP II/III system.
                                                --Each board provides externally 2 synchronous V.35 interface in the mode of DCE or DTE, and two FE1 interfaces.
                bnameHV20ATI(326),              -- For HONET, analog trunk interface board of HONET SIPP II/III system,
                                                -- used to connect subscriber machines which have only EM interfaces,
                                                -- realizing EM communication transfer in the access network. Each AIT cards provides 6 physical EM ports.
                                                --The slots are compatible with such board slots as ASL, DSL, and VFB.
                bnameHV20SRX(327),              -- For HONET, sub-rate board of HONET SIPP II/III system.
                                                -- Each board provides externally 5 synchronous/asynchronous compatible V.24 interfaces in DCE mode,
                                                -- completing the multiplexing of multiple sub-rate data specified in X.50 and X.58 protocols.
                bnameHV20VFB(328),              -- For HONET, 2 line/4 line voice frequency interface board of HONET SIPP II/III system,
                                                -- providing the private network of the railway dispatching system with private interface board.
                bnameHV20VDM(329),              -- For HONET, a board to stack sound frequencies in HONET SIPP II/III system.
                                                -- It is inserted in the subscriber Frame, and is compatible with other board slots in such cards as ASL,
                                                -- DSL, and VFB. Each VDM board has 16 channels, supporting at most 16 paths of voice frequency tiling.
                bnameHV20CDI(330),              -- For HONET, analog trunk board in HONET SIPP II/III system, supporting DDI service.
                                                -- CDI board may dynamically distribute time slots, and its slots are compatible with the slots of
                                                -- such cards as ASL, DSL, and VFB.
                bnameHV20ASP(331),              -- For HONET, AV5 board of the remote main node of HONET SIPP II/III system (HV20A003 version or above not supportable),.
                bnameHV20DTE(332),              -- For HONET, a new- type 2M bit/s digital trunk interface board of HONET SIPP II/III system.
                                                -- Each board configures 8 2M PCM 30/32 systems.
                bnameHV20WSA(333),              -- For HONET, remote main node board which is wireless connected to ETS450 WLL base station in
                                                -- HONET SIPP II/III system. Each board outputs 2M E1 trunk, mainly used in WSA subscriber Frame.
                                                -- WSA board communicates with the host via RSA protocol, which equals to RSA main node board.
                bnameHV20DTH(334),              -- For HONET, 1.544M bit/s digital leased line interface board of HONET SIPP II/III system.
                                                -- Each board configures 8 1.544M PCM 22/24 systems, providing T1 leased line service.
                bnameHV20ASL32(335),            -- For HONET, a new-type analog subscriber board of HONET SIPP II/III system,
                                                -- which can provide 32 paths of subscriber lines on each board.
                bnameHV20NPU(336),              -- For HONET, net process unit in HONET SIPP II/III system, which can provide 10M Ethernet interface .
                bnameHV20DLI(337),              -- For HONET, DECT interface board, which provide 32 channel for wireless subscriber.
                bnameHV20CKS(338),              -- For HONET, a clock board of HONET SIPP II/III system.
                bnameHV20CKD(339),              -- For HONET, a clock board of HONET SIPP II/III system.
                bnameHV20SBL(340),              -- For HONET, 2B1Q board of HONET SIPP II/III system. Each board provides 8 paths of 2B1Q interfaces,
                                                -- which are used in DDN access.
                bnameHV20MLC(341),              -- For HONET, a new-type SBL board, can be used as both subscriber board and main node board.
                bnameHV20SCS(342),              -- For HONET, SCS board is subrate concentrate switch board that is used with SRX board, MTA port,
                                                -- DE1 Channel, and this board only support connection between subrate of 2.4K, 4.8K, 9.6K, 19.2K.
                bnameHV20HWC(343),              -- For HONET, a signal level convert board, only used for PV8 board in PV8-10 control Frame.
-- MIM & SIC card for router:
                bnameReserverd(400),            -- For router, Reserved board name
                bnameUnknownboard(401),              -- For router, Unknown board
                bnameMIM8AS(402),              -- For router, MIM card with 8 asynchronous serial port
                bnameMIM4SA(403),              -- For router, MIM card with 4 high-speed synchronous/asynchronous serial port
                bnameMIM4BS(404),              -- For router, MIM card with 4 ISDN BRI S/T port
                bnameMIM2E1(405),              -- For router, MIM card with 2 channelized cE1/PRI port
                bnameMIM4E1(406),              -- For router, MIM card with 4 channelized cE1/PRI port
                bnameMIM1FE(407),              -- For router, MIM card with 1 10Base-T/100Base-TX port
                bnameMIM1E1(408),              -- For router, MIM card with 1 channelized cE1/PRI port
                bnameMIM2FE(409),              -- For router, MIM card with 2 10Base-T/100Base-TX port
                bnameMIM2VI(411),              -- For router, MIM card with 2 line voice processing unit
                bnameMIM4VI(412),              -- For router, MIM card with 4 line voice processing unit
                bnameMIM30VI(413),             -- For router, MIM card with 30 line voice processing unit
                bnameMIM2S1B(414),             -- For router, MIM card with 2 synchronous/asynchronous serial port and 1 ISDN BRI S/T port
                bnameMIM2SA(415),              -- For router, MIM card with 2 high-speed synchronous/asynchronous serial port
                bnameMIM16AS(416),             -- For router, MIM card with 16 asynchronous serial port
                bnameMIMnew8AS(417),           -- For router, MIM card with 8 asynchronous serial port (new)
                bnameMIM8LSA(418),             -- For router, MIM card with 8 low-speed synchronous/asynchronous serial port
                bnameMIM2FXS(419),             -- For router, MIM card with 2 FXS port
                bnameMIM2FX0(420),             -- For router, MIM card with 2 FXO port
                bnameMIM2EM(421),              -- For router, MIM card with 2 E&M port
                bnameMIM4FXS(422),             -- For router, MIM card with 4 FXS port
                bnameMIM4FXO(423),             -- For router, MIM card with 4 FXO port
                bnameMIM4EM(424),              -- For router, MIM card with 4 E&M port
                bnameFixedSA(425),             -- For router 2620/2621, 1/2 fixed high-speed synchronous serial port
                bnameMIME1VI(426),             -- For router, MIM card with 1 E1 port for voice processing
                bnameMIM12AM(427),             -- For router, MIM card with 12 analog modem port
                bnameMIM6AM(428),              -- For router, MIM card with 6 analog modem port
                bnameMIMNDEC(429),             -- For router, MIM card for network encryption
                bnameMIMnew2SA(430),           -- For router, MIM card with 2 high-speed synchronous/asynchronous serial port (new)
                bnameFixedAux(431),            -- For router, Fixed Aux port
                bnameFixedConsole(432),        -- For router, Fixed Console Port
                bnameFixedSA1760(433),        -- For router 1760/2610/2611, fixed synchronous/asynchronous serial port
                bnameSIC1FE(434),              -- For router, SIC card with 1 10Base-T/100Base-TX port
                bnameSIC1SA(435),              -- For router, SIC card with 1 high-speed sychronous/asynchronous serial port
                bnameSIC3AS(436),              -- For router, SIC card with 3 asynchronous serial port
                bnameSIC1E1(437),              -- For router, SIC card with 1 channelized cE1/PRI port
                bnameSIC1T1(438),              -- For router, SIC card with 1 channelized cT1/PRI port
                bnameSIC1BU(439),              -- For router, SIC card with 1 ISDN BRI U port
                bnameSIC2BU(440),              -- For router, SIC card with 2 ISDN BRI U port
                bnameSIC1BS(441),              -- For router, SIC card with 1 ISDN BRI S/T port
                bnameSIC2BS(442),              -- For router, SIC card with 2 ISDN BRI S/T port
                bnameSIC1AM(443),              -- For router, SIC card with 1 analog modem port
                bnameSIC2AM(444),              -- For router, SIC card with 2 analog modem port
                bnameSIC1EM(445),              -- For router, SIC card with 1 E&M port
                bnameSIC2EM(446),              -- For router, SIC card with 2 E&M port
                bnameSIC1FXS(447),             -- For router, SIC card with 1 FXS port
                bnameSIC2FXS(448),             -- For router, SIC card with 2 FXS port
                bnameSIC1FXO(449),             -- For router, SIC card with 1 FXO port
                bnameSIC2FXO(450),             -- For router, SIC card with 2 FXO port
                bnameMIM6FCM(451),             -- For router, MIM card with 6 fast connect modem port
                bnameMIM8SA(452),              -- For router, MIM card with 8 high-speed sychronous/asychronous serial port
                bnameMIM1T1(453),              -- For router, MIM card with 1 channelized cT1/PRI port
                bnameMIM2T1(454),              -- For router, MIM card with 2 channelized cT1/PRI port
                bnameMIM4T1(455),              -- For router, MIM card with 4 channelized cT1/PRI port
                bnameMIMT1VI(456),             -- For router, MIM card with 1 T1 port for voice processing
                bnameMIM4FCM(457),             -- For router, MIM card with 4 fast connect modem port
                bnameMIM2FCM(458),             -- For router, MIM card with 2 fast connect modem port
                bnameMIMcE3(459),              -- For router, MIM card with 1 channelized E3 port
                bnameMIM6AME(460),             -- For router, MIM card with 6 analog modem port (new)
                bnameMIM12AME(461),            -- For router, MIM card with 12 analog modem port (new)
                bnameMIM1E1F(465),            -- For router, MIM card with 1 fractional E1 port
                bnameMIM2E1F(466),            -- For router, MIM card with 2 fractional E1 port
                bnameMIM4E1F(467),            -- For router, MIM card with 4 fractional E1 port
                bnameMIM1T1F(468),            -- For router, MIM card with 1 fractional T1 port
                bnameMIM2T1F(469),            -- For router, MIM card with 2 fractional T1 port
                bnameMIM4T1F(470),            -- For router, MIM card with 4 fractional T1 port
                bnameSIC1E1F(471),            -- For router, SIC card with 1 fractional E1 port
                bnameSIC1T1F(472),            -- For router, SIC card with 1 fractional T1 port
                bnameMIMcT3(473),              -- For router, MIM card with 1 channelized T3 port
                bnameMIMATMADSL1(474),        -- For router, MIM card with 1 adsl port
                bnameMIMATMADSL2(475),        -- For router, MIM card with 2 adsl ports
                bnameMIMATM155(476),          -- For router, MIM card with 1 155M port
                bnameMIM8AS701(477),          -- For router, MIM card with 8 asynchronous serial port(using SD701)
                bnameMIM16AS701(478),         -- For router, MIM card with 16 asynchronous serial port(using SD701)
                bnameMIM4SA701(479),          -- For router, MIM card with 4 high-speed synchronous/asynchronous serial port(using SD701)
                bnameMIM2SA701(480),          -- For router, MIM card with 2 high-speed synchronous/asynchronous serial port(using SD701)
-- 8070:
                bnameRTC1RSU(550),              -- RSU process board
                bnameRTC1RSK(551),              -- RSU back board
                bnameRTC2RSUA(552),             -- RSU process board 128M
                bnameRTC2RSUB(553),             -- RSU process board 256M
                bnameRTC2RSUC(554),             -- RSU process board 512M
                bnameRTC2RSEU(555),             -- RSU back board
                bnameRTC1VIU(556),              -- VIU process board
                bnameRTC1BAK(557),              -- VIU back board
                bnameRTC2VIUA(558),             -- VIU process board 128M
                bnameRTC2VIUB(559),             -- VIU process board 256M
                bnameRTC2VIUC(560),             -- VIU process board 512M
                bnameRTC2VIEU(561),             -- VIU back board version 2
                bnameRTC4VIU(562),              -- Enhanced VIU process board
                bnameRTC1HAU(563),              -- HAU
                bnameRTC2HAU(564),              -- HAU version 2
                bnameRTC1SMMU(565),             -- ALU used by NE08
                bnameRTC2ALU(566),              -- ALU used by NE16E, NE08E and NE05
                bnameRTC4VIUA(567),             -- NE05/08/16E front board
                bnameRTC4VIUB(568),             -- NE05/08/16E front board
                bnameRTC4VIUC(569),             -- NE05/08/16E front board
                bnameRTC1RSHC(570),             -- NE05/08/16E board:for ne05 rshc
                bname5FEMP(571),                -- NE05/08/16E board:for imu
                bname2GOMP(572),                -- NE05/08/16E board:for imu
                bname1GOMP(573),                -- NE05/08/16E board:for imu
                bname2GEMP(574),                -- NE05/08/16E board:for imu
                bname1GEMP(575),                -- NE05/08/16E board:for imu
                bname5FEMK(576),                -- NE05/08/16E board:for imu
                bname3FEMK(577),                -- NE05/08/16E board:for imu
                bname2GOMK(578),                -- NE05/08/16E board:for imu
                bname2GEMK(579),                -- NE05/08/16E board:for imu
                bname1GOMK(580),                -- NE05/08/16E board:for imu
                bname1GEMK(581),                -- NE05/08/16E board:for imu
                bnameRTC3RSUB(582),             -- RSU process board 256M version 3
                bnameRTC3RSUC(583),             -- RSU process board 512M version 3
                bnameRTC2VIUS(584),             -- VIU process board 256M,used only by NE05
                bnameRTC3VIUB(585),             -- VIU process board 256M version 3
                bnameRTC8VIUB(586),             -- VIU process board 256M version 8
                bnamePWR(587),                  -- Power supply
                bnameFAN(588),                  -- Fan
                bname3FEMP(589),                -- NE05/08/16E board:for imu front
                bnameRTC2RSUD(590),             -- RSU process board 1G

-- 8011:
                bnameCR01BAKB(600),             -- For NE80, backplane of NE80
                bnameCR01BAKC(601),             -- For NE40-8, backplane of NE40-8
                bnameCR01BAKD(602),             -- For NE40-4, backplane of NE40-4
                bnameCR01BAKE(603),             -- For NE40-2, backplane of NE40-2
                bnameCR01PWRB(604),             -- For NE80, power supply card of NE80
                bnameCR01DPRB(605),             -- For NE80, power destribution card of NE80
                bnameCR01PWRD(606),             -- For NE40, power supply card of NE40
                bnameCR01FANB(607),             -- For NE80, fan card of NE80
                bnameCR01FAND(608),             -- For NE40, fan card of NE40
                bnameCR01MPUB(609),             -- For NE80, main control card of NE80
                bnameCR01SRUB(610),             -- For NE40, main control card of NE40
                bnameCR01NETB(611),             -- For NE80, switch card of NE80
                bnameCR01CLKB(612),             -- For NE80, clock card of NE80
                bnameCR01HUBB(613),             -- For NE80, HUB card of NE80
                bnameCR01LPUB(614),             -- For NE80 & NE40, mother card of NE80 and NE40
                bnameCR01NATB(615),             -- For NE80 & NE40, NAT card of NE80 and NE40

-- MA5300:
                bnameH531ESME(616),             -- Ethernet switching control board. This board differs from the ESMA board in the
                                                -- following way: Subslot 2 of this board supports only electric port FE subboard.
                bnameH531EIUA(617),             -- Upstream service board, which supports a GE subboard
-- MA5100 ADSL boards
                bnameH511Mmxs(620),             -- H511MMXS control board of the MA5100. This board does not provide the clock subboard and the service subboard.
                bnameADLL(627),                 -- 32 port ADSL board over pots
                bnameADC(642),                  -- 32 port ADSL2+ board over pots
                bnameADCA(643),                 -- 32 port ADSL2+ board over pots
                bnameADCB(644),                 -- 32 port ADSL2+ board over pots
                bnameADCC(645),                 -- 32 port ADSL2+ board over pots
                bnameADCD(646),                 -- 32 port ADSL2+ board over pots
                bnameADCE(647),                 -- 32 port ADSL2+ board over pots
                bnameADCF(648),                 -- 32 port ADSL2+ board over pots
                bnameADCG(649),                 -- 32 port ADSL2+ board over pots
                bnameADCH(650),                 -- 32 port ADSL2+ board over pots
                bnameADCI(651),                 -- 32 port ADSL2+ board over pots
                bnameADCJ(652),                 -- 32 port ADSL2+ board over pots
                bnameADCK(653),                 -- 32 port ADSL2+ board over pots
                bnameADCL(654),                 -- 32 port ADSL2+ board over pots
                bnameADCM(655),                 -- 32 port ADSL2+ board over pots
                bnameADCN(656),                 -- 32 port ADSL2+ board over pots
                bnameADCO(657),                 -- 32 port ADSL2+ board over pots
                bnameADCP(658),                 -- 32 port ADSL2+ board over pots
                bnameADCQ(659),                 -- 32 port ADSL2+ board over pots
                bnameADCR(660),                 -- 32 port ADSL2+ board over pots
                bnameADCS(661),                 -- 32 port ADSL2+ board over pots
                bnameADCT(662),                 -- 32 port ADSL2+ board over pots
                bnameADCU(663),                 -- 32 port ADSL2+ board over pots
                bnameADCV(664),                 -- 32 port ADSL2+ board over pots
                bnameADCW(665),                 -- 32 port ADSL2+ board over pots
                bnameADCX(666),                 -- 32 port ADSL2+ board over pots
                bnameADCY(667),                 -- 32 port ADSL2+ board over pots
                bnameADCZ(668),                 -- 32 port ADSL2+ board over pots
                bnameADM(696),                  -- 64 port ADSL2+ board over pots
                bnameADMA(697),                 -- 64 port ADSL2+ board over pots
                bnameADMB(698),                 -- 64 port ADSL2+ board over pots
                bnameADMC(699),                 -- 64 port ADSL2+ board over pots
                bnameADMD(700),                 -- 64 port ADSL2+ board over pots
                bnameADME(701),                 -- 64 port ADSL2+ board over pots
                bnameADMF(702),                 -- 64 port ADSL2+ board over pots
                bnameADMG(703),                 -- 64 port ADSL2+ board over pots
                bnameADMH(704),                 -- 64 port ADSL2+ board over pots
                bnameADMI(705),                 -- 64 port ADSL2+ board over pots
                bnameADMJ(706),                 -- 64 port ADSL2+ board over pots
                bnameADMK(707),                 -- 64 port ADSL2+ board over pots
                bnameADML(708),                 -- 64 port ADSL2+ board over pots
                bnameADMM(709),                 -- 64 port ADSL2+ board over pots
                bnameADMN(710),                 -- 64 port ADSL2+ board over pots
                bnameADMO(711),                 -- 64 port ADSL2+ board over pots
                bnameADMP(712),                 -- 64 port ADSL2+ board over pots
                bnameADMQ(713),                 -- 64 port ADSL2+ board over pots
                bnameADMR(714),                 -- 64 port ADSL2+ board over pots
                bnameADMS(715),                 -- 64 port ADSL2+ board over pots
                bnameADMT(716),                 -- 64 port ADSL2+ board over pots
                bnameADMU(717),                 -- 64 port ADSL2+ board over pots
                bnameADMV(718),                 -- 64 port ADSL2+ board over pots
                bnameADMW(719),                 -- 64 port ADSL2+ board over pots
                bnameADMX(720),                 -- 64 port ADSL2+ board over pots
                bnameADMY(721),                 -- 64 port ADSL2+ board over pots
                bnameADMZ(722),                 -- 64 port ADSL2+ board over pots
                bnameADD(723),                  -- ADSL2+ board of the ADD series
                bnameADDA(724),                 -- ADSL2+ board of the ADD series
                bnameADDB(725),                 -- ADSL2+ board of the ADD series
                bnameADDC(726),                 -- ADSL2+ board of the ADD series
                bnameADDD(727),                 -- ADSL2+ board of the ADD series
                bnameADDE(728),                 -- ADSL2+ board of the ADD series
                bnameADDF(729),                 -- ADSL2+ board of the ADD series
                bnameADDG(730),                 -- ADSL2+ board of the ADD series
                bnameADDH(731),                 -- ADSL2+ board of the ADD series
                bnameADDI(732),                 -- ADSL2+ board of the ADD series
                bnameADDJ(733),                 -- ADSL2+ board of the ADD series
                bnameADDK(734),                 -- ADSL2+ board of the ADD series
                bnameADDL(735),                 -- ADSL2+ board of the ADD series
                bnameADDM(736),                 -- ADSL2+ board of the ADD series
                bnameADDN(737),                 -- ADSL2+ board of the ADD series
                bnameADDO(738),                 -- ADSL2+ board of the ADD series
                bnameADDP(739),                 -- ADSL2+ board of the ADD series
                bnameADDQ(740),                 -- ADSL2+ board of the ADD series
                bnameADDR(741),                 -- ADSL2+ board of the ADD series
                bnameADDS(742),                 -- ADSL2+ board of the ADD series
                bnameADDT(743),                 -- ADSL2+ board of the ADD series
                bnameADDU(744),                 -- ADSL2+ board of the ADD series
                bnameADDV(745),                 -- ADSL2+ board of the ADD series
                bnameADDW(746),                 -- ADSL2+ board of the ADD series
                bnameADDX(747),                 -- ADSL2+ board of the ADD series
                bnameADDY(748),                 -- ADSL2+ board of the ADD series
                bnameADDZ(749),                 -- ADSL2+ board of the ADD series
                bnameH601APMB(750),             -- Control board APMB of the UA5000
                bnameH601APSB(751),             -- Control board of the local slave Frame of the UA5000
                bnameH601APSR(752),             -- Control board of the remote slave Frame of the UA5000
                bnameH561SCU(753),              -- H511SCUA control board of the MA5600. This board supports the PHY/LSW subboard.
                bnameH601IPMB(754),             -- IPMP control board of the UA5000
                bnameH533ECBD(755),             -- 64-port GE bus ADSL2+ board (CoronaG)
                bnameH512ADME(756),             -- 64-port double CELLBUS bus ADSL2+ board (AC7 chipset)
-- UA
                bnameH601CSMB(757),             -- UA5000 ADSL2+ board
                bnameH601EAUA(758),             -- 16-port VDSL board of the UA5000
                bnameH601TSSB(759),             -- Broadband test board of the UA5000
                bnameH601BP2B(760),             -- UA5000 BPON

                bnameADE(761),               --ADSL2+ board of the ADE series
                bnameADEA(762),              --ADSL2+ board of the ADE series
                bnameADEB(763),              --ADSL2+ board of the ADE series
                bnameADEC(764),              --ADSL2+ board of the ADE series
                bnameADED(765),              --ADSL2+ board of the ADE series
                bnameADEE(766),              --ADSL2+ board of the ADE series
                bnameADEF(767),              --ADSL2+ board of the ADE series
                bnameADEG(768),              --ADSL2+ board of the ADE series
                bnameADEH(769),              --ADSL2+ board of the ADE series
                bnameADEI(770),              --ADSL2+ board of the ADE series
                bnameADEJ(771),              --ADSL2+ board of the ADE series
                bnameADEK(772),              --ADSL2+ board of the ADE series
                bnameADEL(773),              --ADSL2+ board of the ADE series
                bnameADEM(774),              --ADSL2+ board of the ADE series
                bnameADEN(775),              --ADSL2+ board of the ADE series
                bnameADEO(776),              --ADSL2+ board of the ADE series
                bnameADEP(777),              --ADSL2+ board of the ADE series
                bnameADEQ(778),              --ADSL2+ board of the ADE series
                bnameADER(779),              --ADSL2+ board of the ADE series
                bnameADES(780),              --ADSL2+ board of the ADE series
                bnameADET(781),              --ADSL2+ board of the ADE series
                bnameADEU(782),              --ADSL2+ board of the ADE series
                bnameADEV(783),              --ADSL2+ board of the ADE series
                bnameADEW(784),              --ADSL2+ board of the ADE series
                bnameADEX(785),              --ADSL2+ board of the ADE series
                bnameADEY(786),              --ADSL2+ board of the ADE series
                bnameADEZ(787),              --ADSL2+ board of the ADE series

                bnameH602CSMB(788),             -- 16-port ADSL2+ broadband and narrowband combo board of the UA5000
                bnameH601ADRB(790),             -- 32-port ADSL2+ board (with a built-in splitter) of the UA5000
                bnameH801X1CA(795),              -- 10 GE optical interface board of the OFA5920

-- MA5300:
                bnameH531EBDC(800),             -- 48-port ADSL over POTS service board (with the built-in splitter)
                bnameH531EBDI(801),             -- 48-port ADSL over ISDN service board (with the built-in splitter)
                bnameH531EADI(802),             -- 48-port ADSL over ISDN service board
                bnameH531EADK(803),             -- 48-port ADSL over ISDN + protection service board
                bnameH531EBDL(804),             -- 24-port ADSL2+ service board
-- PVU
                bnamePVU8(1000),                -- H601PVU
                bnamePVU4(1001),                -- H601PVU
-- RSU
                bnameRSUA(1002),             --H601RSUA, which provides eight E1 ports
                bnameRSUA4(1003),            --H601RSUA, which provides four E1 ports
                bnameH602PWX2(1100),            -- H602PWX2

-- 8060
                bnameDEVUNKNOWN(3700),
                bnameDEVRPU(3701),            -- RPU without NP
                bnameDEVNPRPU(3702),          -- RPU with NP (256M RAM)
                bnameDEVNP(3703),             -- NPU
                bnameDEV6FAN(3704),           -- Board with 6 fans
                bnameDEV8FAN(3705),           -- Board with 8 fans
                bnameDEVPOWER(229031),        -- Power module
                bnameDEVRPUE(3707),           -- RPUE without NP
                bnameDEVNPRPUE(3708),         -- RPUE with NP (512M RAM)
                bnameDEVCOPE(3709),           -- COP card
                bnameDEVCF(3710),             -- CF card
                bnameE200EFAN(3711),
                bnameE200EPWRAC(3712),
                bnameE200EPWRDC(3713),
                fnameE200E(3714),
                bnameE200ERPU(3715),
                bnameE100ERPU(3716),
                bnameUSG3040MBD(3717),
                bnameEXIFE2GE(3718),

                bnameDEVH2FE(3719),           -- HIC 2FE
                bnameDEVHG1GE(3720),          -- 1GE
                bnameDEVHG2GE(3721),          -- 2GE
                bnameDEVH4FE(3722),           -- HIC 4FE
                bnameDEVH8FE(3723),           -- HIC 8FE
                bnameDEVH1POS(3724),          -- 1POS
                bnameDEVH2POS(3725),          -- 2POS
                bnameDEVH4POS(3726),          -- 4POS
                bnameDEVH2FEP(3727),          -- 2FEP
                bnameDEVH4FEP(3728),          -- 4FEP
                bnameDEVH8FEP(3729),          -- 8FEP
                bnameDEVLCPOS(3730),          -- CPOS
                bnameDEVHIPSEC(3731),         -- HIC IPSEC
                bnameDEVHBYPASS(3732),        -- BYPass
                bnameEXIFE2FE(3733),          -- Dual port Fast Ethernet Card
                bnameUSG50RPU(3734),          -- Main Processing Unit
                bnameFW11USBC(3735),          -- Universal Serial Bus Interface Card
                bnameFW41HPSEC(3736),         -- High Speed IP Security Card C
                bnameFW41HPSEA(3737),         -- High Speed IP Security Card A
                bnameFW41GEBY(3738),          -- Gigabit Ethernet Card with Bypass Function
                bnameFW11EPSEA(3739),         -- Enhanced IP Security Card A
                bnameRTM1GEUB(3740),          -- 1-Port 1000M Ethernet Electrical Interface Board(RJ45)
                bnameRTM1GEUA(3741),          -- 1-Port 1000BASE-SX Gigabit Ethernet Interface Board(SFP)
                bnameFW11EPSEC(3742),         -- Enhanced IP Security Card
                bnameFW1IPSEC0(3743),         -- IP Security Card
                bnameFW111AMM0(3744),         -- 1-Port ATM/155M Multimode Interface Module(SC)
                bnameFW111ASM0(3745),         -- 1-Port ATM/155M Single Mode Interface Module(1310nm,15km,SC)
                bnameFW111ADP0(3746),         -- 1-Port ADSL over POTS Interface Board

                bnameDEVLATME1(3749),         -- ATM E1
                bnameDEVLATME3(3750),         -- ATM E3
                bnameDEVLATM(3751),           -- ATM Multimode
                bnameDEVL4SA(3752),           -- 4SA
                bnameDEVLGSFE(3753),          -- 10/100 SingleMode FE
                bnameDEVLGMFE(3754),          -- 10/100 MultiMode FE
                bnameDEVLGGE(3755),           -- FIC GE(Fiber)
                bnameDEVLDGE(3756),           -- FIC GE(Copper)
                bnameDEVL1FE(3757),           -- 1FE
                bnameDEVL2FE(3758),           -- 2FE
                bnameDEVL8E1A(3759),          -- 8E1A
                bnameDEVL8E1B(3760),          -- 8E1B
                bnameDEVL8CE1A(3761),         -- 8CE1A
                bnameDEVL8CE1B(3762),         -- 8CE1B
                bnameDEVL8CT1A(3763),         -- 8CT1A
                bnameDEVL8CT1B(3764),         -- 8CT1B
                bnameDEVL4CE1A(3765),         -- 4CE1A
                bnameDEVL4CE1B(3766),         -- 4CE1B
                bnameDEVL4E1A(3767),          -- 4E1A
                bnameDEVL4E1B(3768),          -- 4E1B
                bnameDEVL4CT1A(3769),         -- 4CT1A
                bnameDEVL4CT1B(3770),         -- 4CT1B
                bnameDEVL4E1(3771),           -- 4E1
                bnameDEVL4CE1(3772),          -- 4CE1
                bnameDEVL4CT1(3773),          -- 4CT1
                bnameDEVL8T1(3774),           -- 8T1
                bnameDEVL1CT3(3775),          -- 1CT3
                bnameDEVL1CE3(3776),          -- 1CE3
                bnameDEVLIPSEC(3777),
                bnameDEVL1HSSI(3778),         -- 1HSSI
                bnameDEVL2HSSI(3779),         -- 2HSSI
                bnameDEVH16CE1A(3780),        -- 16CE1(120 Ohm)
                bnameDEVH16CE1B(3781),        -- 16CE1(75 Ohm)
                bnameDEVH16CT1(3782),         -- 16CT1(120 Ohm)
                bnameDEVHCPE1(3783),          -- 1CPOSE1(ESFP)
                bnameDEVHCPT1(3784),          -- 1CPOST1(ESFP)
                bnameDEVH1ATM(3785),          -- HIC 1ATM(ESFP)
                bnameDEVH2ATM(3786),          -- HIC 2ATM(ESFP)
                bnameDEVH4ATM(3787),          -- HIC 4ATM(ESFP)
                bnameDEVLCT3(3788),             -- 1-port T3/CT3 low-rate interface board
                bnameDEVLE8I(3789),             -- 8-port IMA E1 low-rate interface board (75 ohms)
                bnameDEVLE8IA(3790),            -- 8-port IMA E1 low-rate interface board (120 ohms)
                bnameDEVLT8I(3791),             -- 8-port IMA T1 low-rate interface board
                bnameDEVLIPSECSD707(3792),    -- FIC IPSEC(SD707)
                bnameNE20RPU(3793),           -- NE20 RPU (512M RAM)
                bnameNE20ERPU(3794),          -- NE20E RPU (1G RAM)
                bnameNE20ENPU(3795),          -- NE20E NPU
                bnameNE20EFAN(3796),          -- NE20E FAN
                bnameNE20EPOWERAC(3797),      -- NE20E AC POWER
                bnameNE20EPOWERDC(3798),      -- NE20E DC POWER
                bnameDEVLATMSM(3799),         -- ATM Singlemode
                bnameDEVLATMSL(3800),         -- ATM Singlemode Long Reach
                bnameDEVHG2GESFPCOPR(3810),   -- 2GE SFP&COPR
                bnameDEVH3E3(3811),           -- HIC 3E3
                bnameDEVH3T3(3812),           -- HIC 3T3
                bnameDEVH8GEF(3813),           -- HIC 8GE COPER
                bnameDEVH8GFF(3814),           -- HIC 8GE SFP

-- MA5100
                bnameH563ECBD(131082),          -- 64-port ADSL2+ board

                bnameH561EIUB(131083),             -- EIUB board

                bnameADB(131084),               --ADSL2+ board of the ADB series
                bnameH561ADBA(131085),              --ADSL2+ board of the ADB series
                bnameH561ADBB(131086),              --ADSL2+ board of the ADB series
                bnameH561ADBC(131087),              --ADSL2+ board of the ADB series
                bnameH561ADBD(131088),              --ADSL2+ board of the ADB series
                bnameH561ADBE(131089),              --ADSL2+ board of the ADB series
                bnameH561ADBF(131090),              --ADSL2+ board of the ADB series
                bnameH561ADBG(131091),              --ADSL2+ board of the ADB series
                bnameH561ADBH(131092),              --ADSL2+ board of the ADB series
                bnameH561ADBI(131093),              --ADSL2+ board of the ADB series
                bnameH561ADBJ(131094),              --ADSL2+ board of the ADB series
                bnameH561ADBK(131095),              --ADSL2+ board of the ADB series
                bnameH561ADBL(131096),              --ADSL2+ board of the ADB series
                bnameH561ADBM(131097),              --ADSL2+ board of the ADB series
                bnameH561ADBN(131098),              --ADSL2+ board of the ADB series
                bnameH561ADBO(131099),              --ADSL2+ board of the ADB series
                bnameH561ADBP(131100),              --ADSL2+ board of the ADB series
                bnameH561ADBQ(131101),              --ADSL2+ board of the ADB series
                bnameH561ADBR(131102),              --ADSL2+ board of the ADB series
                bnameH561ADBS(131103),              --ADSL2+ board of the ADB series
                bnameH561ADBT(131104),              --ADSL2+ board of the ADB series
                bnameH561ADBU(131105),              --ADSL2+ board of the ADB series
                bnameH561ADBV(131106),              --ADSL2+ board of the ADB series
                bnameH561ADBW(131107),              --ADSL2+ board of the ADB series
                bnameH561ADBX(131108),              --ADSL2+ board of the ADB series
                bnameH561ADBY(131109),              --ADSL2+ board of the ADB series
                bnameH561ADBZ(131110),              --ADSL2+ board of the ADB series

                bnameH561SHEA(131111),              --H561SHEA service board of the MA5600. This board uses the GE bus and provides 32 ports
                bnameH561SCUK(131112),              -- SCUK control board of the MA5600. Compared with the SCUA control board,
                                                    -- the SCUK control board does not provide the LSW/PHY subboard and the clock subboard.

                bnameADG(131113),               -- 32-port GE bus ADSL2+ board of the ADG series
                bnameADGA(131114),              -- 32-port GE bus ADSL2+ board of the ADG series
                bnameADGB(131115),              -- 32-port GE bus ADSL2+ board of the ADG series
                bnameADGC(131116),              -- 32-port GE bus ADSL2+ board of the ADG series
                bnameADGD(131117),              -- 32-port GE bus ADSL2+ board of the ADG series
                bnameADGE(131118),              -- 32-port GE bus ADSL2+ board of the ADG series
                bnameADGF(131119),              -- 32-port GE bus ADSL2+ board of the ADG series
                bnameADGG(131120),              -- 32-port GE bus ADSL2+ board of the ADG series
                bnameADGH(131121),              -- 32-port GE bus ADSL2+ board of the ADG series
                bnameADGI(131122),              -- 32-port GE bus ADSL2+ board of the ADG series
                bnameADGJ(131123),              -- 32-port GE bus ADSL2+ board of the ADG series
                bnameADGK(131124),              -- 32-port GE bus ADSL2+ board of the ADG series
                bnameADGL(131125),              -- 32-port GE bus ADSL2+ board of the ADG series
                bnameADGM(131126),              -- 32-port GE bus ADSL2+ board of the ADG series
                bnameADGN(131127),              -- 32-port GE bus ADSL2+ board of the ADG series
                bnameADGO(131128),              -- 32-port GE bus ADSL2+ board of the ADG series
                bnameADGP(131129),              -- 32-port GE bus ADSL2+ board of the ADG series
                bnameADGQ(131130),              -- 32-port GE bus ADSL2+ board of the ADG series
                bnameADGR(131131),              -- 32-port GE bus ADSL2+ board of the ADG series
                bnameADGS(131132),              -- 32-port GE bus ADSL2+ board of the ADG series
                bnameADGT(131133),              -- 32-port GE bus ADSL2+ board of the ADG series
                bnameADGU(131134),              -- 32-port GE bus ADSL2+ board of the ADG series
                bnameADGV(131135),              -- 32-port GE bus ADSL2+ board of the ADG series
                bnameADGW(131136),              -- 32-port GE bus ADSL2+ board of the ADG series
                bnameADGX(131137),              -- 32-port GE bus ADSL2+ board of the ADG series
                bnameADGY(131138),              -- 32-port GE bus ADSL2+ board of the ADG series
                bnameADGZ(131139),              -- 32-port GE bus ADSL2+ board of the ADG series

                bnameH561VDEA(131140),          -- 64-port GE bus board: VDEA
                bnameH561AIUG(131141),          -- GE bus AIU board of the MA5600
                bnameH561SPLF(131142),          -- Passive ADSL2+ over POTS SPL board, with an impedance of 600 ohms
                bnameH561SPLH(131143),          -- Passive ADSL2+ over ISDN SPL board
                bnameH561SPLL(131144),          -- Passive ADSL2+ over POTS SPL board, with complex impedance

                bnameH511ECUA(131150),          -- ECUA control board of the MA5100 V3

                bnameH511LANE(131151),          -- LANE board of the MA5100
-- MA5105 from 0X20F00 ~0X20Fff
                bnameH521mfea(134912),          -- FE electric port upstream board, which supports 64 ports
                bnameH521mfoa(134913),          -- FE optical port upstream board, which supports 64 ports
                bnameH521mimb(134914),          -- IMA upstream board, which supports 64 ports
                bnameH521mcoa(134915),          -- 155M optical port upstream board, which supports 64 ports
                bnameH521mgoa(134916),          -- GE optical port upstream board, which supports 64 ports
                bnameH523adla(134928),          -- ADLA board, which supports 16 ports

--  MA5200 add definitiong of board type 0x21000(135168) ~ 0x21FFF(139263)
                bnameH521SMU(135168),
                bnameH521CLK(135169),
                bnameH521PWR(135170),
                bnameH521DPR(135171),
                bnameH521FAN(135172),
                bnameH521DRYPWR(135173),
                bnameH521DRYFAN(135174),
                bnameH521SFU(135175),
                bnameH521SFUF(135176),
                bnameH521SSU(135177),
                bnameH521SPU(135178),
                bnameH522SFUT(135179),
                bnameH522SPUT(135180),
                bnameH522SSUT(135181),
                bnameH522SPUF(135182),
                bnameH522SSUF(135183),
                bnameH521SMUE(135184),
                bnameH523SMUG(135185),
                bnameH521NSBD(135186),
                bnameH523SFUG(135187),
-- MA5600

                bnameH801SCUA(143360),          -- Broadband control board H801SCUA of the P300
                bnameH801SPLK(143361),          -- SPL board H801SPLK of the P300
                bnameH801SPMA(143362),          -- Control board of the SPL series boards of the P300
                bnameH805ADLL(143363),          -- P300 ADSL board
                bnameH802SHLA(143364),          -- SHDSL board H802SHLA of the P300
                bnameH801AIUG(143365),          -- ATM interface board H801AIUG of the P300

                bnameADI(143366),               -- P300 32-channel ADSL boards of the ADI series
                bnameADIA(143367),          -- P300 32-channel ADSL board of the ADI series
                bnameADIB(143368),          -- P300 32-channel ADSL board of the ADI series
                bnameADIC(143369),          -- P300 32-channel ADSL board of the ADI series
                bnameADID(143370),          -- P300 32-channel ADSL board of the ADI series
                bnameADIE(143371),          -- P300 32-channel ADSL board of the ADI series
                bnameADIF(143372),          -- P300 32-channel ADSL board of the ADI series
                bnameADIG(143373),          -- P300 32-channel ADSL board of the ADI series
                bnameADIH(143374),          -- P300 32-channel ADSL board of the ADI series
                bnameADII(143375),          -- P300 32-channel ADSL board of the ADI series
                bnameADIJ(143376),          -- P300 32-channel ADSL board of the ADI series
                bnameADIK(143377),          -- P300 32-channel ADSL board of the ADI series
                bnameADIM(143378),          -- P300 32-channel ADSL board of the ADI series
                bnameADIN(143379),          -- P300 32-channel ADSL board of the ADI series
                bnameADIL(143380),          -- P300 32-channel ADSL board of the ADI series
                bnameADIO(143381),          -- P300 32-channel ADSL board of the ADI series
                bnameADIP(143382),          -- P300 32-channel ADSL board of the ADI series
                bnameADIQ(143383),          -- P300 32-channel ADSL board of the ADI series
                bnameADIR(143384),          -- P300 32-channel ADSL board of the ADI series
                bnameADIS(143385),          -- P300 32-channel ADSL board of the ADI series
                bnameADIT(143386),          -- P300 32-channel ADSL board of the ADI series
                bnameADIU(143387),          -- P300 32-channel ADSL board of the ADI series
                bnameADIV(143388),          -- P300 32-channel ADSL board of the ADI series
                bnameADIW(143389),          -- P300 32-channel ADSL board of the ADI series
                bnameADIX(143390),          -- P300 32-channel ADSL board of the ADI series
                bnameADIY(143391),          -- P300 32-channel ADSL board of the ADI series
                bnameADIZ(143392),          -- P300 32-channel ADSL board of the ADI series

                bnameADL(143393),                -- P300 32-channel ADSL board of the ADL series
                bnameADLA(143394),           -- P300 32-channel ADSL board of the ADL series
                bnameADLB(143395),           -- P300 32-channel ADSL board of the ADL series
                bnameADLC(143396),           -- P300 32-channel ADSL board of the ADL series
                bnameADLD(143397),           -- P300 32-channel ADSL board of the ADL series
                bnameADLE(143398),           -- P300 32-channel ADSL board of the ADL series
                bnameADLF(143399),           -- P300 32-channel ADSL board of the ADL series
                bnameADLG(143400),           -- P300 32-channel ADSL board of the ADL series
                bnameADLH(143401),           -- P300 32-channel ADSL board of the ADL series
                bnameADLI(143402),           -- P300 32-channel ADSL board of the ADL series
                bnameADLJ(143403),           -- P300 32-channel ADSL board of the ADL series
                bnameADLK(143404),           -- P300 32-channel ADSL board of the ADL series
                bnameADLM(143405),           -- P300 32-channel ADSL board of the ADL series
                bnameADLN(143406),           -- P300 32-channel ADSL board of the ADL series
                bnameADLO(143407),           -- P300 32-channel ADSL board of the ADL series
                bnameADLP(143408),           -- P300 32-channel ADSL board of the ADL series
                bnameADLQ(143409),           -- P300 32-channel ADSL board of the ADL series
                bnameADLR(143410),           -- P300 32-channel ADSL board of the ADL series
                bnameADLS(143411),           -- P300 32-channel ADSL board of the ADL series
                bnameADLT(143412),           -- P300 32-channel ADSL board of the ADL series
                bnameADLU(143413),           -- P300 32-channel ADSL board of the ADL series
                bnameADLV(143414),           -- P300 32-channel ADSL board of the ADL series
                bnameADLW(143415),           -- P300 32-channel ADSL board of the ADL series
                bnameADLX(143416),           -- P300 32-channel ADSL board of the ADL series
                bnameADLY(143417),           -- P300 32-channel ADSL board of the ADL series
                bnameADLZ(143418),           -- P300 32-channel ADSL board of the ADL series

                bnameSHD(143419),            -- P300 16-channel GDOT boards of the SHD series
                bnameSHDA(143420),           -- P300 16-channel GDOT board of the SHD series
                bnameSHDB(143421),           -- P300 16-channel GDOT board of the SHD series
                bnameSHDC(143422),           -- P300 16-channel GDOT board of the SHD series
                bnameSHDD(143423),           -- P300 16-channel GDOT board of the SHD series
                bnameSHDE(143424),           -- P300 16-channel GDOT board of the SHD series
                bnameSHDF(143425),           -- P300 16-channel GDOT board of the SHD series
                bnameSHDG(143426),           -- P300 16-channel GDOT board of the SHD series
                bnameSHDH(143427),           -- P300 16-channel GDOT board of the SHD series
                bnameSHDI(143428),           -- P300 16-channel GDOT board of the SHD series
                bnameSHDJ(143429),           -- P300 16-channel GDOT board of the SHD series
                bnameSHDK(143430),           -- P300 16-channel GDOT board of the SHD series
                bnameSHDL(143431),           -- P300 16-channel GDOT board of the SHD series
                bnameSHDM(143432),           -- P300 16-channel GDOT board of the SHD series
                bnameSHDN(143433),           -- P300 16-channel GDOT board of the SHD series
                bnameSHDO(143434),           -- P300 16-channel GDOT board of the SHD series
                bnameSHDP(143435),           -- P300 16-channel GDOT board of the SHD series
                bnameSHDQ(143436),           -- P300 16-channel GDOT board of the SHD series
                bnameSHDR(143437),           -- P300 16-channel GDOT board of the SHD series
                bnameSHDS(143438),           -- P300 16-channel GDOT board of the SHD series
                bnameSHDT(143439),           -- P300 16-channel GDOT board of the SHD series
                bnameSHDU(143440),           -- P300 16-channel GDOT board of the SHD series
                bnameSHDV(143441),           -- P300 16-channel GDOT board of the SHD series
                bnameSHDW(143442),           -- P300 16-channel GDOT board of the SHD series
                bnameSHDX(143443),           -- P300 16-channel GDOT board of the SHD series
                bnameSHDY(143444),           -- P300 16-channel GDOT board of the SHD series
                bnameSHDZ(143445),           -- P300 16-channel GDOT board of the SHD series
                bnameH80ASHLM(143446),       -- P300 16-channel GDOT board
                bnameSHG(143447),            -- P300 32-channel G.SHDSL board of the SHG series
                bnameADK(143500),            -- P300 64-channel ADSL2 board of the ADK series
                bnameH521mcca(143600),       -- Control board of the MA5605. This board provides 155M optical port in upstream,
                                             -- provides 64 channels, and supports subtending.

                bnameH801SPLG1(143700),      -- Board in the P300 SPL Frame. This board is used to separate the ADSL
                                             -- signals from the POTS signals. Its function is similar to the function
                                             -- of H801SPLK or H801SPLG2.
                bnameH801SPLG2(143701),      -- Board in the P300 SPL Frame. This board is used to separate the ADSL signals
                                             -- from the POTS signals. Its function is similar to the function of H801SPLK or H801SPLG1.
                bnameH801BSPA(143702),       -- Board in the P300 SPL Frame. This board is used to realize the N+1 backup of boards.

                bnameVDL(143703),        -- P300 32-channel boards of the VDSL series
                bnameVDLA(143704),        -- P300 32-channel board of the VDSL series
                bnameVDLB(143705),        -- P300 32-channel board of the VDSL series
                bnameVDLC(143706),        -- P300 32-channel board of the VDSL series
                bnameVDLD(143707),        -- P300 32-channel board of the VDSL series
                bnameVDLE(143708),        -- P300 32-channel board of the VDSL series
                bnameVDLF(143709),        -- P300 32-channel board of the VDSL series
                bnameVDLG(143710),        -- P300 32-channel board of the VDSL series
                bnameVDLH(143711),        -- P300 32-channel board of the VDSL series
                bnameVDLI(143712),        -- P300 32-channel board of the VDSL series
                bnameVDLJ(143713),        -- P300 32-channel board of the VDSL series
                bnameVDLK(143714),        -- P300 32-channel board of the VDSL series
                bnameVDLL(143715),        -- P300 32-channel board of the VDSL series
                bnameVDLM(143716),        -- P300 32-channel board of the VDSL series
                bnameVDLN(143717),        -- P300 32-channel board of the VDSL series
                bnameVDLO(143718),        -- P300 32-channel board of the VDSL series
                bnameVDLP(143719),        -- P300 32-channel board of the VDSL series
                bnameVDLQ(143720),        -- P300 32-channel board of the VDSL series
                bnameVDLR(143721),        -- P300 32-channel board of the VDSL series
                bnameVDLS(143722),        -- P300 32-channel board of the VDSL series
                bnameVDLT(143723),        -- P300 32-channel board of the VDSL series
                bnameVDLU(143724),        -- P300 32-channel board of the VDSL series
                bnameVDLV(143725),        -- P300 32-channel board of the VDSL series
                bnameVDLW(143726),        -- P300 32-channel board of the VDSL series
                bnameVDLX(143727),        -- P300 32-channel board of the VDSL series
                bnameVDLY(143728),        -- P300 32-channel board of the VDSL series
                bnameVDLZ(143729),        -- P300 32-channel board of the VDSL series

                bnameH803CVD(143730),         -- P300 16-channel boards of the VDSL series
                bnameH803CVDA(143731),        -- P300 16-channel board of the VDSL series
                bnameH803CVDB(143732),        -- P300 16-channel board of the VDSL series
                bnameH803CVDC(143733),        -- P300 16-channel board of the VDSL series
                bnameH803CVDD(143734),        -- P300 16-channel board of the VDSL series
                bnameH803CVDE(143735),        -- P300 16-channel board of the VDSL series
                bnameH803CVDF(143736),        -- P300 16-channel board of the VDSL series
                bnameH803CVDG(143737),        -- P300 16-channel board of the VDSL series
                bnameH803CVDH(143738),        -- P300 16-channel board of the VDSL series
                bnameH803CVDI(143739),        -- P300 16-channel board of the VDSL series
                bnameH803CVDJ(143740),        -- P300 16-channel board of the VDSL series
                bnameH803CVDK(143741),        -- P300 16-channel board of the VDSL series
                bnameH803CVDL(143742),        -- P300 16-channel board of the VDSL series
                bnameH803CVDM(143743),        -- P300 16-channel board of the VDSL series
                bnameH803CVDN(143744),        -- P300 16-channel board of the VDSL series
                bnameH803CVDO(143745),        -- P300 16-channel board of the VDSL series
                bnameH803CVDP(143746),        -- P300 16-channel board of the VDSL series
                bnameH803CVDQ(143747),        -- P300 16-channel board of the VDSL series
                bnameH803CVDR(143748),        -- P300 16-channel board of the VDSL series
                bnameH803CVDS(143749),        -- P300 16-channel board of the VDSL series
                bnameH803CVDT(143750),        -- P300 16-channel board of the VDSL series
                bnameH803CVDU(143751),        -- P300 16-channel board of the VDSL series
                bnameH803CVDV(143752),        -- P300 16-channel board of the VDSL series
                bnameH803CVDW(143753),        -- P300 16-channel board of the VDSL series
                bnameH803CVDX(143754),        -- P300 16-channel board of the VDSL series
                bnameH803CVDY(143755),        -- P300 16-channel board of the VDSL series
                bnameH803CVDZ(143756),        -- P300 16-channel board of the VDSL series

                bnameH805CAN(143757),         -- P300 KPN 16-channel board of the ADSL series
                bnameH805CANA(143758),        -- P300 KPN 16-channel board of the ADSL series
                bnameH805CANB(143759),        -- P300 KPN 16-channel board of the ADSL series
                bnameH805CANC(143760),        -- P300 KPN 16-channel board of the ADSL series
                bnameH805CAND(143761),        -- P300 KPN 16-channel board of the ADSL series
                bnameH805CANE(143762),        -- P300 KPN 16-channel board of the ADSL series
                bnameH805CANF(143763),        -- P300 KPN 16-channel board of the ADSL series
                bnameH805CANG(143764),        -- P300 KPN 16-channel board of the ADSL series
                bnameH805CANH(143765),        -- P300 KPN 16-channel board of the ADSL series
                bnameH805CANI(143766),        -- P300 KPN 16-channel board of the ADSL series
                bnameH805CANJ(143767),        -- P300 KPN 16-channel board of the ADSL series
                bnameH805CANK(143768),        -- P300 KPN 16-channel board of the ADSL series
                bnameH805CANL(143769),        -- P300 KPN 16-channel board of the ADSL series
                bnameH805CANM(143770),        -- P300 KPN 16-channel board of the ADSL series
                bnameH805CANN(143771),        -- P300 KPN 16-channel board of the ADSL series
                bnameH805CANO(143772),        -- P300 KPN 16-channel board of the ADSL series
                bnameH805CANP(143773),        -- P300 KPN 16-channel board of the ADSL series
                bnameH805CANQ(143774),        -- P300 KPN 16-channel board of the ADSL series
                bnameH805CANR(143775),        -- P300 KPN 16-channel board of the ADSL series
                bnameH805CANS(143776),        -- P300 KPN 16-channel board of the ADSL series
                bnameH805CANT(143777),        -- P300 KPN 16-channel board of the ADSL series
                bnameH805CANU(143778),        -- P300 KPN 16-channel board of the ADSL series
                bnameH805CANV(143779),        -- P300 KPN 16-channel board of the ADSL series
                bnameH805CANW(143780),        -- P300 KPN 16-channel board of the ADSL series
                bnameH805CANX(143781),        -- P300 KPN 16-channel board of the ADSL series
                bnameH805CANY(143782),        -- P300 KPN 16-channel board of the ADSL series
                bnameH805CANZ(143783),        -- P300 KPN 16-channel board of the ADSL series

                bnameH805CAL(143784),         -- P300 KPN 32-channel boards of the ADSL series
                bnameH805CALA(143785),        -- P300 KPN 32-channel board of the ADSL series
                bnameH805CALB(143786),        -- P300 KPN 32-channel board of the ADSL series
                bnameH805CALC(143787),        -- P300 KPN 32-channel board of the ADSL series
                bnameH805CALD(143788),        -- P300 KPN 32-channel board of the ADSL series
                bnameH805CALE(143789),        -- P300 KPN 32-channel board of the ADSL series
                bnameH805CALF(143790),        -- P300 KPN 32-channel board of the ADSL series
                bnameH805CALG(143791),        -- P300 KPN 32-channel board of the ADSL series
                bnameH805CALH(143792),        -- P300 KPN 32-channel board of the ADSL series
                bnameH805CALI(143793),        -- P300 KPN 32-channel board of the ADSL series
                bnameH805CALJ(143794),        -- P300 KPN 32-channel board of the ADSL series
                bnameH805CALK(143795),        -- P300 KPN 32-channel board of the ADSL series
                bnameH805CALL(143796),        -- P300 KPN 32-channel board of the ADSL series
                bnameH805CALM(143797),        -- P300 KPN 32-channel board of the ADSL series
                bnameH805CALN(143798),        -- P300 KPN 32-channel board of the ADSL series
                bnameH805CALO(143799),        -- P300 KPN 32-channel board of the ADSL series
                bnameH805CALP(143800),        -- P300 KPN 32-channel board of the ADSL series
                bnameH805CALQ(143801),        -- P300 KPN 32-channel board of the ADSL series
                bnameH805CALR(143802),        -- P300 KPN 32-channel board of the ADSL series
                bnameH805CALS(143803),        -- P300 KPN 32-channel board of the ADSL series
                bnameH805CALT(143804),        -- P300 KPN 32-channel board of the ADSL series
                bnameH805CALU(143805),        -- P300 KPN 32-channel board of the ADSL series
                bnameH805CALV(143806),        -- P300 KPN 32-channel board of the ADSL series
                bnameH805CALW(143807),        -- P300 KPN 32-channel board of the ADSL series
                bnameH805CALX(143808),        -- P300 KPN 32-channel board of the ADSL series
                bnameH805CALY(143809),        -- P300 KPN 32-channel board of the ADSL series
                bnameH805CALZ(143810),        -- P300 KPN 32-channel board of the ADSL series

                bnameH801GICA(143811),        -- P300 KPN general interface board
                bnameH801GICB(143812),        -- P300 KPN general interface board
                bnameH801FICA(143813),        -- P300 KPN general interface board
                bnameH801PRTA(143814),        -- P300 power board H801PRTA
                bnameH801CITA(143815),        -- P300 cable routing board H801CITA
                bnameH801PRTS(143816),        -- P300 power board H801PRTS
                bnameH801CITS(143817),        -- P300 cable routing board H801CITS

                bnameH80xVDS(143818),         -- P300 24-channel boards of the VDSL2 over POTS series
                bnameH80xVDSA(143819),        -- P300 24-channel board of the VDSL2 over POTS series
                bnameH80xVDSB(143820),        -- P300 24-channel board of the VDSL2 over POTS series
                bnameH80xVDSC(143821),        -- P300 24-channel board of the VDSL2 over POTS series
                bnameH80xVDSD(143822),        --P300 24-channel board of the VDSL2 over POTS series
                bnameH80xVDSE(143823),        -- P300 24-channel board of the VDSL2 over POTS series
                bnameH80xVDSF(143824),        -- P300 24-channel board of the VDSL2 over POTS series
                bnameH80xVDSG(143825),        -- P300 24-channel board of the VDSL2 over POTS series
                bnameH80xVDSH(143826),        -- P300 24-channel board of the VDSL2 over POTS series
                bnameH80xVDSI(143827),        -- P300 24-channel board of the VDSL2 over POTS series
                bnameH80xVDSJ(143828),        -- P300 24-channel board of the VDSL2 over POTS series
                bnameH80xVDSK(143829),        -- P300 24-channel board of the VDSL2 over POTS series
                bnameH80xVDSL(143830),        -- P300 24-channel board of the VDSL2 over POTS series
                bnameH80xVDSM(143831),        -- P300 24-channel board of the VDSL2 over POTS series
                bnameH80xVDSN(143832),        -- P300 24-channel board of the VDSL2 over POTS series
                bnameH80xVDSO(143833),        -- P300 24-channel board of the VDSL2 over POTS series
                bnameH80xVDSP(143834),        -- P300 24-channel board of the VDSL2 over POTS series
                bnameH80xVDSQ(143835),        -- P300 24-channel board of the VDSL2 over POTS series
                bnameH80xVDSR(143836),        -- P300 24-channel board of the VDSL2 over POTS series
                bnameH80xVDSS(143837),        -- P300 24-channel board of the VDSL2 over POTS series
                bnameH80xVDST(143838),        -- P300 24-channel board of the VDSL2 over POTS series
                bnameH80xVDSU(143839),        -- P300 24-channel board of the VDSL2 over POTS series
                bnameH80xVDSV(143840),        -- P300 24-channel board of the VDSL2 over POTS series
                bnameH80xVDSW(143841),        -- P300 24-channel board of the VDSL2 over POTS series
                bnameH80xVDSX(143842),        -- P300 24-channel board of the VDSL2 over POTS series
                bnameH80xVDSY(143843),        -- P300 24-channel board of the VDSL2 over POTS series
                bnameH80xVDSZ(143844),        -- P300 24-channel board of the VDSL2 over POTS series

                bnameH80xVDT(143845),         -- P300 24-channel boards of the VDSL2 over ISDN series
                bnameH80xVDTA(143846),        -- P300 24-channel board of the VDSL2 over ISDN series
                bnameH80xVDTB(143847),        -- P300 24-channel board of the VDSL2 over ISDN series
                bnameH80xVDTC(143848),        -- P300 24-channel board of the VDSL2 over ISDN series
                bnameH80xVDTD(143849),        -- P300 24-channel board of the VDSL2 over ISDN series
                bnameH80xVDTE(143850),        -- P300 24-channel board of the VDSL2 over ISDN series
                bnameH80xVDTF(143851),        -- P300 24-channel board of the VDSL2 over ISDN series
                bnameH80xVDTG(143852),        -- P300 24-channel board of the VDSL2 over ISDN series
                bnameH80xVDTH(143853),        -- P300 24-channel board of the VDSL2 over ISDN series
                bnameH80xVDTI(143854),        -- P300 24-channel board of the VDSL2 over ISDN series
                bnameH80xVDTJ(143855),        -- P300 24-channel board of the VDSL2 over ISDN series
                bnameH80xVDTK(143856),        -- P300 24-channel board of the VDSL2 over ISDN series
                bnameH80xVDTL(143857),        -- P300 24-channel board of the VDSL2 over ISDN series
                bnameH80xVDTM(143858),        -- P300 24-channel board of the VDSL2 over ISDN series
                bnameH80xVDTN(143859),        -- P300 24-channel board of the VDSL2 over ISDN series
                bnameH80xVDTO(143860),        -- P300 24-channel board of the VDSL2 over ISDN series
                bnameH80xVDTP(143861),        -- P300 24-channel board of the VDSL2 over ISDN series
                bnameH80xVDTQ(143862),        -- P300 24-channel board of the VDSL2 over ISDN series
                bnameH80xVDTR(143863),        -- P300 24-channel board of the VDSL2 over ISDN series
                bnameH80xVDTS(143864),        -- P300 24-channel board of the VDSL2 over ISDN series
                bnameH80xVDTT(143865),        -- P300 24-channel board of the VDSL2 over ISDN series
                bnameH80xVDTU(143866),        -- P300 24-channel board of the VDSL2 over ISDN series
                bnameH80xVDTV(143867),        -- P300 24-channel board of the VDSL2 over ISDN series
                bnameH80xVDTW(143868),        -- P300 24-channel board of the VDSL2 over ISDN series
                bnameH80xVDTX(143869),        -- P300 24-channel board of the VDSL2 over ISDN series
                bnameH80xVDTY(143870),        -- P300 24-channel board of the VDSL2 over ISDN series
                bnameH80xVDTZ(143871),        -- P300 24-channel board of the VDSL2 over ISDN series
                bnameH801OPFA(143872),        -- P300 16-channel GE bus Ethernet FE optical access board
                bnameH801GICD(143873),        -- P300 4GE optical interface upstream board
                bnameH801GICE(143874),        -- P300 4GE electric interface upstream board
                bnameH801FICB(143875),        -- P300 FE optical interface upstream board

                bnameH801MCUA(143877),        -- Broadband control board H801MCUA of the MA5606T
                bnameH801MPWA(143878),        -- Power board H801MPWA of the MA5606T

                bnameH801ETHA(143879),        -- Ethernet subtend interface board of the MA5600T
                bnameH801MFGA(143880),        -- MPLS service board of the MA5600T

                bnameH801SPLE(143881),         -- SPL boards (with the CPU) of the SPLE series of the MA5600T
                bnameH801SPLE1(143882),        -- SPL board (with the CPU) of the SPLE series of the MA5600T
                bnameH801SPLE2(143883),        -- SPL board (with the CPU) of the SPLE series of the MA5600T
                bnameH801SPLE3(143884),        -- SPL board (with the CPU) of the SPLE series of the MA5600T
                bnameH801SPLE4(143885),        -- SPL board (with the CPU) of the SPLE series of the MA5600T

                bnameH801MCUB(143886),        -- Broadband control board for the slave Frame of the MA5606T: H801MCUB

                bnameH801BIUA(143887),        -- Board of the MA5600T. This board provides two BITS input ports
                                              -- and one BITS output port, and supports the optional configuration of the H801CKMA subboard.
                bnameH802DSRE(143888),        -- 32-channel ISDN service board of the MA5600T
                bnameH802DSRD(143889),        -- 32-channel ISDN service board of the MA5600T
                bnameH80XVDR(143890),         -- P300 24 ports VDSL2 OVER POTS series board
                bnameH801ETHB(143891),        -- Ethernet subtend interface board of the MA5600T
                bnameH80XVDJ(143892),         -- 48-channel boards of the VDSL series of the MA5600

                bnameH561EPBA(145920),        -- EPBA board of the OFA5920&MA5600. This board provides 1, 2, or 4 EPON ports.
                bnameH565VDE(145921),         -- 32-channel boards of the VDSL series of the MA5600
                bnameH565VDEA(145922),        -- 32-channel board of the VDSL series of the MA5600
                bnameH565VDEC(145924),        -- 32-channel board of the VDSL series of the MA5600
                bnameH565VDED(145925),        -- 32-channel board of the VDSL series of the MA5600
                bnameH565VDEE(145926),        -- 32-channel board of the VDSL series of the MA5600
                bnameH565VDEF(145927),        -- 32-channel board of the VDSL series of the MA5600
                bnameH565VDEG(145928),        -- 32-channel board of the VDSL series of the MA5600
                bnameH565VDEH(145929),        -- 32-channel board of the VDSL series of the MA5600
                bnameH565VDEI(145930),        -- 32-channel board of the VDSL series of the MA5600
                bnameH565VDEJ(145931),        -- 32-channel board of the VDSL series of the MA5600
                bnameH565VDEK(145932),        -- 32-channel board of the VDSL series of the MA5600
                bnameH565VDEL(145933),        -- 32-channel board of the VDSL series of the MA5600
                bnameH565VDEM(145934),        -- 32-channel board of the VDSL series of the MA5600
                bnameH565VDEN(145935),        -- 32-channel board of the VDSL series of the MA5600
                bnameH565VDEO(145936),        -- 32-channel board of the VDSL series of the MA5600
                bnameH565VDEP(145937),        -- 32-channel board of the VDSL series of the MA5600
                bnameH565VDEQ(145938),        -- 32-channel board of the VDSL series of the MA5600
                bnameH565VDER(145939),        -- 32-channel board of the VDSL series of the MA5600
                bnameH565VDES(145940),        -- 32-channel board of the VDSL series of the MA5600
                bnameH565VDET(145941),        -- 32-channel board of the VDSL series of the MA5600
                bnameH565VDEU(145942),        -- 32-channel board of the VDSL series of the MA5600
                bnameH565VDEV(145943),        -- 32-channel board of the VDSL series of the MA5600
                bnameH565VDEW(145944),        -- 32-channel board of the VDSL series of the MA5600
                bnameH565VDEX(145945),        -- 32-channel board of the VDSL series of the MA5600
                bnameH565VDEY(145946),        -- 32-channel board of the VDSL series of the MA5600
                bnameH565VDEZ(145947),        -- 32-channel board of the VDSL series of the MA5600

                bnameH561ETHA(145948),        -- Ethernet subtend board of the MA5600
                bnameH801CITD(145949),        -- P300 cable routing board H801CITD
                bnameH801PRTB(145950),        -- P300 power board H801PRTB

                bnameH801MCUC(146035),        -- MA5606T Master board H801MCUC
                bnameH801MPWB(146036),        -- MA5606T DC Power  board H801MPWB
                bnameH801MPWZ(146053),        -- MA5606T AC Power  board H801MPWZ
                bnameH80BCAME(146069),        -- 48-channel ADSL2+ and POTS(combo) service board
                bnameH85BCVME(146070),        -- 48-channel VDSL2+ and POTS(combo) service board
                bnameH801VRGA(146071),        -- Virtual Route Gateway Board
                bnameH806EPBD(146072),        -- 8EPON board
                bnameH801SPUF(146073),        -- interface board.
                bnameH801MPWD(146074),        -- Power board of MA5608T.
                bnameH806CAME(146077),        -- 48-channel ADSL combo service board.
                bnameH801X2CK(146078),        -- 10GE synchronized Ethernet interface board.
                bnameH802GICK(146079),        -- GE synchronized Ethernet interface board of MA5600T
                bnameH803X2CK(146080),         -- 10GE synchronized Ethernet interface board of MA5600T.
                bnameH80XVDP(146066),         -- 64-channel VDSL2 over POTS service board
                bnameH801SPUC(155955),        -- interface board.


-- MA5626
                bnameH821EPUA(145960),        -- Master board of MA5626 Box type device
                bnameH821EPFA(145961),        -- 24-channel Vitual FE Board of MA5626
                bnameH821EPFB(145962),        -- 16-channel Vitual FE Board of MA5626
                bnameH821ASM(145963),         -- 24-channel POTS Board of MA5626
                bnameH821ASN(145964),         -- 16-channel POTS Board of MA5626
-- MA5651
                bnameH822VDJF(145965),         -- 16-channel Vitual VDSL2 Board of MA5651
                bnameH822EVJG(145968),         -- 8-channel Vitual VDSL2 Board of MA5651
-- MA562X
                bnameH821EPFD(145966),        -- MA562X 8LAN
                bnameH821ASL(145967),         -- MA562X 8POTS
-- MA562XP
                bnameH822ASMB(145969),        -- MA562X 24POTS
                bnameH821EPUB(145970),        -- Master board of MA562XP Box type device
                bnameH822ASNB(145971),        -- MA562X 16POTS
-- OT929S
                bnameH821GPMS(146044),        -- Master board of OT929S Box type device
                bnameH821AIUG(146045),        -- 1-channel Vitual ATM Board of OT929S
                bnameH821ETHA(146046),        -- 1-channel Vitual GE Board of OT929S
-- OFA5920
                bnameH801GPBC(145977),         -- GPON interface board of the OFA5920. This board provides four GPON ports.
                bnameH801SCUL(145978),         -- 200GE SCU control board of the OFA5920. This board is 300 mm deep.
                bnameH801X2CA(145979),         -- OFA5920 board that provides two 10GE ports
                bnameH801GICF(145980),         -- This board provides two 1000M optical ports and is used in the Frame of the R2 full-10GE switching platform.
                bnameH801GICG(145981),         -- This board provides two 1000M electric ports and is used in the Frame of the R2 full-10GE switching platform.
                bnameH801CITC(145982),          --Cable routing board
                bnameH801PIUA(145983),          --Power interface board for the X/Y section of the 23-inch Frame of the NEBS

                bnameH821MCUA(145984),         -- Control board of the MA5636
                bnameH82XVDJ(145985),          -- 8-channel boards of the VDSL series of the MA5636
                bnameH82XVDJA(145986),         -- 8-channel board of the VDSL series of the MA5636
                bnameH82XVDJB(145987),         -- 8-channel board of the VDSL series of the MA5636
                bnameH82XVDJC(145988),         -- 8-channel board of the VDSL series of the MA5636
                bnameH82XVDJD(145989),         -- 8-channel board of the VDSL series of the MA5636
                bnameH82XVDJE(145990),         -- 8-channel board of the VDSL series of the MA5636
                bnameH82XVDJF(145991),         -- 8-channel board of the VDSL series of the MA5636
                bnameH82XVDJG(145992),         -- 8-channel board of the VDSL series of the MA5636
                bnameH82XVDJH(145993),         -- 8-channel board of the VDSL series of the MA5636
                bnameH82XVDJI(145994),         -- 8-channel board of the VDSL series of the MA5636
                bnameH82XVDJJ(145995),         -- 8-channel board of the VDSL series of the MA5636
                bnameH82XVDJK(145996),         -- 8-channel board of the VDSL series of the MA5636
                bnameH82XVDJL(145997),         -- 8-channel board of the VDSL series of the MA5636
                bnameH82XVDJM(145998),         -- 8-channel board of the VDSL series of the MA5636
                bnameH82XVDJN(145999),         -- 8-channel board of the VDSL series of the MA5636
                bnameH82XVDJO(146000),         -- 8-channel board of the VDSL series of the MA5636
                bnameH82XVDJP(146001),         -- 8-channel board of the VDSL series of the MA5636
                bnameH82XVDJQ(146002),         -- 8-channel board of the VDSL series of the MA5636
                bnameH82XVDJR(146003),         -- 8-channel board of the VDSL series of the MA5636
                bnameH82XVDJS(146004),         -- 8-channel board of the VDSL series of the MA5636
                bnameH82XVDJT(146005),         -- 8-channel board of the VDSL series of the MA5636
                bnameH82XVDJU(146006),         -- 8-channel board of the VDSL series of the MA5636
                bnameH82XVDJV(146007),         -- 8-channel board of the VDSL series of the MA5636
                bnameH82XVDJW(146008),         -- 8-channel board of the VDSL series of the MA5636
                bnameH82XVDJX(146009),         -- 8-channel board of the VDSL series of the MA5636
                bnameH82XVDJY(146010),         -- 8-channel board of the VDSL series of the MA5636
                bnameH82XVDJZ(146011),         -- 8-channel board of the VDSL series of the MA5636
                bnameH801SCUB(146018),         -- Control board of the MA5600
                bnameH801ASRB(146019),         -- Voice service board of the MA5600
                bnameH801PMIA(146020),         -- Environment monitoring board of the MA5603
                bnameH561SCUB(146021),         --Control board H561SCUB of the MA5600V3R3C03
                bnameH802SHLB(146022),         -- 16-channel SHL board of the MA5600
                bnameH801EPBA(146023),         --EPON interface board of the MA5600. This board provides four EPON ports.
                bnameH801TOPA(146025),         -- TDM interface board of the MA5600
                bnameH569SHEB(146026),         --Service board H569SHEB of the MA5600. This board uses the GE bus and provides 32 channels.
                bnameH801SCUF(146027),         --Control board of the MA5600
                bnameH802ADPD(146028),         --64-channel board of the ADSL2+ series of the MA5600
                bnameH802ADQD(146029),         --64-channel board of the ADSL2+ series of the MA5600
                bnameH80XASP(146030),          --64-channel voice service board of the MA5600T
                bnameH801EDTB(146031),         --64-channel voice service board of the MA5600T
                bnameH80xVDM (146032),         --48-channel board of the VDSL2 series of the MA5600T
                bnameH80xVDN (146033),         --48-channel board of the VDSL2 series of the MA5600T
                bnameH801GSCA(146034),         --GE synchronization Ethernet interface board of the MA5600T
                bnameH801SCUN(146037),         --MA5600T control board H801SCUN
                bnameH801X2CS(146038),         --10GE synchronized Ethernet interface board
                bnameH802EPBD(146039),         --8EPON board
                bnameH801PRTE(146040),         --H801PRTE Power board

                bnameH801X4CS(146041),         --Giu board that provides 4*10GE
                bnameH801GPBD(146042),         --8GPON board
                bnameH801OPGA(146043),         --Ethernet access board of the MA5600. This board provides 48 FE ports.
                bnameH801CITB(146047),         -- Environment monitoring board of the MA5603U
                bnameH855VDMF(146048),         --48-channel board of the VDSL2 series of the MA5603U
                bnameH801PAIB(146049),         --H801PAIB Power board
                bnameH851VSNKE(146050),        --48-channel VDSL voice SPL board of the MA5603U
                bnameH851VSNLE(146051),        --48-channel VDSL voice SPL board of the MA5603U
                bnameH801GPJC(146052),        --GPON board
                bnameH802GPBD(146054),         --8GPON board
                bnameH801CSPA(146055),        --64-channel board of CESoP service board of the MA5600T
                bnameH801GICK(146056),        --This board provides two 1000M optical ports and is used in the Frame of the R2 full-10GE switching platform.
                bnameH801SPUA(146057),        --Ethernet subtend interface board of the MA5600T
                bnameH801SPUB(146058),        --MPLS service board of the MA5600T
                bnameH801EPBC(146059),        --EPON board
                bnameH801BIUB(146060),         -- H801BIUB BOARD
                bnameH801PRTG(146061),         -- H801PRTG BOARD
                bnameH802OPGD(146062),         -- H802OPGD BOARD
                bnameH85BVDMD(146063),         -- H85BVDMD BOARD
                bnameH802EDTB(146064),         -- H802EDTB BOARD
                bnameH802P2CA(146065),         -- H802P2CA BOARD
                bnameH802OPGE(146075),         -- H802OPGE BOARD
                bnameH801MPWE(146076),         -- Power board of MA5608T
                bnameH808ASPB(146081),         -- H808ASPB BOARD -64-channel voice service board of the MA5600
                bnameH801PAIC(146082),         -- H801PAIC Power board
                bnameH803TPBA(146083),         -- 2-port 10G EPON interface board
                bnameH803TPBC(146084),         -- 4-port 10G EPON interface board
                bnameH805GPBD(146085),         -- 8GPON board
                bnameH805EPBD(146086),         -- 8EPON board
                bnameH808EPSD(146087),         -- 8EPON board
                bnameH803GPFD(146088),         -- 16GPON board.
                bnameH807EPBD(146089),         -- 8EPON board.
                bnameH808EPBD(146090),         -- 8EPON board.
                bnameH806EPFD(146091),         -- 16EPON board.
                bnameH806GPBD(146092),         -- 8GPON board.
                bnameH807GPBD(146093),         -- 8GPON board.
                bnameH808GPBD(146094),         -- 8GPON board.
                bnameH801GPFD(146095),         -- 16GPON board.
                bnameH802GPFD(146096),         -- 16GPON board.
                bnameH80XVPE(146097),          -- support vector board.
                bnameH80XVCM(146098),          -- support vector board.
                bnameH80BCVME(146099),         -- 48-channel VDSL2+ and POTS(combo) service board.
                bnameH801XGBC(146100),         -- 4-channel 10GE GPON board.
                bnameH801SCUH(146101),         -- two GE port and two 10GE port H801SCUH control board of MA5600T.
                bnameH801MCUD(146102),         --  control board of MA5600T.
                bnameH801MPWC(146103),         --  Power board of MA5600T.
                bnameH801XEBD(146104),         --  10G EPON board of MA5600T.
                bnameH802XGBC(146105),         --  10G EPON board of MA5600T.
                bnameH80xVCP(146106),          --  64 VDSL Vector board of MA5600T.
                bnameH80xVDQ(146107),          --  64 VDSL over ISDN  board of MA5600T.
                bnameH80xVCQ(146108),          --  64 VDSL over ISDN Vector Melt board of MA5600T.
                bnameH801GPCD(146109),         --  8GPON board of MA5600T.
                bnameH802GPCD(146110),         --  8GPON board of MA5600T.
                bnameH806EPCD(146111),         --  8EPON board of MA5600T.
                bnameH809EPSD(146112),         --  8EPON board of MA5600T.
                bnameH801EPFD(146113),         --  16EPON board of MA5600T.
                bnameH802EPFD(146114),         --  16EPON board of MA5600T.
                bnameH803EPFD(146115),         --  16EPON board of MA5600T.
                bnameH801EPTD(146116),         --  16EPON board of MA5600T.
                bnameH802EPTD(146117),         --  16EPON board of MA5600T.
                bnameH805GPBH(146118),         --  8GPON board of MA5600T.
                bnameH806GPBH(146119),         --  8GPON board of MA5600T.
                bnameH807GPBH(146120),         --  8GPON board of MA5600T.
                bnameH808GPBH(146121),         --  8GPON board of MA5600T.
                bnameH801GPCH(146122),         --  8GPON board of MA5600T.
                bnameH802GPCH(146123),         --  8GPON board of MA5600T.
                bnameH801GPFH(146124),         --  16GPON board of MA5600T.
                bnameH802GPFH(146125),         --  16GPON board of MA5600T.
                bnameH803GPFH(146126),         --  16GPON board of MA5600T.
                bnameH805EPBH(146127),         --  8GPON board of MA5600T.
                bnameH806EPBH(146128),         --  8GPON board of MA5600T.
                bnameH806EPCH(146129),         --  8GPON board of MA5600T.
                bnameH808EPSH(146130),         --  8GPON board of MA5600T.
                bnameH809EPSH(146131),         --  8GPON board of MA5600T.
                bnameH801EPFH(146132),         --  16GPON board of MA5600T.
                bnameH802EPFH(146133),         --  16GPON board of MA5600T.
                bnameH803EPFH(146134),         --  16GPON board of MA5600T.
                bnameH801EPTH(146135),         --  16GPON board of MA5600T.
                bnameH802EPTH(146136),         --  16GPON board of MA5600T.
                bnameH801XESD(146137),         --  8 ports 10G EPON board of MA5600T
                bnameH80XVPG(146138),          --  support vector board of MA5600T.
                bnameH806CCPE(146139),         --  64-channel POTS(combo) + Vectoring board of MA5600T.
                bnameH801XGBD(146141),         --  8 ports 10G GPON board of MA5600T.
                bnameH803XEBD(146142),         --  8 ports 10G EPON board of MA5600T.
                bnameH805EPFD(146143),         --  16EPON board of MA5600T.
                bnameH802GPMD(146144),         --  8GPON board of MA5600T.
                bnameH805GPFD(146145),         --  16GPON board of MA5600T.
                bnameH802XEBD(146146),         --  8 ports 10G EPON board of MA5600T.
                bnameH809EPBD(146147),         --  8EPON board.
                bnameH801TOPB(146148),         --  TDM interface board of the MA5600.
                bnameH80DCCPE(146149),         --  64-channel POTS(combo) + Vectoring board of MA5600T device.
                bnameH80XATR(146150),          --  ATR series voice board of MA5600T device.
                bnameH801CGBD(146151),         --  8-port 10G GPON and GPON combo interface board of MA5600T.
                bnameH802CGBD(146152),         --  8-port 10G GPON and GPON combo interface board of MA5600T.
                bnameH801CSBD(146153),         --  8-port 10GS-PON and GPON combo interface board of MA5600T.
                bnameH802CSBD(146154),         --  8-port 10GS-PON and GPON combo interface board of MA5600T.
                bnameH801XSBD(146155),         --  8-port 10GS-PON interface board of MA5600T.
                bnameH801XEUD(146156),         --  8-port 10G EPON interface board of MA5600T.
				bnameH806GPFD(146157),         --  16GPON board of MA5600T.
                bnameH802SCUN(148001),         --  MA5600T control board H802SCUN
                bnameH801SPUH(148002),         --  interface board of the MA5600T
                bnameH801SCUK(148003),         --  MA5600T control board H801SCUK
                bnameH801SCUE(148004),         --  MA5600T control board H801SCUE
                bnameH801MCUD1(148005),        --  control board of MA5608T
                bnameH801MCUE(148006),         --  control board of MA5608T
                bnameH801GPMD(148007),         --  8GPON board of MA5600T.
                bnameH801SCUV(148008),         --  control board of MA5600T
                bnameH802SCUH(148009),         --  control board of MA5600T
                bnameH802SCUV(148010),         --  control board of MA5600T
                bnameH802SCUB(148011),         --  control board of MA5600T
                bnameH80XSDM(148012),          --  48 VDSL SuperVector board of MA5600T.
                bnameH80XSDP(148013),          --  64 VDSL SuperVector board of MA5600T.
                bnameH80XVPS(148014),          --  support vector board of MA5600T
                bnameH802X2CS(148015),         --  10GE synchronized Ethernet interface board
                bnameH801GPND(148016),         --  8GPON board of MA5600T.
                bnameH801XP1A(155958),          -- 1-port XG-PON/XGS-PON interface board.
                bnameH80DCSPE(155960),         --  64-channel POTS(combo) + Vectoring board of MA5600T device, Support SuperVector board.
                bnameH806VPED(156070),          -- support super vector board.

--MA5800:
                bnameH901MPLA(148501),         --  control board of MA5800
                bnameH901MPLB(148502),         --  control board of MA5800
                bnameH901MPSA(148503),         --  control board of MA5800-X2
                bnameH902MPLA(148504),         --  control board of MA5800
                bnameH901MPSC(148505),         --  control board of MA5800-X2.
                bnameH901MPSD(148506),         --  control board of MA5800-X2.
                bnameH901MPLC(148507),         --  control board of MA5800
                bnameH901MPLD(148508),         --  control board of MA5800
                bnameH902MPLC(148509),         --  control board of MA5800
                bnameH921MPCA(148510),         --  control board of MA5801-GP08
                bnameH921MPCAE(148511),        --  control board of EA5801-GP08

                bnameH901XGHD(148521),         --  8*10G GPON board of MA5800
                bnameH901GPHF(148522),         --  16*GPON board of MA5800
                bnameH901OGHK(148523),         --  48 P2P board of MA5800
                bnameH901NXED(148524),         --  8*10GE board of MA5800
                bnameH901OXHD(148525),         --  8*10GE extend board of MA5800
                bnameH901PILA(148526),         --  Power board of MA5800
                bnameH901CIUA(148527),         --  GPIO board of MA5800
                bnameH901GPSF(148529),         --  16*GPON board of MA5800
                bnameH901EPHF(148530),         --  16*EPON board of MA5800
                bnameH901XEHD(148531),         --  8*10G EPON board of MA5800
                bnameH901EDSH(148536),         --  TDM service board of MA5800
                bnameH901PILB(148537),         --  Power board of MA5800
                bnameH901CRED(148538),         --  IP backhaul board of MA5800
                bnameH901CVEC(148539),         --  Video board of MA5800
                bnameH921GPHD(148540),         --  8*GPON board of MA5801-GP08.
                bnameH921NXHC(148541),         --  4*10GE board of MA5801-GP08.
                bnameH921GPHDE(148542),        --  8*GPON board of EA5801-GP08.
                bnameH921PICA(148543),         --  DC Power board of MA5801-GP08.
                bnameME170-12A(148544),        --  AC Power board of MA5801-GP08.
                bnameH921CIUA(148545),         --  GPIO board of MA5801-GP08.
                bnameH921CGHC(148546),         --  4*GE and 10GE combo board of MA5801-CG04.
                bnameH921CGHCE(148547),        --  4*GE and 10GE combo board of EA5801-CG04.
                bnameH921NXHCE(148548),        --  4*10GE board of EA5801-GP08.
                bnameH901ACSA(148549),         --  Access Edge Computing board of MA5800.
                bnameH901OXEG(148600),         --  24*10GE board of MA5800
                bnameH901MPWD(148601),         --  AC Power board of MA5800-X2
                bnameH901MPWE(148602),         --  DC Power board of MA5800-X2
                bnameH901MPWC(148603),         --  DC Power board of MA5800-X2
                bnameH901XSED(148604),         --  8*10G GPON board of MA5800
                bnameH901GPHD(148605),         --  8*GPON board of MA5800
                bnameH901GPSD(148606),         --  8*GPON board of MA5800
                bnameH901TWED(148607),         --  8*10G GPON board of MA5800
                bnameH901CGCD(148608),         --  8*GE and 10GE combo board of MA5800
                bnameH901XGSF(148609),         --  16*10GE board of MA5800
                bnameH901PISA(148610),         --  DC Power board of MA5800-X2
                bnameH901PISB(148611),         --  AC Power board of MA5800-X2
                bnameH901PISC(148612),         --  DC Power board of MA5800-X2
                bnameH901CGID(148613),         --  8*GE and 10GE combo board of MA5800

--MA5694_8VD  R016C00
                bnameH821BVIC(148533),        -- Master board of MA5694_8VD device.

--MA5694_4VD  R016C00
                bnameH821AVIC(148534),        -- Master board of MA5694_4VD device.
                bnameHS21GE4B(148535),        -- 4GE baoard for MA5694_4VD device.

--MA5800:
                bnameH901PIMA(148614),        --  DC Power board of MA5800-X7.
                bnameH901GPLF(148615),        --  16*GPON board of MA5800
                bnameH901XGLD(148616),        --  8*10G GPON board of MA5800
                bnameH901XGLF(148617),        --  16*10G GPON board of MA5800
                bnameH901XELD(148618),        --  8*10G EPON board of MA5800
                bnameH902MPLAE(148619),       --  control board of EA5800.
                bnameH901MPSCE(148620),       --  control board of EA5800-X2.
                bnameH901GPSFE(148621),       --  16*GPON board of EA5800.
                bnameH901XGHDE(148622),       --  8*10G GPON board of EA5800.
                bnameH902XSED(148623),        --  8*10G GPON board of MA5800.
                bnameH901DSHD(148624),        --  8*GE and 10GE combo board of MA5800.
                bnameH901OGHF(148625),        --  16 P2P board of MA5800.
                bnameH901OXHG(148626),        --  24*10GE board of MA5800.
                bnameH901NXLC(148627),        --  4*10GE board of MA5800.
                bnameH901TWEDE(148628),       --  8*10G GPON board of MA5800.
                bnameH902TWED(148629),        --  8*10G Flex-PON board of MA5800 support TWDM-PON XGS-PON.
                bnameH903XSHD(148630),        --  8*10G GPON board of MA5800.
                bnameH901XSHF(148631),        --  16*10G XGS-PON board of MA5800.
                bnameH901CSHD(148632),        --  8*XGS GPON and GPON combo board of MA5800.
                bnameH901CGHF(148633),        --  16*XG GPON and GPON combo board of MA5800.
                bnameH901CSHF(148634),        --  16*XGS GPON and GPON combo board of MA5800.
                bnameH901XEHF(148635),        --  16*10G EPON board of MA5800.
                bnameH902CGHD(148636),        --  8*XGS GPON and GPON combo board of MA5800.
                bnameH902CSHD(148637),        --  8*XG GPON and GPON combo board of MA5800.
                bnameH902CRED(148638),        --  IP backhaul board of MA5800.
                bnameH901CSHDE(148639),       --  8*XGS GPON and GPON combo board of EA5800.
                bnameH901CSHFE(148640),       --  16*XGS GPON and GPON combo board of EA5800.
                bnameH901CGUD(148641),        --  8*GE and 10GE combo board of MA5800.
                bnameH901CGUF(148642),        --  16*XG GPON and GPON combo board of MA5800.
         		bnameH902TWHD(148643),        --  8*10G GPON board of MA5800.
                bnameH902XSHD(148644),        --  8*10G GPON board of MA5800.
                bnameH901FLHF(148645),        --  16*flex-PON board of MA5800.
                bnameH902CSHF(148646),        --  16*XGS GPON and GPON combo board of MA5800.
                bnameH902GPHF(148647),        --  16*10G GPON board of MA5800.
                bnameH902XEHD(148648),        --  8*10G EPON board of MA5800.
				bnameH902NXED(148649),        --  8*Port ETH board of MA5800.
                bnameH903MPLA(148650),        --  control board of MA5800.
                bnameH902MPLB(148651),        --  control board of MA5800.
                bnameH902CIUA(148652),        --  GPIO board of MA5800.
                bnameH902PILA(148653),        --  Power board of MA5800.
                bnameH901GPUF(148654),        --  16*GPON board of MA5800.
                bnameH901NCEB(148655),        --  2*100G service board of MA5800.
                bnameH901GPHH(148656),        --  32*GPON board of MA5800.
                bnameH901MPLE(148657),         --  control board of MA5800.
                bnameH902CGHF(148658),        --  16*XG/G GPON board of MA5800.
                bnameH902GPUF(148659),        --  16*GPON board of MA5800.
                bnameH902GPLF(148660),        --  16*GPON board of MA5800.
                bnameH902XELD(148661),        --  8*10G EPON board of MA5800.
                bnameH902GPSF(148662),         --  16*GPON board of MA5800.
                bnameMA5800Reserve63(148663),         --  Board of MA5800, reserve for support new board in old version.
                bnameH902XSHF(148664),         --  16*10G XGS-PON board of MA5800.
                bnameH902FLHF(148665),         --  16*flex-PON board of MA5800.
                bnameH902CGUF(148666),         --  16*XG GPON and GPON combo board of MA5800.
                bnameH902OXHD(148667),         --  8*10GE P2P board of MA5800.
                bnameH902GPHFE(148668),        --  16*10G GPON board of MA5800
                bnameH902FLHFE(148669),        --  16*flex-PON board of EA5800.
                bnameH903MPLAE(148670),        --  control board of EA5800.
                bnameH902OGHK(148671),         --  48 P2P board of MA5800.
                bnameH902XSHFE(148672),        --  16*10G XGS-PON board of EA5800.
                bnameH902EPHFE(148673),        --  16 port EPON board of EA5800.
                bnameH902EPHF(148674),         --  16 port EPON board of MA5800.
                bnameH902PISB(148675),         --  AC Power board of MA5800-X2.
                bnameH901MPSAE(148676),        --  control board of EA5800-X2.
                bnameH901OTSF(148677),         --  OTDR board of MA5800.
                bnameH903CGHD(148678),         --  8*XG/G combo board of MA5800.
                bnameH903CSHD(148679),         --  8*XGS/G combo board of MA5800.
                bnameH902OXEG(148680),         --  24*10GE board of MA5800.
                bnameH903CGUD(148681),         --  8*XGS/G combo board of MA5800.
                bnameH902FLEF(148682),         --  16*flex-PON board of MA5800.
                bnameH902XGLF(148683),         --  16*XG GPON board of MA5800.
                bnameH901MPSB(148684),         --  control board of MA5800-X2.
                bnameH903XSHDE(148685),        --  8*10G GPON board of MA5800
                bnameH903XEHD(148686),         --  8*10G EPON board of MA5800.
                bnameH903MPLB(148687),         --  control board of MA5800-X17.
                bnameH902NCEB(148688),         --  2x100G BOARD_GIC of MA5800.
                bnameH903FLHF(148689),         --  16*flex-PON board of MA5800.
                bnameH901CASZT(148690),               --  AI compute board of MA5800.
                bnameH901GPEF(148691),                --  16*GPON board of MA5800.
                bnameH905CIUA(148692),                --  GPIO board of MA5800.
                bnameH901GPEFE(148693),               --  16*GPON board of EA5800.
                bnameH903CSHDE(148694),               --  8*XGS combo PON of EA5800.
                bnameH905CGHD(148695),         --  8*XG/G combo board of MA5800.
                bnameH903PILA(148696),         --  Power board of MA5800.
                bnameH903CGHF(148697),                --  16*XG/G combo board of MA5800.
                bnameH903GPHF(148698),                --  16*GPON board of MA5800.
                bnameH903CSHF(148699),                --  16*XGS GPON and GPON combo board of MA5800.
                
                bnameH901MPLF(148700),                --  Board of MA5800, reserve for support new board in old version.
                bnameH921MPCB(148701),                --  control board of MA5801-FL16.
                bnameV931MPBA(148702),                --  control board of MA5801S-FL16.
                bnameV921NXHC(148703),                --  4*10GE board of MA5801-FL16-H1.
                bnameV921FLHF(148704),                --  16*flex-PON board of MA5801-FL16-H1.
                bnameV921CIUA(148705),                --  GPIO board of MA5801-FL16-H1.
                bnamePAC300S12(148706),               --  AC Power board of MA5801-FL16-H1.
                bnamePDC300S12(148707),               --  DC Power board of MA5801-FL16-H1.
                bnameV931FLHF(148708),                --  16*flex-PON board of MA5801-FL16-H1.
                bnameV931NXHC(148709),                --  4*10GE board of MA5801S-FL16.
                bnameV931CIUA(148710),                --  GPIO board of MA5801S-FL16.
                bnameH931PICA(148711),                --  DC Power board of MA5801S-FL16.
                bnameH931PICB(148712),                --  AC Power board of MA5801S-FL16.
                bnameMA5800Reserve113(148713),        --  Board of MA5800, reserve for support new board in old version.
                bnameV921MPCC(148714),                --  control board of MA5801-GP16.
                bnameV931MPBB(148715),                --  control board of MA5801S-GP16.
                bnameV921GPHF(148716),                --  16*GPON board of MA5801-GP16.
                bnameV923NXHC(148717),                --  4*10GE/GE board of MA5801-GP16.
                bnameV931GPHF(148718),                --  16*GPON board of MA5801S-GP16.
                bnameV932NXHC(148719),                --  4*10GE/GE board of MA5801S-GP16.
                bnameH903MPLBE(148720),               --  control board of EA5800-X17.
                bnameTM62HPXCL(148721),               --  control board of OSN1600IIM.
                bnameTM62HPCS8(148722),               --  8 port dual-channel service board of OSN1600IIM.
                bnameH906CIUA(148723),                -- GPIO board of MA5800.
                bnameH907CIUA(148724),                --  GPIO board of MA5800.
                bnameH901OTEF(148725),                --  DN_ODN baseboard of MA5800.
                bnameH901CSPD(148726),                --  8*XGS/G combo board of MA5800.
                bnameORCSF1(148727),                    --  16*XGS GPON and GPON combo board of EA5800.
                bnameH901OTHF(148728),                --  DN_ODN board of MA5800.
                bnameV921MPCCE(148729),               --  control board of EA5801E-GP16.
                bnameV921GPHFE(148730),               --  16*GPON board of EA5801E-GP16.
                bnameMA5800Reserve131(148731),        --  Board of MA5800, reserve for support new board in old version.
                bnameH901MPLG(148732),                --  control board of MA5800-X17.
                bnameV931GPSF(148733),                --  16*GPON board of MA5801S-GP16-S1.
                bnameV921GPHD(148734),                --  8*GPON board of MA5801-GP08-H2.
                bnameV921CGHF(148735),                --  16*GPON board of MA5801-CG16-H1.
                bnameH901DXHD(148736),                --  20GPON board of 21A version.
                bnameV921MPCB(148737),                --  control board of MA5801-FL16-H1.
                bnameV932NXSC(148738),                --  4*GE board of MA5801S-GP16-S1.
                bnameH901DQHF(148739),                --  DQ ODN OAI board of MA5800 and EA5800.
                bnameH901MPSG(148740),                --  control board of MA5800-X2.
                bnameH901MPSFE(148741),               --  control board of EA5800-X2.
                bnameH905MPLA(148742),                --  control board of MA5800-X17.
                bnameH901MPLGE(148743),               --  control board of EA5800.
                bnameV921GPHDE(148744),               --  8*GPON board of EA5801E-GP08-H2.
                bnameH902ACSA(148745),                --  Access Edge Computing board of MA5800.
                bnameV931MPBBE(148746),               --  control board of EA5801S-GP16-H1.
                bnameV931GPHFE(148747),               --  16*GPON board of EA5801-GP16-H1.
                bnameH901CGPD(148748),                --  8*XG combo board of MA5800.
                bnameH901FGHFE(148749),               --  16*XG/G GPON combo board of EA5800.
                bnameH901TNSC(148750),                --  4*OTN board of MA5800.
                bnameH902TNSC(148751),                --  4*OTN board of MA5800.
                bnameV951NQHC(148752),                --  4*25GE board of MA5801C-FL08
                bnameH902CGPD(148753),                --  8*XG combo board of MA5800.
                bnameV951MPBA(148754),                --  control board of MA5801C-FL08
                bnameMA5800Reserve155(148755),        --  Board of MA5800, reserve for support new board in old version.
                bnameV921GPHCE(148756),               --  4*GPON board of EA5801E-GP04-H1.
                bnameV921MPCDE(148757),               --  control board of EA5801E-GP08-H2.
                bnameV921MPCEE(148758),               --  control board of EA5801E-GP04-H1.
                bnameV922MPCC(148759),                --  control board of MA5801-GP16-H2.
                bnameV922GPHF(148760),                --  16*GPON board of MA5801-GP16-H2.
                bnameH905MPLB(148761),                --  control board of MA5800.
                bnameV925NXHC(148762),                --  4*10GE/GE board of MA5801-GP16-H2.
                bnameV932MPBB(148763),                --  control board of MA5801S-GP16-H2.
                bnameV932GPHF(148764),                --  16*GPON board of MA5801S-GP16-H2.
                bnameV932GPSF(148765),                --  16*GPON board of MA5801S-GP16-S2.
                bnameV933NXHC(148766),                --  4*10GE/GE board of MA5801S-GP16-H2.
                bnameV933NXSC(148767),                --  4*GE board of MA5801S-GP16-S2.
                bnameV922GPHD(148768),                --  8*GPON board of MA5801-GP08-H3.
                bnameH905CSHF(148769),                --  16*XG/G GPON combo board of MA5800.
                bnameH905CSHFE(148770),               --  16*XG/G GPON combo board of EA5800.
                bnameH905XSHF(148771),                --  16*10G XGS-PON board of MA5800.
                bnameH905XSHFE(148772),               --  16*10G XGS-PON board of EA5800.
                bnameH903OGHK(148773),                --  48 P2P board of MA5800.
                bnameH905OXEG(148774),                --  24*10GE board of MA5800.
                bnameV922MPCCE(148775),               --  control board of EA5801E-GP16-H2.
                bnameV922MPCEE(148776),               --  control board of EA5801E-GP04-H2.
                bnameV932MPBBE(148777),               --  control board of EA5801S-GP16-H2.
                bnameV922MPCDE(148778),               --  control board of EA5801E-GP08-H3.
                bnameV922GPHFE(148779),               --  16*GPON board of EA5801E-GP16-H2.
                bnameV922GPHDE(148780),               --  8*GPON board of EA5801E-GP08-H3.
                bnameV922GPHCE(148781),               --  4*GPON board of EA5801E-GP04-H2.
                bnameV932GPHFE(148782),               --  16*GPON board of EA5801S-GP16-H2.
                bnameH901ACSC(148783),                --  Access Edge Computing board of MA5800.
                bnameH901DQHT(148784),                --  DQ ODN OAI board of MA5800 and EA5800.
                bnameH902CSPD(148785),                --  8*XGS combo board of MA5800.
                bnameH907CGHD(148786),                --  8*XG combo board of MA5800.
                bnameV921FLHFE(148787),               --  16*GPON board of EA5801E_FL16_H1.
                bnameV921MPCBE(148788),               --  control board of EA5801E_FL16_H1.
				bnameH903PISB(148789),                --  AC Power board of MA5800-X2.
                bnameH908CGHF(148790),                --  16*XG/G combo board of MA5800.
                bnameH902DQHF(148791),                --  DQ ODN OAI board of MA5800 and EA5800.
                bnameH905CGUD(148792),                --  8*XG/G combo board of MA5800.
                bnameV932MPBA(148793),                --  control board of MA5801S-FL16-H2.
                bnameV935NXHC(148794),                --  4*10GE board of MA5801S-FL16-H2.
                bnameV932FLHF(148795),                --  16*flex-PON board of MA5801S-FL16-H2.
                bnameH905XEHF(148796),                --  16*10G EPON board of MA5800.
                bnameH901MPSDE(148797),               --  control board of EA5800-X2.
                bnameH907MPLB(148798),                --  control board of MA5800.
                bnameH907MPLBE(148799),               --  control board of EA5800.
                bnameV932MPBAE(148800),               --  control board of EA5801S-FL16-H2.
                bnameV932FLHFE(148801),               --  16*flex-PON board of EA5801S-FL16-H2.
                bnameH902MPLG(148802),                --  control board of MA5800.
                bnameH902MPLGE(148803),               --  control board of EA5800.
                bnameH901MPSJ(148804),                -- control board of MA5800-X2.
                bnameHA01ATHF(148805),                --  16*GPON, XGSPON and 50GPON combo board of MA5800T.
                bnameORCSF2(148806),                  --  16*XGS combo board of EA5800.
                bnameH902CSPDE(148807),               --  8*XGS combo board of EA5800.
                bnameH902CGPDE(148808),               --  8*XG/G combo board of EA5800.
                bnameH901MPSF(148809),                -- control board of MA5800-X2.
                bnameMA5800Reserve210(148810),        --  Board of MA5800, reserve for support new board in old version.
                bnameMA5800Reserve211(148811),        --  Board of MA5800, reserve for support new board in old version.
                bnameH906CSHF(148812),                --  16*XGS combo board of MA5800.
                bnameH901HXHD(148813),                --  8*50GPON board of MA5800.
                bnameH906FLHF(148814),                --  16*XGS combo board of MA5800.
                bnameH902FLSF(148815),                --  16*XGS combo board of MA5800.
                bnameH906FLHFE(148816),               --  16*XGS combo board of EA5800.
                bnameH906CSHFE(148817),               --  16*XGS combo board of EA5800.
                bnameH901FLHH(148818),                --  32*flex-PON board of MA5800.
                bnameH901FLPF(148819),                --  16*flex-PON board of MA5800.
                bnameH901MPSH(148820),                --  control board of MA5800-X2.
                bnameHA01UPLA(148821),                --  Ultra Processing board of MA5800T.
                bnameH901HXED(148822),                --  8*XGSPON and 50GSPON combo board of MA5800.
                bnameH901AEED(148823),                --  8*EPON, 10GEPON and 50GPON combo board of MA5800.
                bnameH901ATED(148824),                --  8*GPON, XGSPON and 50GPON combo board of MA5800.
                bnameH901NCEC(148825),                --  4*100G uplink interface board of MA5800.
                bnameH901FLVF(148826),                --  16*flex-PON board of MA5800.
                bnameHA01PDLA(148827),                --  Power board of MA5800T-X17.
                bnameHA01PDLB(148828),                --  Power board of MA5800T-X17.
                bnameH901DPWA(148829),                --  Dustproof board of MA5800T-X17.
                bnameH901HXEDE(148830),               --  8-port 10GS-PON and 50GS-PON combo interface board of EA5800.
                bnameV921MPCG(148831),        		  --  control board of MA5801-FL04-H1.
                bnameV921FLHC(148832),        		  --  4*flex-PON board of MA5800-FL04-H1.
                bnameV921NXLC(148833),        		  --  4*10GE and 2*2.5GE/GE electric port board of MA5801-FL04-H1.
                bnameH901FLVFE(148834),               --  16*flex-PON board of EA5800.
                bnameHE01MCSA(148835),                --  control board of MA5800-X2
                bnameHE01LXSG(148836),                --  24*10GE board of MA5800.
                bnameH901HTED(148837),        		  --  8*50GPON board of MA5800.
                bnameH901HTHD(148838),                --  8*50GPON board of MA5800.
                bnameH901ATHD(148839),        		  --  8*50GPON board of MA5800.
                bnameHA01CILA(148840),        		  --  GPIO board of MA5800T.
                bnameH901MPLH(148841),                --  control board of MA5800.
                bnameHA01PDMB(148842),                --  Power board of MA5800T-X8.
                bnameH908CSHF(148843),                --  16*XGS combo board of MA5800.
                bnameH909CGHF(148844),                --  16*XGS combo board of MA5800.
                bnameH908FLHF(148845),                --  16*XGS combo board of MA5800.
                bnameH905OGHK(148846),                --  24/48 P2P board of MA5800.
                bnameH908CSHFE(148847),               --  16*XGS combo board of EA5800.
                bnameV921CGHC(148848),                --  4*XG/G combo board of MA5801-CG04-H2.
                bnameHA01PDMA(148849),                --  Power board of MA5800T-X8.
                bnameH901DPWB(148850),                --  Wind board of MA5800T-X17.
                bnameH901FLRF(148851),                -- 16*XGS combo board of MA5800.
                bnameH901FLBF(148852),                -- 16*XGS combo board of MA5800.
                bnameH901HEED(148853),                -- 50G XPON board of MA5800.
                bnameH901MPLHE(148854),               --  control board of EA5800
                bnameMA5800Reserve255(148855),        --  Board of MA5800, reserve for support new board in old version.
                bnameH901MPSK(148856),                -- control board of MA5800-X2.
                bnameV951CIUA(148857),                --  GPIO board of MA5801C-FL08.
                bnameH951PICC(148858),                --  AC Power board of MA5801C-FL08.
                bnameV951FLHD(148859),                --  8*flex-PON board of MA5801C-FL08.
                bnameV922MPCG(148860),                -- control board of MA5801-FL08-H1.
                bnameV921FLHD(148861),                -- 4*GPON board of MA5801-FL08-H1.
                bnameV926NXHC(148862),                -- 2*XGE/GE board of MA5801-FL08-H1.
                bnameV922MPCB(148863),                -- control board of MA5801-FL16-H2.
                bnameV922FLHF(148864),                -- 4*10GE board of MA5801-FL16-H2.
                bnameV922NXHC(148865),                -- 16*flex-PON board of MA5801-FL16-H2.
                bnameH902HTED(148866),                -- 8*50GPON board of MA5800.
                bnameMA5800Reserve267(148867),        --  Board of MA5800, reserve for support new board in old version.
                bnameMA5800Reserve268(148868),        --  Board of MA5800, reserve for support new board in old version.
                bnameMA5800Reserve269(148869),        --  Board of MA5800, reserve for support new board in old version.
                bnameMA5800Reserve270(148870),        --  Board of MA5800, reserve for support new board in old version.
                bnameMA5800Reserve271(148871),        --  Board of MA5800, reserve for support new board in old version.
                bnameMA5800Reserve272(148872),        --  Board of MA5800, reserve for support new board in old version.
                bnameMA5800Reserve273(148873),        --  Board of MA5800, reserve for support new board in old version.
                bnameMA5800Reserve274(148874),        --  Board of MA5800, reserve for support new board in old version.
                bnameMA5800Reserve275(148875),        --  Board of MA5800, reserve for support new board in old version.
                bnameMA5800Reserve276(148876),        --  Board of MA5800, reserve for support new board in old version.
                bnameMA5800Reserve277(148877),        --  Board of MA5800, reserve for support new board in old version.
                bnameMA5800Reserve278(148878),        --  Board of MA5800, reserve for support new board in old version.
                bnameMA5800Reserve279(148879),        --  Board of MA5800, reserve for support new board in old version.
                bnameMA5800Reserve280(148880),        --  Board of MA5800, reserve for support new board in old version.
                bnameMA5800Reserve281(148881),        --  Board of MA5800, reserve for support new board in old version.
                bnameMA5800Reserve282(148882),        --  Board of MA5800, reserve for support new board in old version.
                bnameMA5800Reserve283(148883),        --  Board of MA5800, reserve for support new board in old version.
                bnameMA5800Reserve284(148884),        --  Board of MA5800, reserve for support new board in old version.
                bnameMA5800Reserve285(148885),        --  Board of MA5800, reserve for support new board in old version.
                bnameMA5800Reserve286(148886),        --  Board of MA5800, reserve for support new board in old version.
                bnameMA5800Reserve287(148887),        --  Board of MA5800, reserve for support new board in old version.
                bnameMA5800Reserve288(148888),        --  Board of MA5800, reserve for support new board in old version.
                bnameMA5800Reserve289(148889),        --  Board of MA5800, reserve for support new board in old version.
                bnameMA5800Reserve290(148890),        --  Board of MA5800, reserve for support new board in old version.
                bnameMA5800Reserve291(148891),        --  Board of MA5800, reserve for support new board in old version.
                bnameMA5800Reserve292(148892),        --  Board of MA5800, reserve for support new board in old version.
                bnameMA5800Reserve293(148893),        --  Board of MA5800, reserve for support new board in old version.
                bnameMA5800Reserve294(148894),        --  Board of MA5800, reserve for support new board in old version.
                bnameMA5800Reserve295(148895),        --  Board of MA5800, reserve for support new board in old version.
                bnameMA5800Reserve296(148896),        --  Board of MA5800, reserve for support new board in old version.
                bnameMA5800Reserve297(148897),        --  Board of MA5800, reserve for support new board in old version.
                bnameMA5800Reserve298(148898),        --  Board of MA5800, reserve for support new board in old version.
                bnameMA5800Reserve299(148899),        --  Board of MA5800, reserve for support new board in old version.
                bnameMA5800Reserve300(148900),        --  Board of MA5800, reserve for support new board in old version.
                bnameMA5800Reserve301(148901),        --  Board of MA5800, reserve for support new board in old version.
                bnameMA5800Reserve302(148902),        --  Board of MA5800, reserve for support new board in old version.
                bnameMA5800Reserve303(148903),        --  Board of MA5800, reserve for support new board in old version.
                bnameMA5800Reserve304(148904),        --  Board of MA5800, reserve for support new board in old version.
                bnameMA5800Reserve305(148905),        --  Board of MA5800, reserve for support new board in old version.
                bnameMA5800Reserve306(148906),        --  Board of MA5800, reserve for support new board in old version.
                bnameMA5800Reserve307(148907),        --  Board of MA5800, reserve for support new board in old version.
                bnameMA5800Reserve308(148908),        --  Board of MA5800, reserve for support new board in old version.
                bnameMA5800Reserve309(148909),        --  Board of MA5800, reserve for support new board in old version.
                bnameMA5800Reserve310(148910),        --  Board of MA5800, reserve for support new board in old version.
                bnameMA5800Reserve311(148911),        --  Board of MA5800, reserve for support new board in old version.
                bnameMA5800Reserve312(148912),        --  Board of MA5800, reserve for support new board in old version.
                bnameMA5800Reserve313(148913),        --  Board of MA5800, reserve for support new board in old version.
                bnameMA5800Reserve314(148914),        --  Board of MA5800, reserve for support new board in old version.
                bnameMA5800Reserve315(148915),        --  Board of MA5800, reserve for support new board in old version.
                bnameMA5800Reserve316(148916),        --  Board of MA5800, reserve for support new board in old version.
                bnameMA5800Reserve317(148917),        --  Board of MA5800, reserve for support new board in old version.
                bnameMA5800Reserve318(148918),        --  Board of MA5800, reserve for support new board in old version.
                bnameMA5800Reserve319(148919),        --  Board of MA5800, reserve for support new board in old version.
                bnameMA5800Reserve320(148920),        --  Board of MA5800, reserve for support new board in old version.
                bnameMA5800Reserve321(148921),        --  Board of MA5800, reserve for support new board in old version.
                bnameMA5800Reserve322(148922),        --  Board of MA5800, reserve for support new board in old version.
                bnameMA5800Reserve323(148923),        --  Board of MA5800, reserve for support new board in old version.
                bnameMA5800Reserve324(148924),        --  Board of MA5800, reserve for support new board in old version.
                bnameMA5800Reserve325(148925),        --  Board of MA5800, reserve for support new board in old version.
                bnameMA5800Reserve326(148926),        --  Board of MA5800, reserve for support new board in old version.
                bnameMA5800Reserve327(148927),        --  Board of MA5800, reserve for support new board in old version.
                bnameMA5800Reserve328(148928),        --  Board of MA5800, reserve for support new board in old version.
                bnameMA5800Reserve329(148929),        --  Board of MA5800, reserve for support new board in old version.
                bnameMA5800Reserve330(148930),        --  Board of MA5800, reserve for support new board in old version.
                bnameMA5800Reserve331(148931),        --  Board of MA5800, reserve for support new board in old version.
                bnameMA5800Reserve332(148932),        --  Board of MA5800, reserve for support new board in old version.
                bnameMA5800Reserve333(148933),        --  Board of MA5800, reserve for support new board in old version.
                bnameMA5800Reserve334(148934),        --  Board of MA5800, reserve for support new board in old version.
                bnameMA5800Reserve335(148935),        --  Board of MA5800, reserve for support new board in old version.
                bnameMA5800Reserve336(148936),        --  Board of MA5800, reserve for support new board in old version.
                bnameMA5800Reserve337(148937),        --  Board of MA5800, reserve for support new board in old version.
                bnameMA5800Reserve338(148938),        --  Board of MA5800, reserve for support new board in old version.
                bnameMA5800Reserve339(148939),        --  Board of MA5800, reserve for support new board in old version.
                bnameMA5800Reserve340(148940),        --  Board of MA5800, reserve for support new board in old version.
                bnameMA5800Reserve341(148941),        --  Board of MA5800, reserve for support new board in old version.
                bnameMA5800Reserve342(148942),        --  Board of MA5800, reserve for support new board in old version.
                bnameMA5800Reserve343(148943),        --  Board of MA5800, reserve for support new board in old version.
                bnameMA5800Reserve344(148944),        --  Board of MA5800, reserve for support new board in old version.
                bnameMA5800Reserve345(148945),        --  Board of MA5800, reserve for support new board in old version.
                bnameMA5800Reserve346(148946),        --  Board of MA5800, reserve for support new board in old version.
                bnameMA5800Reserve347(148947),        --  Board of MA5800, reserve for support new board in old version.
                bnameMA5800Reserve348(148948),        --  Board of MA5800, reserve for support new board in old version.
                bnameMA5800Reserve349(148949),        --  Board of MA5800, reserve for support new board in old version.
                bnameMA5800Reserve350(148950),        --  Board of MA5800, reserve for support new board in old version.
                bnameMA5800Reserve351(148951),        --  Board of MA5800, reserve for support new board in old version.
                bnameMA5800Reserve352(148952),        --  Board of MA5800, reserve for support new board in old version.
                bnameMA5800Reserve353(148953),        --  Board of MA5800, reserve for support new board in old version.
                bnameMA5800Reserve354(148954),        --  Board of MA5800, reserve for support new board in old version.
                bnameMA5800Reserve355(148955),        --  Board of MA5800, reserve for support new board in old version.
                bnameMA5800Reserve356(148956),        --  Board of MA5800, reserve for support new board in old version.
                bnameMA5800Reserve357(148957),        --  Board of MA5800, reserve for support new board in old version.
                bnameMA5800Reserve358(148958),        --  Board of MA5800, reserve for support new board in old version.
                bnameMA5800Reserve359(148959),        --  Board of MA5800, reserve for support new board in old version.
                bnameMA5800Reserve360(148960),        --  Board of MA5800, reserve for support new board in old version.
                bnameMA5800Reserve361(148961),        --  Board of MA5800, reserve for support new board in old version.
                bnameMA5800Reserve362(148962),        --  Board of MA5800, reserve for support new board in old version.
                bnameMA5800Reserve363(148963),        --  Board of MA5800, reserve for support new board in old version.
                bnameMA5800Reserve364(148964),        --  Board of MA5800, reserve for support new board in old version.
                bnameMA5800Reserve365(148965),        --  Board of MA5800, reserve for support new board in old version.
                bnameMA5800Reserve366(148966),        --  Board of MA5800, reserve for support new board in old version.
                bnameMA5800Reserve367(148967),        --  Board of MA5800, reserve for support new board in old version.
                bnameMA5800Reserve368(148968),        --  Board of MA5800, reserve for support new board in old version.
                bnameMA5800Reserve369(148969),        --  Board of MA5800, reserve for support new board in old version.
                bnameMA5800Reserve370(148970),        --  Board of MA5800, reserve for support new board in old version.
                bnameMA5800Reserve371(148971),        --  Board of MA5800, reserve for support new board in old version.
                bnameMA5800Reserve372(148972),        --  Board of MA5800, reserve for support new board in old version.
                bnameMA5800Reserve373(148973),        --  Board of MA5800, reserve for support new board in old version.
                bnameMA5800Reserve374(148974),        --  Board of MA5800, reserve for support new board in old version.
                bnameMA5800Reserve375(148975),        --  Board of MA5800, reserve for support new board in old version.
                bnameMA5800Reserve376(148976),        --  Board of MA5800, reserve for support new board in old version.
                bnameMA5800Reserve377(148977),        --  Board of MA5800, reserve for support new board in old version.
                bnameMA5800Reserve378(148978),        --  Board of MA5800, reserve for support new board in old version.
                bnameMA5800Reserve379(148979),        --  Board of MA5800, reserve for support new board in old version.
                bnameMA5800Reserve380(148980),        --  Board of MA5800, reserve for support new board in old version.
                bnameMA5800Reserve381(148981),        --  Board of MA5800, reserve for support new board in old version.
                bnameMA5800Reserve382(148982),        --  Board of MA5800, reserve for support new board in old version.
                bnameMA5800Reserve383(148983),        --  Board of MA5800, reserve for support new board in old version.
                bnameMA5800Reserve384(148984),        --  Board of MA5800, reserve for support new board in old version.
                bnameMA5800Reserve385(148985),        --  Board of MA5800, reserve for support new board in old version.
                bnameMA5800Reserve386(148986),        --  Board of MA5800, reserve for support new board in old version.
                bnameMA5800Reserve387(148987),        --  Board of MA5800, reserve for support new board in old version.
                bnameMA5800Reserve388(148988),        --  Board of MA5800, reserve for support new board in old version.
                bnameMA5800Reserve389(148989),        --  Board of MA5800, reserve for support new board in old version.
                bnameMA5800Reserve390(148990),        --  Board of MA5800, reserve for support new board in old version.
                bnameMA5800Reserve391(148991),        --  Board of MA5800, reserve for support new board in old version.
                bnameMA5800Reserve392(148992),        --  Board of MA5800, reserve for support new board in old version.
                bnameMA5800Reserve393(148993),        --  Board of MA5800, reserve for support new board in old version.
                bnameMA5800Reserve394(148994),        --  Board of MA5800, reserve for support new board in old version.
                bnameMA5800Reserve395(148995),        --  Board of MA5800, reserve for support new board in old version.
                bnameMA5800Reserve396(148996),        --  Board of MA5800, reserve for support new board in old version.
                bnameMA5800Reserve397(148997),        --  Board of MA5800, reserve for support new board in old version.
                bnameMA5800Reserve398(148998),        --  Board of MA5800, reserve for support new board in old version.
                bnameMA5800Reserve399(148999),        --  Board of MA5800, reserve for support new board in old version.
                bnameH901OSCL(157011),                --  OSU board of MA5800.
                bnameC04Q40E(157013),                 --  control board of MC5101-C04Q40E.
                bnamePAC1K2S12(157014),               --  Power board of MC5101-C04Q40E.
                bnamePAC600S12(157015),               --  Power board of MC5101-C04Q40E.
                bnamePDC1K2S12(157016),               --  Power board of MC5101-C04Q40E.

--MA5800C:
	            bnameH805SCUP(156057),                --  MA5800C control board H805SCUP.
		        bnameH805SCUQ(156061),                --  MA5800C control board H805SCUQ.
		        bnameH801SCUP(156082),         	      --  MA5800C control board H801SCUP.
		        bnameH801SCUQ(156083),         	      --  MA5800C control board H801SCUQ.
--WA5700:
                bnameBWAMPU(155648),            -- Control board MPU of the BWA indoor unit
                bnameBWAODU(155649),            -- BWA ODU service board

--MA561X
                bnameH838ASRB(155650),          --32-channel POTS Board of MA561X.
                bnameH831PAIA(155651),          --Power board H831PAIA of the MA561X
                bnameH831PDIA(155652),          --Power board H831PDIA of the MA561X

-- MA5610
                bnameH831CCUA(155653),          -- Master board of MA5610 Box type device
                bnameH831EIUA(155654),          -- 16 channel LAN Board of MA5610

--MA5616
                bnameH83XVDG(155655),           --16-channel board of the VDSL series of the MA5616
                bnameH83XADL(155656),           --32-channel board of the ADSL series of the MA5616
                bnameH831CCUB(155657),          -- Master board of MA5616 Box type device

--MA5652
                bnameH822GVKG(155658),          --8L VDSL2(IFX,30a),GPON(no RF)  Over ISDN
                bnameH822GVHG(155659),          --16L VDSL2(IFX,30a),GPON(no RF)  Over ISDN
                bnameH831EPUA(155660),          -- Master board of MA5652 Box type device

--MA561X
                bnameH838ASPB(155661),          --64-channel POTS Board of MA561X

--MA5618
                bnameH831CCUH(155662),
                bnameH831PDIH(155663),
                bnameH831PSUH(155664),
                bnameH835ADMD(155665),
                bnameH831VSNKE(155666),

--MA561X
                bnameH831PAIB(155667),          --Power board H831PAIB of the MA561X

--MA5652
                bnameH822RVKG(155668),          --8L VDSL2(IFX,30a),GPON(RF)  Over ISDN
                bnameH822FVKG(155669),          --8L VDSL2(IFX,30a),GE(no RF)  Over ISDN
                bnameH822RVHG(155670),          --16L VDSL2(IFX,30a),GPON(RF)  Over ISDN
                bnameH822FVHG(155671),          --16L VDSL2(IFX,30a),GE(no RF)  Over ISDN
                bnameH822RVJG(155672),          --8L VDSL2(IFX,30a),GPON(RF)  Over POTS
                bnameH822GVJG(155673),          --8L VDSL2(IFX,30a),GPON(no RF) ,Over POTS
                bnameH822FVJG(155674),          --8L VDSL2(IFX,30a),GE(no RF) ,Over POTS
                bnameH822RVGG(155675),          --16L VDSL2(IFX,30a),GPON(RF) ,Over POTS
                bnameH822GVGG(155676),          --16L VDSL2(IFX,30a),GPON(no RF) ,Over POTS
                bnameH822FVGG(155677),          --16L VDSL2(IFX,30a),GE(no RF) ,Over POTS
                bnameH821GRVAA(155713),         --24L VDSL2(IFX,17a),GPON(RF) ,Over POTS
                bnameH821GRVAB(155715),         --24L VDSL2(IFX,17a),GPON(RF) ,Over POTS

--MA5612 +-
                bnameH831CCFE(155678),          -- Master board of MA5612 Box type device
                bnameH831EPFB(155679),          -- 8-channel Vitual FE Board of MA5612
                bnameH831EIUC(155680),          -- 8-channel FE Board of MA5612
                bnameH831ASNB(155681),          -- 16-channel Vitual POTS Board of MA5612
                bnameH848ASNB(155682),          -- 16-channel POTS Board of MA5612

--MA5616
                bnameH83XVDS(155683),           -- 24-channel 17a vdsl2 Over POTS Board of MA5616
                bnameH83XVDT(155684),           -- 24-channel 17a vdsl2 Over ISDN Board of MA5616

--MA5652G
                bnameH831ASTB(155685),         -- 4-channel POTS Board of MA5652G
--OT930
                bnameH831CCEK(155690),          -- Master board of OT930 Box type device
                bnameH831EPFE(155691),          -- 4-channel Vitual FE Board of OT930
                bnameH831EDVA(155692),          -- 8-channel Vitual E1 Board of OT930
--MA5616
                bnameH832SHLH(155693),          -- 16   G.shdsl ports G.SHDSL board
                bnameH832DSLD(155694),          -- 8    bra ports ISDN board
--MA5662
                bnameH825BVMD(155695),          -- Master board of MA5662 Box type device
                bnameH825VDMD(155696),          -- 48-channel VDSL2  board for MA5662
--MA562XP
                bnameH848ASLB(155697),          -- MA562XP 8POTS

                bnameH831CCIK(155698),          -- Master board of ATN930 Box type device

--ATN931
                bnameH831CCEL(155699),          -- Master board of ATN931 Box type device
                bnameH835BVJA(155700),          -- adsl board of ATN931 Box type device
                bnameTNCM000PIU00(155701),           -- power board of ATN931 Box type device

-- SD5103
                bnameH822EPUB(155702),        -- Master board of MA562X(SD5103) Box type device
                bnameH831CCUC(155703),        -- Master board of MA5616(SD5103) Box type device
                bnameH832CCFE(155704),        -- Master board of MA5612(SD5103) Box type device

                bnameH835CALE(155705),        -- 32 ADSL+32 POTS combo board
                bnameH831EIUD(155706),        -- 4GE(combo)+4FE board
                bnameH831E81A(155707),        -- 8E1 board
                bnameH831EPWA(155708),        -- POE board
                bnameH821EPFE(155709),        -- 4GE+4FE POE board
                bnameH831EDVB(155711),        -- 4E1 Vitual board of H822CCGH
                bnameH822CCGJ(155712),        -- Master board of MA5628(SD5103) Box type device
--MA5616
                bnameASP(155714),             -- 64-channel VoIP POTS service board of MA5616

--MA5631
                bnameH831CCUN(155716),        -- Master board of MA5631(SD5103) Box type device
                bnameH831HE1A(155717),        -- 1 port EoC board of MA5631(SD5103)

--MA5628
                bnameH822CCGJA(155718),       -- Master board of MA5628 outdoor
--MA5620
                bnameH825XPUB-MA5620(156090),  -- Master board H825XPUB of MA5620(sd5133)device

--MA5626
                bnameH825XPUB-MA5626(155720),  -- Master board H825XPUB of MA5626(sd5133)device
                bnameH821EPFA-MA5626(155721),  -- 24FE Board H821EPFA of MA5626(sd5133)
                bnameH821EPFB-MA5626(155722),  -- 16FE Board H821EPFB of MA5626(sd5133)
                bnameH821EPFD-MA5626(155723),  -- 8FE  Board H821EPFD of MA5626(sd5133)
--MA5616
                bnameH83BVDSB(155800),        -- 24-channel VDSL board of MA5616
--MA5612
                bnameH837ASMB(155801),        -- 24-channel POTS board of MA5612
--MA5616
                bnameH83BVDMM(155802),        -- 48-channel board of the VDSL series of the MA5616
                bnameH832PDIA(155803),        -- 2 DC input power board of MA5616
--MA5622
                bnameHS22CCVA(155804),        -- Master board of MA5623 Box type device
                bnameHS3BCVSE(155805),        -- 24 vdsl2 + 24 pots combo board of MA5622A
                bnameHS3BVDSE(155806),        -- 24-channel vdsl2 board of MA5623

--MA5652
                bnameH832EPUA(155807),        -- Master board of MA5652 Box type device
                bnameHS22VDRE(155808),        -- 24 VDSL2 + over POTS board
                bnameHS22VDGE(155809),        -- 16 VDSL2 + over POTS board
                bnameHS22GRVD(155810),        -- 8  VDSL2 + over POTS + RF board
                bnameHS22VDOE(155811),        -- 24 VDSL2 + over ISDN board
                bnameHS22VDHE(155812),        -- 16 VDSL2 + over ISDN board
                bnameHS22VDKE(155813),        -- 8  VDSL2 + over ISDN board

--MA5621
                bnameH822CCIQ(155814),        -- Master board of MA5621 Box type device
                bnameH821EPFF(155815),        -- 4-channel GE board of MA5621
                bnameH821COME(155816),        -- 4-channel Serial board of MA5621

--MA5632
                bnameH822CCJS(155817),         -- Master board of MA5632 Box type device.

--MA5616
                bnameH831PAIC(155818),         -- Power board H831PAIC of the MA5616.
                bnameH83BVDLE(155819),         -- 32-port VDSL interface board of MA5616.
                bnameH836ADPE(155820),         -- 64-port ADSL2 interface board of MA5616.

--MA5661
                bnameH82BCVRJ(155821),         -- Master board of MA5661 Box type device.
                bnameHS2CCVPE(155822),         -- 64 VDSL+64 POTS combo board of MA5661.
                bnameH821PTBA(155823),         -- Power board H821PTBA of the MA5661
                bnameHS21WF1A(155824),         -- WIFI board HS21WF1A of the MA5661.

--MA5662
                bnameH82BCVMMMA5662(155825), -- Master board of MA5662(SD5103) Box type device.
                bnameHS3BVDMM(155826),          -- 48-channel VDSL2  board for MA5662(SD5103).
--MA5669
                bnameH822EPUD(155827),         -- 1-port autoAdpt Master board of MA5669 Box type device.
                bnameH822UPIG(155828),         -- 2-port GE board without POE of MA5669.
                bnameH822UPWG(155829),         -- 2-port GE board with POE of MA5669.

--POE
                bnameHS22EPFA(155910),        -- 24 POE board of 5626
                bnameHS22EPFB(155911),        -- 16 POE board of 5626
                bnameHS22EPFD(155913),        -- 8  POE board of 5626

--MA5616
                bnameH832PDVA(155914),        -- Double DC Power board H832PDVA of  the  MA5616
                bnameH831CCUE(155912),        -- Master board of MA5616(SD5130) Box type device

--MA5621A
                bnameHS22EPFF(155915),        -- 4 FE board of MA5621A
                bnameHS22COMF(155916),        -- 2-channel Serial board of MA5621A
                bnameH823CCIQ(155917),        -- Master board of MA5621A Box type device
                bnameHS22COME(155987),        -- 4-channel Serial Board of MA5621A, RS485 mode only
                bnameH832CCIQ(155988),        -- Master board of MA5621A(SD5132) Box type device

--MA5811S_BT
                bnameHS35BVUP(155989),               -- 16G.FAST+VECTOR board of MA5811S_BT  device.
                bnameH835BVUP(155991),               -- Master board of MA5811S_BT device.

--MA5616
                bnameH83BCVL(155918),         -- 32 VDSL+32 POTS combo board of MA5616

--MA5623
                bnameHS22CCVB(155920),        -- Master board of MA5622A(SD5103) Box type device

--MA5616
                bnameH83BVCMM(155921),        -- 48 VDSL baoard, supportting for vector
                bnameH831VPBB(155922),        -- vector control engine board

                bnameH831CCUD(155923),        -- Master board of MA5616(SD5130) Box type device
                bnameH831PAIBA(155924),       -- Power board H831PAIBA of the MA561X
                bnameH825EPUB(155925),        -- Master board of MA5620/26(SD5132) Box type device
                bnameH823EPUB(155926),        -- Master board of MA5626-8 PoE(SD5130) Box type device
                bnameHS22EPFG(155927),        -- 8 GE board of MA5626(SD5130)
                bnameH832PDSA(155992),        --DC Power board H832PDSA of  the  MA5616.
                bnameH832PDVSA(155993),       --DC Power board H832PDVSA of  the  MA5616.
                bnameH832PDNSA(155994),       --DC Power board H832PDNSA of  the  MA5616.
                bnameH83DSDMM(155995),        -- 48-channel super vectoring vdsl2+ service board
                bnameCSM(156063),             -- 48-channel Vectoring VDSL2 + POTS COMBO service board, supports super vectoring feature.
                bnameH832PDMSA(156064),       --  DC Power board H832PDMSA of the MA5616.
		        bnameH832PDMSB(156075),       --  DC Power board H832PDMSB of the MA5616.
    		    bnameH832CCUE(156084),        --  Master board of MA5616 device

--MA5811S-AE08
                bnameH835BGUD(155998),       --Master board of MA5811S-AE08 device.
                bnameHS35BGUD(155999),        --8 G.FAST board of MA5811S-AE08  device(AC).
                bnameHS35BGUDR(156000),       --8 G.FAST board of MA5811S-AE08  device (RPOE).
                bnameH82DEFMG(156034),        --Master board of MA5811S-AE48/DE48 device.
                bnameHS2DEFMG(156035),        --48 G.FAST board of MA5811S-AE48/DE48 service board.
                bnameH835BGUDM(156044),       --Master board of MA5811S-AE08 device(AC).
                bnameHS35BGUDM(156048),       --8 G.FAST board of MA5811S-AE08  device(AC).
                bnameH835BGUDR(156054),       --Master board of  of MA5811S-AE08 PD.

--MA5811S-G5
                bnameH82EEFUG(156066),        --Master board of MA5811S-AE08/AE16/DE16 device.
                bnameHS2EEFUG(156067),        --16 G.FAST board of MA5811S-DE16 service board.
                bnameH82EEFMG(156068),        --Master board of MA5811S-DE48 device.
                bnameHS2EEFMG(156069),        --48 G.FAST board of MA5811S-DE48 service board.
                bnameHS2EEFUR(156071),        --16 G.FAST remote board of MA5811S-AE16 service board.
                bnameHS2EEFJR(156072),        --8 G.FAST remote board of MA5811S-AE08 service board.
                bnameH82EBFVM(156073),        --Master board of MA5811S-AE16(8SV uplink) device.
                bnameHS2EBFVM(156074),        --16 G.FAST service board of MA5811S-AE16(8SV uplink) device.
                bnameH82EEFUG-DE16(156080),   --Master board of MA5811S-DE16-G5 device.

--MA5812S
                bnameH82EEFKR(156093),        --Master board of MA5812S-AE08 device.
                bnameHS2EEFKR(156091),        --8 G.FAST board of MA5812S-DE16 service board.
                bnameHS2EEFKA(156092),        --8 G.FAST board of MA5812S-DE16 service board.

--MA5818
                bnameH831CCMAMA5818(156036),   --Master board of MA5818 device.
                bnameVPJ(156037),              --G.FAST vectoring control engine board of the MA5818 device.
                bnameINT(156038),              --Serial board(without VP chip) of the MA5818 device.
                bnameH831PAMA(156039),         --550W AC power board of the MA5818 device.
                bnameH831PAMB(156040),         --550W AC power board(support standby power) of the MA5818 device.
                bnameH831PDMA(156041),         --550W DC power board of the MA5818 device.
                bnameFDS(156042),              --24 line G.FAST serial board of the MA5818 device.
                bnameVPQ(156081),              --G.FAST vectoring control engine board of the MA5818 device.
		        bnameH831CCMB(156085),   	--Master board of MA5818 device
		        bnameH831PDMB(156086),   	--500W DC power board(support standby power) of the MA5818 device
                bnameH838VPDE(156100),         --MA5818 VP board H838VPDE sd5573
                bnameH832CCMB(156101),          --Master board of MA5818 device
				bnameH83GSDPD(156102),         -- 64-channel super vectoring vdsl2+ service board
				bnameH833CCMS(156103),         --Master board of MA5818 device
       		    bnameH83GCSPE(156105),	       -- 64-channel Vectoring VDSL2 + POTS COMBO service board, supports super vectoring feature.

--MA5600T
		        bnameH803OPGE(156087),         -- H803OPGE BOARD
	            bnameH803EDTB(156088),         -- H803EDTB BOARD
--MA5621
                bnameH823E2IQ(156043),         --Master board of the MA5621(sd5130) device.
                bnameHS22EPFFMA5621(156049),   --4 FE board of MA5621.

--MA5621H
                bnameH825CCIQ(156094),         --Master board of MA5621H device.

--MA5821
                bnameH823TCIAT(156045),         --Master board of MA5821(sd5568) device.
                bnameHS23TCIAT(156046),         --24GE and 1*10GE board of MA5821(sd5568) device.
                bnameH825XCWA(156050),          --Master board of  of MA5821 POE.
                bnameHS22EPGP(156051),          --24 GE board of MA5821 POE.

--MA5878
                bnameH833CCFE(156001),        -- Master board of MA5878.
                bnameHS31EIUC(156002),        -- 8 FE vitual board of MA5878.
                bnameHS31GE2A(156003),        -- 2 GE vitual board of MA5878.
                bnameHS31ASNB(156004),        -- 16-channel VoIP POTS service board of MA5878.
                bnameHS31ASLB(156005),        -- 8-channel VoIP POTS service board of MA5878.
                bnameH836CCLD(156032),        -- Master board of MA5878(SD5568).
                bnameH831EGUC(156033),        -- 8GE board of MA5878 device.
                bnameHS22EPGDMA5878(156047),  -- 8GE board of MA5878 device.

--MA582X R021
                bnameH835XPUB(156104),        -- Master board of MA582xS
				bnameH838XPUB(156106),        -- Master board of MA582xS-G01

--MA582X
                bnameHS22EPGB(156006),        -- 16GE board of MA582x device.
                bnameH826XPUB(156007),        -- Master board of MA582x 16GE device.
                bnameHS22EPGD(156008),        -- 8GE board of MA582x device.

--MA582x R019C30
                bnameH828XPUB(156095),        -- Master board of MA582xS/MA582xH
                bnameH822ASMC(156096),        --MA5822S 24POTS
                bnameH822ASNC(156097),        --MA5822S 16POTS
                bnameH822ASLC(156098),        --MA5822S 8POTS

--MA5612
                bnameH835CCFE(156009),        -- Master board of MA5612 Box type device.

--MA5616
                bnameCAL(156030),             -- 32 ADSL+32 POTS serial combo board.
                bnameH832PDVSB(156031),       -- DC Power board H832PDVSB of the MA5616.

--MA5623A
                bnameHS22CCVW(155928) ,       -- Master board of MA5623A(sd5130)device.
                bnameHS3BVCMM(155929),        -- 48 VDSL baoard, supportting for vector
--MA5633
                bnameH822CCKRA(155930),       -- Master board of MA5633(sd5130)device.
                bnameHS33CDAA(155931),        -- DOCSIS virtual board of MA5633
                bnameH822CCKRD(155996),       -- Master board of MA5633(sd5130) new device.
                bnameHS33CDAF(155997),        -- MA5633 new sevice board HS33CDAF
                bnameHS33CDAG(155601),        -- MA5633 new sevice board HS33CDAG
--MA5633
                bnameH822CCKRP(156065),       -- R18C00 Master board of MA5633(sd5130) new device.
                bnameH822CCKRR(156076),       --  Master board of MA5833 new device.
                bnameHS33CDAH(156077),        --  MA5833 new sevice board HS33CDAH
                bnameHS33CDAI(156078),        --  MA5833 new sevice board HS33CDAI


                bnameH906CGHF(156010),         -- 16*XG/G GPON combo board of MA5800.
                bnameH906CGUF(156011),         -- 16*XG/G GPON combo board of MA5800.
                bnameH903OXEG(156012),         --  24*10GE board of MA5800.
                bnameH903XGLF(156013),         -- 16*XG GPON board of MA5800.
                bnameH903CSHFE(156014),        -- 16*XGS GPON and GPON combo board of EA5800.
                bnameH903FLHFE(156015),        -- 16*flex-PON board of EA5800.
                bnameH903GPHFE(156016),        -- 16*GPON board of EA5800.
                bnameH903XEHF(156017),         -- 16*10G EPON board of MA5800.
                bnameH903GPSF(156018),         -- 16*GPON board of MA5800.
                bnameH903XSHF(156019),         -- 16*10G XGS-PON board of MA5800.
                bnameH901FGHF(156020),         -- 16*XG/G GPON combo board of MA5800.
                bnameH905OXHD(156021),         -- 8*10GE P2P board of MA5800.
                bnameH903XSHFE(156022),        -- 16*10G XGS-PON board of EA5800.
                bnameH905NXED(156023),         -- 8*Port ETH board of MA5800
                bnameH907CGHF(156024),         -- 16*XG/G GPON combo board of MA5800.
                bnameH907CGUF(156025),         -- 16*XG/G GPON combo board of MA5800.
                bnameH905FLHF(156026),         -- 16*flex-PON board of MA5800.
                bnameH905GPHF(156027),         -- 16 GPON board of MA5800.
                bnameH905FLHFE(156028),        -- 16*flex-PON board of EA5800.
                bnameH905XEHD(156029),         -- 8*XG EPON board of MA5800.

--MA5616
                bnameH83BVCL(155932),         -- 32 VDSL + Vectoring board of MA5616

--MA5616
                bnameH832PDVAA(155933),        -- Double DC Power board H832PDVAA of  the  MA5616, supportting vector vp subboard

--MA5698
                bnameHS31GC4A(155934),         -- 4GE baoard(2GE+2GE COMBO) for MA5698.
--MA5694
                bnameH821CCIC(155935),         -- Master board of MA5694(sd5130)device.
                bnameHS21GE4A(155936),         -- 4GE baoard for MA5694.
--MA5678
                bnameH831CCLF(155952),         -- Master board of MA5678(sd5130)device.
                bnameH831E41B(155938),         -- 4E1 baoard for MA5678.
                bnameHS38ASRB(155939),         -- 32POTS baoard for MA5678.
                bnameHS31GE4A(155940),         -- 4GE baoard for MA5678.
--MA5698
                bnameH831CCMC(155941),         -- Master board of MA5698(sd5130)device.

--MA5616A
                bnameH831PAVD(155919),         -- 400W AC for MA5616.
                bnameH831PAVDA(155937),        -- 400W AC + Vector for MA5616.
--MA582X
                bnameH825XPUB(155944),         -- Master board of MA582x(sd5133)device.

--MA5622A  R313C00
                bnameHS3BCVSB(155945),         -- 16 VDSL+16 POTS combo board of MA5622A(SD5103).
                bnameHS3BCVSD(155946),         --  8 VDSL+ 8 POTS combo board of MA5622A(SD5103).

--MA5652   R313C00
                bnameH823UPVB(155947),         -- Master board of MA5652(sd5130) device.
                bnameHS23UPVB(155948),        -- 16 VDSL + Vectoring board of MA5652(sd5130) device.

--MA5611S   R313C10
                bnameHS26BVVS(155950),         -- 16 VDSL + Vectoring board of MA5611S FTTS device.
                bnameH826BVVS(155951),         -- Master board of MA5611S FTTS device.

--MA5694S   R313C10 DSL DOCK
                bnameH822CC3G(155957),          --DSL DOCK Master board of MA5694S(sd5130) device.
                bnameHS31EPFB(155959),          --3GE port board.

--MA5821    R313C10
                bnameHS22EPGE(155961),         -- Virtual 24GE board of the MA5821.

--MA5616    R313C10
                bnameH836VPAA(155963),         -- VPA board for MA5616.
                bnameH832PDNAA(155964),        -- Power board (for NLV) of the MA5616.

--MA5612    R15C10
                bnameH831EPFF(155965),          -- 2 GE Vitual Board of MA5612

--MA5612    R16C00
                bnameH831ASLB(155985),          -- 8 POTS Vitual Board of MA5612
                bnameMA5612ASL(155990),         -- 8-channel VoIP POTS service board of MA5612

--MA5633    R16C00
                bnameHS33CDAE(155986),          -- DOCSIS virtual service board of MA5633.

--MA5694S   R313C10 PON DOCK
                bnameH822UPWC(155970),          --PON DOCK Master board of MA5694S(sd5130) device.
                bnameHS22GE4A(155971),          --4GE port board.
                bnameHS22GE3A(155984),          --3GE port board.

--MA5611S   R312C91
                bnameH82BCVMM(155972),       -- Master board of MA5611S-DE48 north Americal device.

--MA5611S   R313C10
                bnameH82DVCMM(155949),         -- Master board of MA5611S-DE48(sd5130) FTTS device.
                bnameHS2DVCMM(155962),         -- 48 VDSL + Vectoring board of MA5611S-DE48(sd5130) FTTS device.

                bnameH822CCKRB(155973),       -- Master board of mini MA5633(sd5130) device
                bnameHS33CDAB(155974),        -- DOCSIS virtual board of mini MA5633

--MA5616   R015C00
                bnameH831EDTB(155975),          -- E1 board of MA5616 for CCUE and CCUD.

--MA5611S  R015C00
                bnameH823UPVBP(155976),         -- Master board of MA5611S-AE16(sd5130) FTTS device for Oman.
                bnameHS23UPVBP(155977),         -- 16 VDSL2 board of MA5611S-AE16(sd5130) FTTS device for Oman.
                bnameH826BVUP(155978),          -- Master board of MA5611S-DE16(sd5130) FTTS device for BT.
                bnameHS26BVUP(155979),          -- 16 VDSL2 board of MA5611S-DE16(sd5130) FTTS device for BT.

--MA5616  R015C10
                bnameCCM(155982),              -- 48-channel Vectoring VDSL2 + POTS COMBO service board
                bnameVCP(155983),              -- 64-channel Vectoring VDSL2 + SPL service board

--MA5611S  R015C10
                bnameH82BDVJM(155966),         -- Master board of MA5611S-AE08(sd5130) FTTS device.
                bnameHS2BDVJM(155967),         -- 8 VDSL2 board of MA5611S-AE08(sd5130) FTTS device.
                bnameH822CCKRC(155980),        -- Master board of MA5633(sd5130) device
                bnameHS33CDAC(155981),         -- DOCSIS virtual board of MA5633

--MA5611S  R017C10
                bnameH82BBVJM(156052),      --Master board of  of PH MA5611S-AE08 PD.
                bnameH82BBVUM(156053),      --Master board of  of PH MA5611S-AE16 PD.
                bnameHS2BBVJM(156055),      --8 VDSL board of PH MA5611S-AE08 PD.
                bnameHS2BBVUM(156056),      --16 VDSL board of PH MA5611S-AE16 PD.

--MA5821A  R017C10
                bnameH825CCIA(156058),            -- Master board of MA5821A device.
                bnameH831PAIS(156059),            -- AC Power board of MA5821A device.

--MA5626B  R016C10
                bnameH822EPUBM(156060),        -- Master board of MA5626B(SD5103) Box type device.

--MA5811S  R016C00
                bnameHS35FDEM(155968),         -- 16G.FAST+VECTOR board of MA5811S FTTS device.
                bnameH835FDEM(155969),         -- Master board of MA5811S-DE16 FTTS device.

-- WLAN
                bnameWA611WACA(160000),        -- Master board of WS6603(WLAN V1R2) Box type device
                bnameWA611PAIA(160001),        -- power board of WS6603(WLAN V1R2) Box type device
                bnameWA611PDIA(160002),        -- power board of WS6603(WLAN V1R2) Box type device
                bnameH801WACA(160003),         -- AC service Board of WS6800/WS6803(WLAN V1R3)

--SRG  series,   frome 190001
                bnameFWF1FCONT(190003),              -- SRG2200-4, FWF1FCONT, WIFI board
                bnameSU111GPNT(190008),              -- SRG2200-4, SU111GPN,  GPON access board
                bnameSU11FFXS(190009),               -- SRG2200-4, SU11FFXS,  16-pots vioce board
                bnameSU11EWFS(190012),               -- 32-pots fxs board
                bnameSU11E4MS(190013),               -- 4-pots fxs board
                bnameSU11E4MO(190014),               -- 4-pots fxo board
                bnameSU11E4MM(190015),               -- 2-pots fxs + 2-pots fxo board
                bnameSU11E2MV(190016),               -- 2-pots ve1 board
                bnameSU11UP2A(190017),               -- PON board(3 mode)

-- UA5000 from 204800
                bnameH601ADLF(204810),          -- 16-channel ADSL over ISDN service board. This is a full-broadband service board.
                bnameH603CSMC(204811),          -- 16-channel ADSL2+ and POTS combo board, with the Infineon chipset
                bnameH603CSR(204812),           -- 32-channel ADSL2+ and POTS combo board, with the Infineon chipset
                bnameH601TSSC(204815),          -- UA broadband and narrowband test board
                bnameH603ADR(204816),           -- The H603ADRB board is a UA 32-channel ADSL2+ service board. It uses the Infineon inband
                                                --  solution and belongs to the H603ADR series.
                bnameH602CSM(204817),           -- Board of the H602CSM series
                bnameH612IPMB(204818),          -- New control board for the master Frame of the UA5000 for BT
                bnameH612APSB(204819),          -- New control board for the slave Frame of the UA5000 for BT

                bnameH602CSV(204820),           -- New boards of the CSV series for BT
                bnameH602CSVA(204821),          -- New board of the CSV series for BT
                bnameH602CSVB(204822),          -- New board of the CSV series for BT
                bnameH602CSVC(204823),          -- New board of the CSV series for BT
                bnameH602CSVD(204824),          -- New board of the CSV series for BT
                bnameH602CSVE(204825),          -- New board of the CSV series for BT
                bnameH602CSVF(204826),          -- New board of the CSV series for BT
                bnameH602CSVG(204827),          -- New board of the CSV series for BT
                bnameH602CSVH(204828),          -- New board of the CSV series for BT
                bnameH602CSVI(204829),          -- New board of the CSV series for BT
                bnameH602CSVJ(204830),          -- New board of the CSV series for BT
                bnameH602CSVK(204831),          -- New board of the CSV series for BT
                bnameH602CSVL(204832),          -- New board of the CSV series for BT
                bnameH602CSVM(204833),          -- New board of the CSV series for BT
                bnameH602CSVN(204834),          -- New board of the CSV series for BT
                bnameH602CSVO(204835),          -- New board of the CSV series for BT
                bnameH602CSVP(204836),          -- New board of the CSV series for BT
                bnameH602CSVQ(204837),          -- New board of the CSV series for BT
                bnameH602CSVR(204838),          -- New board of the CSV series for BT
                bnameH602CSVS(204839),          -- New board of the CSV series for BT
                bnameH602CSVT(204840),          -- New board of the CSV series for BT
                bnameH602CSVU(204841),          -- New board of the CSV series for BT
                bnameH602CSVV(204842),          -- New board of the CSV series for BT
                bnameH602CSVW(204843),          -- New board of the CSV series for BT
                bnameH602CSVX(204844),          -- New board of the CSV series for BT
                bnameH602CSVY(204845),          -- New board of the CSV series for BT
                bnameH602CSVZ(204846),          -- New board of the CSV series for BT

                bnameH605CSR(204847),           -- 32-channel ADSL2+ broadband and narrowband combo service board

                bnameH612SPLI(204874),           -- SPL board, which uses SCM 89C51, provides 96 relays for separating
                                                 -- the broadband and narrowband services, and supports only the ADSL
                                                 -- service when used with the CSRI board
                bnameH612GAUA(204875),           -- New board for BT. This board supports the S+C feature.
                bnameH612SDLB(204876),           -- 16-channel broadband service board of the SHDSL access
                bnameH603ADRF(204877),           -- 32-channel ADSL2+Annex B series board
                bnameH601GP1A(204878),           -- UA5000 GPON board which unites Broadband and narrowband
                bnameH601EP1A(204879),           -- UA5000 EPON board which unites Broadband and narrowband
                bnameH601XP1A(204880),           -- UA5000 XPON board which unites Broadband and narrowband has 5*FE Electric Ports, 4*E1 Ports, 2*GE Optical Ports, 1GE Electric Port and 1GPON Port

-- AMG
                bnameAG03PVM(262154),           -- Control board AG03PVM
                bnameH602PVU8(262155),          -- Active/standby E1 PVU board, that is, the low-density active/standby E1
                                                -- PVU board under the PVM that provides 8 E1 ports
                bnameH602PVU4(262156),          -- Active/standby E1 PVU board, that is, the low-density active/standby E1
                                                -- PVU board under the PVM that provides 4 E1 ports
                bnameH601PVMB(262157),          -- High density control board H601PVMB. This board supports master extended + slave extended.
                bnameSDLE(262158),              -- 8-channel G.SHDSL service board
                bnameEDT(262159),               -- 16-channel narrowband E1 interface board
                bnameTDT(262160),               -- 16-channel narrowband T1 interface board
                bnameH601RSUG(262161),          -- RSP and G.SHDSL integrated board (a simple integration of RSP and SDL).
                                                -- This board provides two G.SHDSL ports.
                bnameH602RSUG(262162),          -- RSP and G.SHDSL combo board (RSP and G.SHDSL share a CPU).
                                                -- This board provides two G.SHDSL ports and one E1 port.
                bnameH601PVMA(262163),          -- H601PVMA board, which is used in the low-density Frame and supports active/standby E1 ports
                bnameH801PVMA(262164),          -- P300 narrow control board H801PVMA (electric interface board)
                bnameH801PVMB(262165),          -- P300 narrow control board H801PVMB (optical interface board)
                bnameH801HWTF(262166),          -- P300 H801HWTF HWT interface board
                bnameH801HWCF(262167),          -- P300 H801HWCF HWC interface board
                bnameH801TSSA(262168),          -- P300 narrowband test board: H801TSSA
                bnameH801ASLG(262169),          -- P300 narrowband service board: H801ASLG
                bnameH801DSCD(262170),          -- P300 2B1Q ISDN digital service board: H801DSLD
                bnameH801PWXA(262171),          -- P300 narrowband power board: H801PWXA
                bnameH801SDLT(262172),          -- P300 TDM SHDSL board: H801SDLT
                bnameH801TSSB(262173),          -- P300 test board
                bnameH801ASCK(262174),          -- P300 ASL32 service board
                bnameH801EDTA(262175),          -- P300 EDT interface board

                bnameAG02PVMC(262180),          -- AG02PVMC board, which is used in the low-density Frame and provides the multi-mode optical port
                bnameAG03PVMC(262181),          -- AG03PVMC board, which is used in the high-density Frame and provides the multi-mode optical port
                bnameH601PVMBB(262182),         -- H601PVMBB board (2.0KM), which is used in the high-density Frame and provides the optical port
                bnameH601PVMBF(262183),         -- H601PVMBF board (15.0KM), which is used in the high-density Frame and provides the optical port
                bnameH601PVMBG(262184),         -- H601PVMBG board (40.0KM), which is used in the high-density Frame and provides the optical port

                bnameH612PVMB(262185),          -- High-density control board H612PVMB, which supports master extended + slave extended

                bnameH612HWCF(262186),          -- BT H612HWCF  HWC transfer board
                bnameH612HWTF(262187),          -- BT H612HWTF  HWT transfer board
                bnameH612HWFF(262188),          -- BT H612HWTF  HWF transfer board
                bnameH612PSTF(262189),          --BT H612PSTF board: HW transfer board of the small-capacity Frame H612HABF
                bnameH612HLSF(262190),          -- BT H612HLSF transfer board
                bnameH612HLAF(262191),          -- BT H612HLAF transfer board
                bnameH612HLEF(262192),          -- BT H612HLEF transfer board
                bnameH612SLTF(262193),          -- BT H612SLTF transfer board
                bnameH612EFTF(262194),          -- BT H612EFTF transfer board
                bnameH612E1TF(262195),          -- BT H612E1TF transfer board
                bnameH612TSTF(262196),          -- BT H612TSTF transfer board

                bnameH602PWX(262197),           -- Narrowband power board with the CPU

                bnameH612PVMBG(262198),         -- H612PVMBG board (40.0KM), which is used in the high-density Frame and provides the optical port
                bnameH612PWXB(262199),          -- BT H612PWXB power board

                bnameH612RATF(262200),          -- BT H612RATF transfer board
                bnameH612SLPF(262201),          -- BT H612SLPF transfer board
                bnameH612WATF(262202),          -- BT H612WATF transfer board
                bnameH612PRTF(262203),          -- BT H612PRTF transfer board
                bnameH601PVMC(262204),          -- Low-density control board H601PVMC
                bnameH601PVMCG(262205),         -- H601PVMC optical interface board, which supports the maximum transmission distance of 40.0 km
                bnameH603RSUG(262656),          -- H603RSUG
                bnameA04(262657),               -- A04
                bnameA08(262658),               -- A08
                bnameDSLD(262659),              -- 16-channel digital service board
                bnameDSLE(262660),              -- 16-channle digital service board
                bnameH601PVMD(262662),          -- H601PVMD
                bnameH301HWTA(262663),          -- H301HWTA
                bnameH602TSSB(262664),          -- H602TSSB
                bnameCC0SASL(262665),           -- CC0SASL
                bnameH601PVME(262669),          -- H601PVME board
                bnameH601IPMD(262207),          -- H601IPMD board
                bnameH612IPMD(262208),          -- H612IPMD board
                bnameH605VDMB(262209),          -- H605VDMB board
                bnameH603SHLB(262210),          -- H603SHLB board
                bnameH601CPMA(262211),          -- H601CPMA board
                bnameH601COPA(262212),          -- H601COPA board
                bnameA64(262213),               -- A64 board
                bnameH612PVMT(262214),          -- H612PVMT board
                bnameGIU(262215),               -- GIU board(H612IPMD)
                bnameH612HWCB(262216),          -- H612HWCB board
                bnameH612HWTB(262217),          -- H612HWTB board
                bnameH612PVMD(262218),          -- H612PVMD main board
-- 8011
                bnameCR01LPUF(528384),             --For NE40, new main control card of NE40
                bnameCR01CLKD(528385),             --For NE80, new main control card of NE80
                bnameCR01NETD(528386),             --For NE80, new switch card of NE80
                bnameCR03NETH(528387),             --For NE80, new switch card of NE80
                bnameCR03SRUD(528388),             --For NE40-2,NE40-8,new main control card of NE40
                bnameCR03SRUE(528389),             --For NE40-4 or NE40-8,new main control card of NE40
                bnameCR03MPUF(528390),         --For NE80, new main control card of NE80
                bnameCR01M2GSR(528391),            --For NE80, new power supply card of NE80
                bnameCR01SPUA(528392),             --Flexible Card Service Processing Unit A
                bnameCR01SPUB(528393),             --Flexible Card Service Processing Unit B, NetStream Traffic Statistics Service Board
                bnameCR01SPUC(528394),             --Flexible Card Service Processing Unit C
                bnameCR01CLPU(528395),             --
                bnameCR01LPUE(528396),       --For NE40 & NE80 , mother card of NE80 and NE40
                bnameCR01MPUE(528397),       --For NE80 , main control card of NE80
                bnameCR01SRUC(528398),       --For NE40-2 , main control card of NE40-2
                bnameRS01SFCB(528399),         --For S8016 SPECIAL, SWITCH CARD
                bnameCR01NETSTREAMB(528400),         --For ne40&ne80, netstream board

-- 8031:

                bnameCX00UNBD(536832),                   -- Unknown board
                bnameCX21SCUB(536833),                   -- Switching and Control Processing Unit - 24 Port Fast Ethernet Electrical Interface
                bnameCX21SCUC(536834),                   -- General Switch Control Unit-24 Ports 100BASE-FX Interface Card(SFP)
                bnameCX31E2GE0(536835),                  -- 2 Ports 1000Base-T Gigabit Ethernet Electrical Interface Card
                bnameCX31E2GF0(536836),                  -- 2 Ports Gigabit Ethernet SFP Optical Interface Card  With LC Connector
                bnameCX31E2GFE0(536837),                 -- 2 Ports Gigabit Ethernet SFP Optical Interface Card With LC Connector (Enhance Board)
                bnameCX31E4GE0(536838),                  -- 4 Ports 1000Base-T Gigabit Ethernet Electrical Interface Card
                bnameCX31E4GF0(536839),                  -- 4 Ports Gigabit Ethernet SFP Optical Interface Card  With LC Connector
                bnameCX31EGFE0(536840),                  -- 16 Ports Fast Ethernet Electrical Interface Card
                bnameCX31EGFF0(536841),                  -- 16 Ports Fast Ethernet SFP Optical Interface Card With LC Connector
                bnameCX31R2GF0(536842),                  -- 2 Ports Gigabit Ethernet RPR-SFP Optical Interface Card With LC Connector
                bnameCX31SCUA0(536843),                  -- 48G Switching and Control Processing Unit
                bnameCX31SCUB0(536844),                  -- 24G Switching and Control Processing Unit
                bnameCX21FMCB(536845),                   -- CX200B Fan Monitor Control Board
                bnameCX31FMCBA(536846),                  -- CX300A Fan Monitor Control Board
                bnameCX31FMCBB(536847),                  -- CX300B Fan Monitor Control Board
                bnameCX21POWDC(536848),                  -- CX200B DC Power Monitor Control Board
                bnameCX31POWDC(536849),                  -- CX300A/B DC Power Monitor Control Board
                bnameCX21POWAC(536850),                  -- CX200B AC Power Monitor Control Board
                bnameCX31POWAC(536851),                  -- CX300A/B AC Power Monitor Control Board
                bnameCX31R2UF0(536852),                  -- 2-Port STM-16c/OC-48c RPR Interface Card(SFP)
                bnameCX31E4GFF(536853),                  -- 4-Port 1000BASE-X Interface Card(Enhanced II,SFP)
                bnameCX31E2GFF(536854),                  -- 2-Port 1000BASE-X Interface Card(Enhanced II,SFP)
                bnameCX31MPUA(536855),                   -- CX380 Main Processing Unit
                bnameCX31LPUA(536856),                   -- CX380 Switch Forward Unit
                bnameCX31E1XE(536857),                   -- CX380 1-Port 10GE Electrical Interface Card(RJ45)
                bnameCX31E8GE(536858),                   -- CX380 8-Port 1000BASE-T Interface Card(RJ45)
                bnameCX31EAGE(536859),                   -- CX380 10-Port 1000BASE-T Interface Card(RJ45)
                bnameCX31ECGE(536860),                   -- CX380 12-Port 1000BASE-T Interface Card(RJ45)
                bnameCX31EGGE(536861),                   -- CX380 16-Port 1000BASE-T Interface Card(RJ45)
                bnameCX31E1XF(536862),                   -- CX380 1-Port 10GE Optical Interface Card(XFP)
                bnameCX31E8GF(536863),                   -- CX380 8-Port 1000BASE-X Interface Card(SFP)
                bnameCX31EAGF(536864),                   -- CX380 10-Port 1000BASE-X Interface Card(SFP)
                bnameCX31ECGF(536865),                   -- CX380 12-Port 1000BASE-X Interface Card(SFP)
                bnameCX31EGGF(536866),                   -- CX380 16-Port 1000BASE-X Interface Card(SFP)
                bnameCX3B1AUAC(536867),                  -- CX380 Chassis(8U,2 MCU Slots,2 SRU Slots,8 SIC Slots,2 Power Supply Slots,Without MCU and Power Module)
                bnameCX31AGE1B(536868),                  -- CX380 16-Port ATM Service E1 75ohm Interface Card
                bnameCX31AGE1A(536869),                  -- CX380 16-Port ATM Service E1 120ohm Interface Card
                bnameCX31AGT1(536870),                   -- CX380 16-Port ATM Service T1 100ohm Interface Card
                bnameCX31A1CC(536871),                   -- CX380 1-Port Channelized STM-1 ATM Service Interface Card
                bnameCX31A4CC(536872),                   -- CX380 4-Port Channelized STM-1 ATM Service Interface Card
                bnameCX31CMPB(536873),                   -- CX380 CPU ATM Service Pinch Board
                bnameCX31CLKA(536874),                   -- CX380 CX31MPUA Clock Pinch Board
                bnameCX31TCMA(536875),                   -- CX380 CX31SFUA TCAM Pinch Board
                bnameCX31BAKE(536876),                   -- CX380 Backplane

                bnameCX61SRUA0(536877),                  -- CX600-8 - Main Process Switch Fabric Unit
                bnameCX61MPUB0(536878),                  -- CX600-16 Main Processing Unit
                bnameCX61SFUD0(536879),                  -- CX600-8 Switch Fabric Unit
                bnameCX61SFUF0(536880),                  -- CX600-16 Switch Fabric Unit
                bnameCX61FCBA(536881),                   -- CX600 Fan module
                bnameCX61TSUA(536882),                   -- CX600 TSU Module
                bnameCX61SPUB(536883),                   -- CX600 NETSTREAM Module
                bnameCX61LPUA(536884),                   -- CX600 LPUA Module
                bnameCX61LPUG(536885),                   -- CX600 LPUG Module

                bnameCX31R2GFT(536886),                  -- 2-Port 1000BASE-X RPR Interface Card (Timing)
                bnameCX31E2GFET(536887),                 -- 2-Port 1000BASE-X Interface Card (Timing, Enhanced I)
                bnameCX31T8CE1A(536888),                 -- 8-Port,Channelized E1,TDM,DB68,75ohm,Interface Card
                bnameCX31T8CE1B(536889),                 -- 8-Port,Channelized E1,TDM,DB68,120ohm,Interface Card
                bnameCX31T8CT1(536890),                  -- 8-Port,Channelized T1,TDM,DB68,100ohm,Interface Card

                bnameCX21SCUD(536891),                   -- General Switch Control,2GE(SFP)+16FE(SFP)+8FE(RJ45) Mixed Interface Card

                bnameCX31T4CE1A(536892),                 -- 4-Port,Channelized E1,TDM,DB68,75ohm,Interface Card
                bnameCX31T4CE1B(536893),                 -- 4-Port,Channelized E1,TDM,DB68,120ohm,Interface Card
                bnameCX31T4CT1(536894),                  -- 4-Port,Channelized T1,TDM,DB68,100ohm,Interface Card
                bnameCX31T1CCE1(536895),                 -- CX,CX31T1CC,Channelized STM-1 TDMPWE Interface Card

                bnameCX3E1FBXA(536896),                  -- CX380 CX3E1FBXA CX380 Upper FAN Box
                bnameCX3E1FBXB(536897),                  -- CX380 CX3E1FBXB CX380 Under FAN Box

                bnameCX22EOFE(536898),                   -- CX200D, 24FE(RJ45)+2GE(SFP) Mixed Interface Card
                bnameCX61LPUF(536899),                   -- CX600 LPUF Module
                bnameCX61LPUK(536900),                   -- CX600 LPUK Module

                bnameCX21SCUBVD(536901),                 -- Switching and Control Processing Unit - 24 Ports Fast Ethernet Electrical Interface and 1 Port MEth Interface
                bnameCX21SCUCVC(536902),                 -- General Switch Control Unit-24 Ports 100BASE-FX Interface Card(SFP) and 1 Port MEth Interface


                bnameCX31TMCE1A(536903),                 -- CX,CX31TMCE1A,32-Port,Channelized E1,FB,75ohm,Interface Card,1*1
                bnameCX31TMCE1B(536904),                 -- CX,CX31TMCE1B,32-Port,Channelized E1,FB,120ohm,Interface Card,1*1
                bnameCX31TGCE1A(536905),                 -- CX,CX31TGCE1A,16-Port,Channelized E1,FB,75ohm,Interface Card
                bnameCX31TGCE1B(536906),                 -- CX,CX31TGCE1B,16-Port,Channelized E1,FB,120ohm,Interface Card,1*1
                bnameCX31A4CF(536907),                   -- CX,CX31A4CF,4-Port,STM-1,SFP,Interface Card,1*1
                bnameCX31A1KF(536908),                   -- CX,CX31A4CF,1-Port,STM-4,SFP,Interface Card,1*1

                bnameCX31PWRAC(536909),                      -- CX380 CX31PWRAC AC Power
                bnameCX31PWRDC(536910),                      -- CX380 CX31PWRDC DC Power
                bnameCX31CLOCKA(536911),                     -- CX380,CX31CLKA,Stratum 3 Clock Unit
                bnameCX31E4GFS(536912),                      -- CX380,CX31E4GFS,4-Port 1000BASE-X Optical Interface Card(SyncE,SFP)
                bnameCX31E4GFP(536913),                      -- CX380,CX31E4GFP,4-Port 1000BASE-X Optical Interface Card(SyncE,PTP,SFP)
                bnameCX31E4GES(536914),                      -- CX380,CX31E4GES,4-Port 1000BASE-T Interface Card(SyncE,RJ45)
                bnameCX31E4GEP(536915),                      -- CX380,CX31E4GEP,4-Port 1000BASE-T Interface Card(SyncE,PTP,RJ45)
                bnameCX31EGGFTA(536916),                     -- CX380,CX31EGGFTA,16-Port 1000BASE-X Interface Card(Timing transmit,SFP)
                bnameCX31E8PA(536917),                       -- CX380,CX31E8PA,CX31EGGFTA Ethernet Pinch Board
                bnameCX31EGGFS(536918),                      -- CX380,CX31EGGFS,16-Port 1000BASE-X Interface Card(SyncE,SFP
                bnameCX31EGGES(536919),                      -- CX380,CX31EGGES,16-Port 1000BASE-T Interface Card(SyncE,RJ45)
                bnameCX31LPUB(536920),                       -- CX380,CX31LPUB,Line Processing Unit
                bnameCX31E1XFS(536921),                      -- CX380,CX31E1XFS,1-Port 10GE Optical Interface Card(SyncE,XFP)

                bnameCX22EOFEC(536922),          -- CX200DMC, 24FE(RJ45)+2GE(SFP)+2Monitor Mixed Interface Card
                bnameCX22EOFEA(536923),          -- CX200DEA, 24FE(RJ45)+2GE(SFP)+2Combo Mixed Interface Card
                bnameCX22EOFEAMC(536924),        -- CX200DEAMC, 24FE(RJ45)+2GE(SFP)+2Combo+2Monitor Mixed Interface Card

                bnameCX22EFFF(536925),           -- CX22EFFF,24FE(RJ45)+2GE(SFP)+2Combo Mixed Interface Card
                bnameCX22EMFEA(536926),                  -- CX22EMFEA,48FE(RJ45)+4GE(SFP) Interface Card
                bnameCX22EMFEB(536927),                  -- CX22EMFEB,24FE(RJ45)+24FE(SFP)+4GE(SFP) Interface Card
                bnameCX22EMFF(536928),                   -- CX22EMFF,48FE(SFP)+4GE(SFP) Interface Card
                bnameCX61LPUK1(536929),               -- CX600 CR52LPUK1,Flexible Card Line Processing Unit(LPUF-20,2 sub-slots,Not hot pluggable for sub cards) B
                bnameCX61LPUK2(536930),               -- CX600 CR52LPUK2,Flexible Card Line Processing Unit(LPUF-21) A
                bnameCX61LPUK3(536931),               -- CX600 CR52LPUK3,Flexible Card Line Processing Unit(LPUF-21) B
                bnameCX61SFUG(536932),                -- CX600,CX61SFUG0,Switch Fabric Unit G

                bnameCX22E8FF(536933),                 -- CX22E8FF,8FE(RJ45)+1Combo Mixed Interface Card
                bnameCX22EDFE(536934),                  -- CX22EDFF,16FE(RJ45)+2Combo Mixed Interface Card
                bnameCX22EFFE(536935),                  -- CX22EFFF,24FE(RJ45)+2Combo Mixed Interface Card
                bnameCX61MPUD(536936),                -- CX600-3 Main Processing Unit

                bnameCX22EFGE(536937),                  -- CX22EFGE,24GE(RJ45)+ E2XX(XGE) + E4GF(SFP) Interface Card
                bnameCX22EFGF(536938),                  -- CX22EFGF,24GE(SFP)+ E2XX(XGE)+ E4GF(SFP)  Interface Card
                bnameCX22EMGE(536939),                  -- CX22EMGE,48GE(RJ45)+ E2XX(XGE)+ E4GF(SFP)  Interface Card

                bnameCX22EFGEA(536940),                  -- CX22EMGE,48GE(RJ45)+ E2XX(XGE)+ E4GF(SFP)  Interface Card
                bnameCX22EMGEA(536941),                  -- CX22EFGEA,20GE+4COMBO General Switch Control Card
                bnameCX22EFGEF(536942),                  -- CX22EFGEF,20GE+4COMBO,24 PORT PSE General Switch Control Card
                bnameCX22EMGEB(536943),                  -- CX22EMGEB,44GE+4COMBO,48 PORT PSE General Switch Control Card
                bnameCX22EFGEC(536944),                  -- CX22EFGEC,20GE+4COMBO+2XGE General Switch Control Card
                bnameCX22EMGEC(536945),                  -- CX22EMGEC,48GE+2XGE General Switch Control Card
                bnameCX22EFGED(536946),                  -- CX22EFGED,20GE+4COMBO+2XGE,24 PORT PSE General Switch Control Card
                bnameCX22EMGED(536947),                  -- CX22EMGED,48GE+2XGE,48 PORT PSE General Switch Control Card
                bnameCX22EFGEE(536948),                  -- CX22EFGEE,24GE+2*10GE General Switch Control Card(PSE)
                bnameCX22EMGEE(536949),                  -- CX22EMGEE,48GE+2*10GE General Switch Control Card(PSE)
                bnameCX22E8FEC(536950),                  -- CX22E8FEC,8FE+1GE General Switch Control Card(PSE)
                bnameCX22EFFEA(536951),                  -- CX22EFFEA,24FE+2GE General Switch Control Card(PSE)
                bnameCX22EFFEC(536952),                  -- CX22EFFEC,24FE+4GE General Switch Control Card(PSE)
                bnameCX22EMFEC(536953),                  -- CX22EMFEC,48FE+4GE General Switch Control Card(PSE)

                bnameCX22LS31T28SA(536954),               -- CX22LS31T28SA,24GE+2GE COMBO+2GE(SFP) General Switch Control Card
                bnameCX22LS31T18SA(536955),               -- CX22LS31T18SA,16GE+2GE(SFP)General Switch Control Card
                bnameCX22LS51T24C(536956),               -- CX22LS51T24C,24GE + 4GE(SFP) Interface Card
                bnameCX22LS51S24C(536957),               -- CX22LS51S24C,24GE(SFP) + 4GE(SFP)Interface Card
                bnameCX22LS51T6UM(536958),               -- CX22LS51T6UM,4GE+2GE COMBO General Switch Control Card(PSE)
                bnameCX22LS31T24C(536959),               -- CX22LS31T24C,24FE+2GE(SFP) Interface Card
                bnameCX22LS51S24CA(536960),               -- CX22LS51S24CA,24GE + 4GE(SFP) General Switch Control Card(PSE)

                bnameCX62NPUI20(536961),                  -- CX600-16 Main Processing Unit
                bnameCX62NPU20B0(536962),                  -- CX600-16 Main Processing Unit
                bnameCX62MPUB4(536963),                  -- CX600-8 - Main Process Switch Fabric Unit
                bnameCX62SFU40B0(536964),                  -- CX600-16 Main Processing Unit
                bnameCX62SRU40A4(536965),                  -- CX600-8 - Main Process Switch Fabric Unit
                bnameCX62SFU40C0(536966),                  -- CX600-16 Main Processing Unit
                bnameCX62MPUD0(536967),                  -- CX600-16 Main Processing Unit
                bnameCX62ISUF10(536968),                  -- CX600-8 - Main Process Switch Fabric Unit
                bnameCX62ISUF20(536969),                  -- CX600-16 Main Processing Unit
                bnameCX62ISUF40(536970),                  -- CX600-8 - Main Process Switch Fabric Unit
                bnameCX62MPUG0(536971),                  -- CX600-8 - Main Process Switch Fabric Unit
                bnameLS61S24N(536972),                   -- CX22LS61S24N,24*10G(SFP+) General Switch Control Card(PSE)
                bnameLS61S48N(536973),                   -- CX22LS61S48N,48*10G(SFP+) General Switch Control Card(PSE)
                bnameLS61S48NA(536974),                  -- CX22LS61S48N,48*10G(SFP+) General Switch Control Card(PSE)
                bnameLS52T28S(536975),               -- S5700 LS52T28S 24-Port GE RJ45+4-Port GE SFP General Switch Control Card 1*1  S5728P-LI
                bnameLS52V28S(536976),            -- S5700 LS52V28S 24-Port GE RJ45+4-Port GE SFP General Switch Control Card PSE 1*1 S5728P-PWR-LI
                bnameLS52T52S(536977),              -- S5700 LS52T28S 48-Port GE RJ45+4-Port GE SFP General Switch Control Card 1*1 S5752P-LI
                bnameLS52V52S(536978),           -- S5700 LS52V28S 48-Port GE RJ45+4-Port GE SFP General Switch Control Card (PSE)1*1  S5752P-PWR-LI
                bnameLS52T28C(536979),              -- S5700 LS52T28C 24-Port GE RJ45+4-Port 10GE SFP+ General Switch Control Card 1*1  S5728X-EI
                bnameLS52T52C(536980),              -- S5700 LS52T52C 48-Port GE RJ45+4-Port 10GE SFP+ General Switch Control Card 1*1 S5752X-EI
                bnameLS52T28SS5328PLI(536981),              -- S5300 LS52T28S 24-Port GE RJ45+4-Port GE SFP General Switch Control Card 1*1  S5328P-LI
                bnameLS52T52SS5352PLI(536982),              -- S5300 LS52T28S 48-Port GE RJ45+4-Port GE SFP General Switch Control Card 1*1 S5352P-LI
                bnameLS52T28SB(536983),               -- S5700 LS52T28S 24-Port GE RJ45+4-Port GE SFP General Switch Control Card 1*1  S5728P-LI-DC
                bnameLS52T52SB(536984),              -- S5700 LS52T28S 48-Port GE RJ45+4-Port GE SFP General Switch Control Card 1*1 S5752P-LI-DC
                bnameLS52T28SC(536985),              -- S5300 LS52T28S 24-Port GE RJ45+4-Port GE SFP General Switch Control Card 1*1  S5328P-LI-DC
                bnameLS52T52SC(536986),              -- S5300 LS52T28S 48-Port GE RJ45+4-Port GE SFP General Switch Control Card 1*1 S5352P-LI-DC
                bnameLS52T28SD(536987),              -- S5700 LS52T28S 24-Port GE RJ45+4-Port GE SFP General Switch Control Card 1*1  S5700S-28P-LI-AC
                bnameLS52T52SD(536988),              -- S5700 LS52T52S 48-Port GE RJ45+4-Port GE SFP General Switch Control Card 1*1 S5700S-52P-LI-AC
                bnameLS52V28C(536989),              -- S5700 LS52V28C 24-Port GE RJ45+4-Port 10GE SFP+ General Switch Control Card 1*1  S5710-28C-PWR-EI
                bnameLS52V52C(536990),              -- S5700 LS52V52C 48-Port GE RJ45+4-Port 10GE SFP+ General Switch Control Card 1*1  S5710-52C-PWR-EI
                bnameCX61MPUH(536991),                -- CX600-X3 Main Processing Unit
                bnameCX62SFU100D(536992),             -- CX600-X8 Switch Fabric Unit
                bnameCX62SRU100D(536993),             -- CX600-X8 Main Process Switch Fabric Unit

                bnameCX68MPUK(536994),                -- CX600-X2 Main Processing Unit,
                bnameCX68NPU50(536995),               -- CX600-X2 Net  Processing Unit,
                bnameCX68NPU50B(536996),              -- CX600-X2 Net  Processing Unit outside,
                bnameCX68PSUC(536997),                -- CX600-X2 DC/DC Power Module,
                bnameCX68FAN(536998),                 -- CX600-X2 FAN Module,
                bnameCX68E8GEB(536999),               -- 100M/1000M interface card (RJ45),
                bnameCX68L2XFB(537000),               -- 2x10G  card,
                bnameCX68TIE1(537001),                -- 32E1 interface card,
                bnameCX68C4CF(537002),                -- 4*155M CPOS interface card
                bnameES5D2T10M000(537003),            -- S5700 ES5D2T10M000 8 GE RJ45,2 GE SFP,AC 110/220V S5700-10P-LI-AC
                bnameES5D2V10M000(537004),            -- S5700 ES5D2V10M000 8 GE RJ45,2 GE SFP,AC 110/220V S5700-10P-PWR-LI-AC
                bnameES5D2H26S000(537005),            -- S5700 ES5D2H26S000 12-Prot GE RJ45 + 12-Port GE Optical + 2-Port SFP+ Optical General Switch Control Unit S5700-26X-SI-12S-AC
                bnameES5D2T28S000(537006),            -- S5700 ES5D2T28S000 24 GE RJ45,4 10GE SFP+,AC 110/220V S5700-28X-LI-AC
                bnameES5D2T28S000S5728XLIDC(537007),  -- S5700 ES5D2T28S000 24 GE RJ45,4 10GE SFP+,DC -48V S5700-28X-LI-DC
                bnameES5D2T52S000(537008),            -- S5700 ES5D2T52S000 48 GE RJ45,4 10GE SFP+,AC 110/220V S5700-52X-LI-AC
                bnameES5D2T52S000S5752XLIDC(537009),  -- S5700 ES5D2T52S000 48 GE RJ45,4 10GE SFP+,DC -48V S5700-52X-LI-DC
                bnameES5D2V28S000(537010),            -- S5700 ES5D2V28S000 24 GE RJ45,4 10GE SFP+,PoE,AC 110/220V S5700-28X-PWR-LI-AC
                bnameES5D2V52S000(537011),            -- S5700 ES5D2V52S000 48 GE RJ45,4 10GE SFP+,PoE,AC 110/220V S5700-52X-PWR-LI-AC
                bnameS5710108CPWRHIAC(537012),        -- S5710 ES5D2T10M000 48 GE RJ45,8 10GE SFP+,PoE,Four Slots of Flexible Card,Dual Slots of Power,Including Dual 580W AC PowerS5710-108C-PWR-HI-AC
                bnameS5710108CHIAC(537013),           -- S5710 ES5D2T56S000 48-Port GE RJ45 + 8-Port 10GE SFP+ Optical General Switch Control Unit S5710-108C-HI-AC
                bnameS6300E6000(537014),              -- S5700 S6300_E6000  20-Port 10GE SFP+ Optical General Switch Control Unit E6000
                bnameS5310PLIAC(537015),           -- S5300-10P-LI-AC
                bnameS531028CEI(537016),           -- S5310-28C-EI 20-port GE RJ45+4-port Combo + 4-Port SFP+ Optical General Switch Control Unit
                bnameS531052CEI(537017),           -- S5310-52C-EI 48-Port GE RJ45 + 4-Port SFP+ Optical General Switch Control Unit
                bnameS2328PEIAC(537018),           -- 24-port FE RJ45 + 4-port SFP General Switch Control Unit
                bnameS275026TPPWREIAC(537019),     -- S2750-26TP-PWR-EI-AC Mainframe(24 FE RJ45,2 GE COMBO,PoE,AC 110/220V)
                bnameS235026TPPWREIAC(537020),     -- S2350-26TP-PWR-EI-AC Mainframe(24 FE RJ45,2 GE COMBO,PoE,AC 110/220V)
                bnameS275126TPPWREIAC(537021),     -- S2751-26TP-PWR-EI-AC Mainframe(24FE RJ45,2 GE COMBO,8 PoE,AC 110/220V)
                bnameS235028TPEIAC(537022),        -- S2350-28TP-EI-AC Mainframe(24 FE RJ45,2 GE Combo,2 GE SFP,AC 110/220V)
                bnameS275028TPEIAC(537023),        -- S2750-28TP-EI-AC Mainframe(24 FE RJ45,2 GE Combo,2 GE SFP,AC 110/220V)
                bnameS235018TPPWREIAC(537024),     -- S2350-18TP-PWR-EI-AC Mainframe(16 FE RJ45,2 GE COMBO,PoE,AC 110/220V)
                bnameS275018TPPWREIAC(537025),     -- S2750-18TP-PWR-EI-AC Mainframe(16 FE RJ45,2 GE COMBO,PoE,AC 110/220V)
                bnameS330052PEI(537026),           -- S3300-52P-EI Mainframe( 48FE + 4 GE SFP)
                bname8031S5700-28X-LI-24S-DC(537027),    --S5700-28X-LI-24S-DC Mainframe(20 GE SFP,4 GE Combo,4 10GE SFP+,DC -48V)
                bname8031S5300-28X-LI-24S-DC(537028),    --S5300-28X-LI-24S-DC Mainframe(20 GE SFP,4 GE Combo,4 10GE SFP+,DC -48V)
                bname8031S5700-28X-LI-24S-AC(537029),    --S5700-28X-LI-24S-AC Mainframe(20 GE SFP,4 GE Combo,4 10GE SFP+,AC 110/220V)
                bname8031S5300-28X-LI-24S-AC(537030),   --S5300-28X-LI-24S-AC Mainframe(20 GE SFP,4 GE Combo,4 10GE SFP+,AC 110/220V)
                bname8031S5300-28X-LI-DC(537031),      --5300-28X-LI-DC Mainframe(24 GE RJ45,4 10GE SFP+,DC -48V)
                bname8031S5300-28X-LI-AC(537032),      --S5300-28X-LI-AC Mainframe(24 GE RJ45,4 10GE SFP+,AC 110/220V)
                bname8031S2750-28TP-PWR-EI-AC(537033),  --S2750-28TP-PWR-EI-AC Mainframe(24 FE RJ45,2 GE SFP,2 GE COMBO,PoE,AC 110/220V)
                bname8031S2350-28TP-PWR-EI-AC(537034),  --S2350-28TP-PWR-EI-AC  Mainframe(24 FE RJ45,2 GE SFP,2 GE COMBO,PoE,AC 110/220V)
                bname8031S2751-28TP-PWR-EI-AC(537035),  --S2751-28TP-PWR-EI-AC  Mainframe(24FE RJ45,2 GE SFP,2 GE COMBO,12 PoE,AC 110/220V)
                bname8031S2350-20TP-PWR-EI-AC(537036),   --S2350-20TP-PWR-EI-AC Mainframe(16 FE RJ45,2 GE SFP,2 GE COMBO,PoE,AC 110/220V)
                bname8031S2750-20TP-PWR-EI-AC(537037),   --S2750-20TP-PWR-EI-AC Mainframe(16 FE RJ45,2 GE SFP,2 GE COMBO,PoE,AC 110/220V)
                bname8031S2350-28TP-EI-AC(537038),     --S2350-28TP-EI-AC Mainframe(24 FE RJ45,2 GE SFP,2 GE COMBO,AC 110/220V)
                bname8031S2750-28TP-EI-AC(537039),   --S2750-28TP-EI-AC  Mainframe(24 FE RJ45,2 GE SFP,2 GE COMBO,AC 110/220V)
                bname8031S3700-28TP-EI-24S-DC(537040), -- S3700-28TP-EI-24S-DC

                bname8031S5701-28X-LI-AC(537041),           --S5701-28X-LI-AC       Metro Service Platform for V2R3C00
                bname8031S5701-28X-LI-24S-AC(537042),       --S5701-28X-LI-24S-AC   Metro Service Platform for V2R3C00
                bname8031S5700-28P-LI-BAT(537043),          --S5700-28P-LI-BAT      Metro Service Platform for V2R3C02
                bname8031S5700-28P-LI-4AH(537044),          --S5700-28P-LI-4AH      Metro Service Platform for V2R3C02
                bname8031S5700-28P-LI-24S-BAT(537045),      --S5700-28P-LI-24S-BAT  Metro Service Platform for V2R3C02
                bname8031S5700-28P-LI-24S-4AH(537046),      --S5700-28P-LI-24S-4AH  Metro Service Platform for V2R3C02
                bname8031S5300-28P-LI-BAT(537047),          --S5300-28P-LI-BAT      Metro Service Platform for V2R3C02
                bname8031S5300-28P-LI-4AH(537048),          --S5300-28P-LI-4AH      Metro Service Platform for V2R3C02
                bname8031S5300-28P-LI-24S-BAT(537049),      --S5300-28P-LI-24S-BAT  Metro Service Platform for V2R3C02
                bname8031S5300-28P-LI-24S-4AH(537050),      --S5300-28P-LI-24S-4AH  Metro Service Platform for V2R3C02
                bname8031S5700-28X-LI-24CS-AC(537051),      --S5700-28X-LI-24CS-AC  Metro Service Platform for V2R3C02
                bname8031S5700-28X-LI-24CS-DC(537052),      --S5700-28X-LI-24CS-DC  Metro Service Platform for V2R3C02
                bname8031S5300-28X-LI-24CS-AC(537053),      --S5300-28X-LI-24CS-AC  Metro Service Platform for V2R3C02
                bname8031S5300-28X-LI-24CS-DC(537054),      --S5300-28X-LI-24CS-DC  Metro Service Platform for V2R3C02

                bname8031S5310-108C-PWR-HI(537055),         --S5310-108C-PWR-HI     Metro Service Platform for V2R5C00
                bname8031S5300-10P-PWR-LI-AC(537056),       --S5300-10P-PWR-LI-AC   Metro Service Platform for V2R5C00
                bname8031S5300-28P-PWR-LI-AC(537057),       --S5300-28P-PWR-LI-AC   Metro Service Platform for V2R5C00
                bname8031S5300-52P-PWR-LI-AC(537058),       --S5300-52P-PWR-LI-AC   Metro Service Platform for V2R5C00
                bname8031S5300-52X-LI-AC(537059),           --S5300-52X-LI-AC       Metro Service Platform for V2R5C00
                bname8031S5300-52X-LI-DC(537060),           --S5300-52X-LI-DC       Metro Service Platform for V2R5C00
                bname8031S5300-28X-PWR-LI-AC(537061),       --S5300-28X-PWR-LI-AC   Metro Service Platform for V2R5C00
                bname8031S5300-52X-PWR-LI-AC(537062),       --S5300-52X-PWR-LI-AC   Metro Service Platform for V2R5C00
                bname8031S2350-28TP-EI-DC(537063),          --S2350-28TP-EI-DC      Metro Service Platform for V2R5C00
                bname8031S5700-28TP-LI-AC(537064),          --S5700-28TP-LI-AC      Metro Service Platform for V2R3C10
                bname8031S5700-28TP-PWR-LI-AC(537065),      --S5700-28TP-PWR-LI-AC  Metro Service Platform for V2R3C10
                bname8031S5701-28TP-PWR-LI-AC(537066),      --S5701-28TP-PWR-LI-AC  Metro Service Platform for V2R3C10

                bname8031S5720-56C-HI-AC(537067),           --S5720-56C-HI-AC       Metro Service Platform for V2R6C00
                bname8031S5720-56C-PWR-HI-AC(537068),       --S5720-56C-PWR-HI-AC   Metro Service Platform for V2R6C00
                bname8031S5720-32C-HI-24S-AC(537069),       --S5720-32C-HI-24S-AC   Metro Service Platform for V2R6C00

                bname8031S1720-28GFR-4TP(537070),           --S1720-28GFR-4TP       Metro Service Platform for V2R6C10
                bname8031S1720-20GFR-4TP(537071),           --S1720-20GFR-4TP       Metro Service Platform for V2R6C10
                bname8031S2720-28TP-EI-AC(537072),          --S2720-28TP-EI-AC      Metro Service Platform for V2R6C10

                bname8031S5720-36C-EI-28S-AC(537073),       --S5720-36C-EI-28S-AC   Metro Service Platform for V2R7C00
                bname8031S5320-36C-EI-28S-AC(537074),       --S5320-36C-EI-28S-AC   Metro Service Platform for V2R7C00
                bname8031S5320-36C-EI-28S-DC(537075),       --S5320-36C-EI-28S-DC   Metro Service Platform for V2R7C00
                bname8031S5720-56C-EI-48S-AC(537076),       --S5720-56C-EI-48S-AC   Metro Service Platform for V2R7C00
                bname8031S5320-56C-EI-48S-AC(537077),       --S5320-56C-EI-48S-AC   Metro Service Platform for V2R7C00
                bname8031S5320-56C-EI-48S-DC(537078),       --S5320-56C-EI-48S-DC   Metro Service Platform for V2R7C00
                bname8031S5720-36C-EI-AC(537079),           --S5720-36C-EI-AC       Metro Service Platform for V2R7C00
                bname8031S5320-36C-EI-AC(537080),           --S5320-36C-EI-AC       Metro Service Platform for V2R7C00
                bname8031S5320-36C-EI-DC(537081),           --S5320-36C-EI-DC       Metro Service Platform for V2R7C00
                bname8031S5720-36PC-EI-AC(537082),          --S5720-36PC-EI-AC      Metro Service Platform for V2R7C00
                bname8031S5320-36PC-EI-AC(537083),          --S5320-36PC-EI-AC      Metro Service Platform for V2R7C00
                bname8031S5320-36PC-EI-DC(537084),          --S5320-36PC-EI-DC      Metro Service Platform for V2R7C00
                bname8031S5720-56C-EI-AC(537085),           --S5720-56C-EI-AC       Metro Service Platform for V2R7C00
                bname8031S5320-56C-EI-AC(537086),           --S5320-56C-EI-AC       Metro Service Platform for V2R7C00
                bname8031S5320-56C-EI-DC(537087),           --S5320-56C-EI-DC       Metro Service Platform for V2R7C00
                bname8031S5720-56PC-EI-AC(537088),          --S5720-56PC-EI-AC      Metro Service Platform for V2R7C00
                bname8031S5320-56PC-EI-AC(537089),          --S5320-56PC-EI-AC      Metro Service Platform for V2R7C00
                bname8031S5320-56PC-EI-DC(537090),          --S5320-56PC-EI-DC      Metro Service Platform for V2R7C00
                bname8031S5720-36C-PWR-EI-AC(537091),       --S5720-36C-PWR-EI-AC   Metro Service Platform for V2R7C00
                bname8031S5320-36C-PWR-EI-AC(537092),       --S5320-36C-PWR-EI-AC   Metro Service Platform for V2R7C00
                bname8031S5320-36C-PWR-EI-DC(537093),       --S5320-36C-PWR-EI-DC   Metro Service Platform for V2R7C00
                bname8031S5720-56C-PWR-EI-AC(537094),       --S5720-56C-PWR-EI-AC   Metro Service Platform for V2R7C00
                bname8031S5320-56C-PWR-EI-AC(537095),       --S5320-56C-PWR-EI-AC   Metro Service Platform for V2R7C00
                bname8031S5720-56C-PWR-EI-AC1(537096),      --S5720-56C-PWR-EI-AC1  Metro Service Platform for V2R7C00
                bname8031S5720-32X-EI-24S-AC(537097),       --S5720-32X-EI-24S-AC   Metro Service Platform for V2R7C00
                bname8031S5320-32X-EI-24S-AC(537098),       --S5320-32X-EI-24S-AC   Metro Service Platform for V2R7C00
                bname8031S5320-32X-EI-24S-DC(537099),       --S5320-32X-EI-24S-DC   Metro Service Platform for V2R7C00
                bname8031S5720-50X-EI-46S-AC(537100),       --S5720-50X-EI-46S-AC   Metro Service Platform for V2R7C00
                bname8031S5320-50X-EI-46S-AC(537101),       --S5320-50X-EI-46S-AC   Metro Service Platform for V2R7C00
                bname8031S5320-50X-EI-46S-DC(537102),       --S5320-50X-EI-46S-DC   Metro Service Platform for V2R7C00
                bname8031S5720-32X-EI-AC(537103),           --S5720-32X-EI-AC       Metro Service Platform for V2R7C00
                bname8031S5320-32X-EI-AC(537104),           --S5320-32X-EI-AC       Metro Service Platform for V2R7C00
                bname8031S5320-32X-EI-DC(537105),           --S5320-32X-EI-DC       Metro Service Platform for V2R7C00
                bname8031S5720-32P-EI-AC(537106),           --S5720-32P-EI-AC       Metro Service Platform for V2R7C00
                bname8031S5320-32P-EI-AC(537107),           --S5320-32P-EI-AC       Metro Service Platform for V2R7C00
                bname8031S5320-32P-EI-DC(537108),           --S5320-32P-EI-DC       Metro Service Platform for V2R7C00
                bname8031S5720-52X-EI-AC(537109),           --S5720-52X-EI-AC       Metro Service Platform for V2R7C00
                bname8031S5320-52X-EI-AC(537110),           --S5320-52X-EI-AC       Metro Service Platform for V2R7C00
                bname8031S5320-52X-EI-DC(537111),           --S5320-52X-EI-DC       Metro Service Platform for V2R7C00
                bname8031S5720-52P-EI-AC(537112),           --S5720-52P-EI-AC       Metro Service Platform for V2R7C00
                bname8031S5320-52P-EI-AC(537113),           --S5320-52P-EI-AC       Metro Service Platform for V2R7C00
                bname8031S5320-52P-EI-DC(537114),           --S5320-52P-EI-DC       Metro Service Platform for V2R7C00
                bname8031S5720-50X-EI-AC(537115),           --S5720-50X-EI-AC       Metro Service Platform for V2R7C00
                bname8031S5320-50X-EI-AC(537116),           --S5320-50X-EI-AC       Metro Service Platform for V2R7C00
                bname8031S5320-50X-EI-DC(537117),           --S5320-50X-EI-DC       Metro Service Platform for V2R7C00

                bname8031S5720S-28P-SI-AC(537118),          --S5720S-28P-SI-AC           Metro Service Platform for V2R8C00
                bname8031S5321-28P-SI-AC(537119),           --S5321-28P-SI-AC            Metro Service Platform for V2R8C00
                bname8031S5720S-28X-SI-AC(537120),          --S5720S-28X-SI-AC           Metro Service Platform for V2R8C00
                bname8031S5321-28X-SI-AC(537121),           --S5321-28X-SI-AC            Metro Service Platform for V2R8C00
                bname8031S5321-28X-SI-DC(537122),           --S5321-28X-SI-DC            Metro Service Platform for V2R8C00
                bname8031S5720S-52P-SI-AC(537123),          --S5720S-52P-SI-AC           Metro Service Platform for V2R8C00
                bname8031S5321-52P-SI-AC(537124),           --S5321-52P-SI-AC            Metro Service Platform for V2R8C00
                bname8031S5720S-52X-SI-AC(537125),          --S5720S-52X-SI-AC           Metro Service Platform for V2R8C00
                bname8031S5321-52X-SI-AC(537126),           --S5321-52X-SI-AC            Metro Service Platform for V2R8C00
                bname8031S5321-52X-SI-DC(537127),           --S5321-52X-SI-DC            Metro Service Platform for V2R8C00
                bname8031S5720-28P-SI-AC(537128),           --S5720-28P-SI-AC            Metro Service Platform for V2R8C00
                bname8031S5320-28P-SI-AC(537129),           --S5320-28P-SI-AC            Metro Service Platform for V2R8C00
                bname8031S5720-28X-SI-AC(537130),           --S5720-28X-SI-AC            Metro Service Platform for V2R8C00
                bname8031S5320-28X-SI-AC(537131),           --S5320-28X-SI-AC            Metro Service Platform for V2R8C00
                bname8031S5720-52P-SI-AC(537132),           --S5720-52P-SI-AC            Metro Service Platform for V2R8C00
                bname8031S5320-52P-SI-AC(537133),           --S5320-52P-SI-AC            Metro Service Platform for V2R8C00
                bname8031S5720-52X-SI-AC(537134),           --S5720-52X-SI-AC            Metro Service Platform for V2R8C00
                bname8031S5320-52X-SI-AC(537135),           --S5320-52X-SI-AC            Metro Service Platform for V2R8C00
                bname8031S5720-28X-PWR-SI-AC(537136),       --S5720-28X-PWR-SI-AC        Metro Service Platform for V2R8C00
                bname8031S5320-28X-PWR-SI-AC(537137),       --S5320-28X-PWR-SI-AC        Metro Service Platform for V2R8C00
                bname8031S5720-52X-PWR-SI-AC(537138),       --S5720-52X-PWR-SI-AC        Metro Service Platform for V2R8C00
                bname8031S5720-52X-PWR-SI-ACF(537139),      --S5720-52X-PWR-SI-ACF       Metro Service Platform for V2R8C00
                bname8031S5320-52X-PWR-SI-AC(537140),       --S5320-52X-PWR-SI-AC        Metro Service Platform for V2R8C00
                bname8031S5710-28X-LI-AC(537141),           --S5710-28X-LI-AC            Metro Service Platform for V2R8C00
                bname8031S5710-52X-LI-AC(537142),           --S5710-52X-LI-AC            Metro Service Platform for V2R8C00
                bname8031S6720-30C-EI-24S-AC(537143),       --S6720-30C-EI-24S-AC        Metro Service Platform for V2R8C00
                bname8031S6320-30C-EI-24S-AC(537144),       --S6320-30C-EI-24S-AC        Metro Service Platform for V2R8C00
                bname8031S6320-30C-EI-24S-DC(537145),       --S6320-30C-EI-24S-DC        Metro Service Platform for V2R8C00
                bname8031S6720-54C-EI-48S-AC(537146),       --S6720-54C-EI-48S-AC        Metro Service Platform for V2R8C00
                bname8031S6320-54C-EI-48S-AC(537147),       --S6320-54C-EI-48S-AC        Metro Service Platform for V2R8C00
                bname8031S6320-54C-EI-48S-DC(537148),       --S6320-54C-EI-48S-DC        Metro Service Platform for V2R8C00
                bname8031S5700S-28X-LI-AC(537149),          --S5700S-28X-LI-AC           Metro Service Platform for V2R8C00
                bname8031S5700S-52X-LI-AC(537150),          --S5700S-52X-LI-AC           Metro Service Platform for V2R8C00
                bname8031S5700S-28P-PWR-LI-AC(537151),      --S5700S-28P-PWR-LI-AC       Metro Service Platform for V2R8C00
                bname8031E628(537152),                      --E628                       Metro Service Platform for V2R8C00
                bname8031E628-X(537153),                    --E628-X                     Metro Service Platform for V2R8C00
                bname8031E652(537154),                      --E652                       Metro Service Platform for V2R8C00
                bname8031E652-X(537155),                    --E652-X                     Metro Service Platform for V2R8C00

                bname8031S5720-14X-PWH-SI-AC(537156),       --S5720-14X-PWH-SI-AC        Metro Service Platform for V2R9C00
                bname8031S6720S-26Q-EI-24S-AC(537157),      --S6720S-26Q-EI-24S-AC       Metro Service Platform for V2R9C00
                bname8031S6720S-26Q-EI-24S-DC(537158),      --S6720S-26Q-EI-24S-DC       Metro Service Platform for V2R9C00
                bname8031S6320-26Q-EI-24S-AC(537159),       --S6320-26Q-EI-24S-AC        Metro Service Platform for V2R9C00
                bname8031S6320-26Q-EI-24S-DC(537160),       --S6320-26Q-EI-24S-DC        Metro Service Platform for V2R9C00
                bname8031S5300-28TP-PWR-LI-AC(537161),      --S5300-28TP-PWR-LI-AC       Metro Service Platform for V2R9C00
                bname8031S5300-10P-PWR-LI-AC-NEW(537162),   --S5300-10P-PWR-LI-AC        Metro Service Platform for V2R9C00
                bname8031S5320-28X-SI-DC(537163),           --S5320-28X-SI-DC            Metro Service Platform for V2R9C00
                bname8031S5320-52X-SI-DC(537164),           --S5320-52X-SI-DC            Metro Service Platform for V2R9C00
                bname8031S5720-28X-PWR-SI-DC(537165),       --S5720-28X-PWR-SI-DC        Metro Service Platform for V2R9C00
                bname8031S5720-52X-PWR-SI-DC(537166),       --S5720-52X-PWR-SI-DC        Metro Service Platform for V2R9C00
                bname8031S5320-52X-PWR-SI-ACF(537167),      --S5320-52X-PWR-SI-ACF       Metro Service Platform for V2R9C00
                bname8031S5720-28X-SI-DC(537168),           --S5720-28X-SI-DC            Metro Service Platform for V2R9C00
                bname8031S5720-52X-SI-DC(537169),           --S5720-52X-SI-DC            Metro Service Platform for V2R9C00
                bname8031S5720S-28X-SI-DC(537170),          --S5720S-28X-SI-DC           Metro Service Platform for V2R9C00
                bname8031S5720S-52X-SI-DC(537171),          --S5720S-52X-SI-DC           Metro Service Platform for V2R9C00
                bname8031S5720-32X-EI-DC(537172),           --S5720-32X-EI-DC            Metro Service Platform for V2R9C00
                bname8031S5720-50X-EI-DC(537173),           --S5720-50X-EI-DC            Metro Service Platform for V2R9C00
                bname8031S5720-32X-EI-24S-DC(537174),       --S5720-32X-EI-24S-DC        Metro Service Platform for V2R9C00
                bname8031S5720-50X-EI-46S-DC(537175),       --S5720-50X-EI-46S-DC        Metro Service Platform for V2R9C00
                bname8031S5720-36C-EI-DC(537176),           --S5720-36C-EI-DC            Metro Service Platform for V2R9C00
                bname8031S5720-56C-EI-DC(537177),           --S5720-56C-EI-DC            Metro Service Platform for V2R9C00
                bname8031S5720-36C-PWR-EI-DC(537178),       --S5720-36C-PWR-EI-DC        Metro Service Platform for V2R9C00
                bname8031S5720-56C-PWR-EI-DC(537179),       --S5720-56C-PWR-EI-DC        Metro Service Platform for V2R9C00
                bname8031S5720-36C-EI-28S-DC(537180),       --S5720-36C-EI-28S-DC        Metro Service Platform for V2R9C00
                bname8031S5720-56C-EI-48S-DC(537181),       --S5720-56C-EI-48S-DC        Metro Service Platform for V2R9C00
                bname8031S5320-56C-HI-AC(537182),           --S5320-56C-HI-AC            Metro Service Platform for V2R9C00
                bname8031S5320-56C-HI-DC(537183),           --S5320-56C-HI-DC            Metro Service Platform for V2R9C00
                bname8031S5320-32C-HI-24S-DC(537184),       --S5320-32C-HI-24S-DC        Metro Service Platform for V2R9C00
                bname8031S5320-32C-HI-24S-AC(537185),       --S5320-32C-HI-24S-AC        Metro Service Platform for V2R9C00
                bname8031S6720-30C-EI-24S-DC(537186),       --S6720-30C-EI-24S-DC        Metro Service Platform for V2R9C00
                bname8031S6720-54C-EI-48S-DC(537187),       --S6720-54C-EI-48S-DC        Metro Service Platform for V2R9C00
                bname8031S5720-56C-PWR-HI-AC1(537188),      --S5720-56C-PWR-HI-AC1       Metro Service Platform for V2R9C00
                bname8031S6720S-26Q-EI-24S(537189),         --S6720S-26Q-EI-24S          Metro Service Platform for V2R9C00
                bname8031S6320-26Q-EI-24S(537190),          --S6320-26Q-EI-24S           Metro Service Platform for V2R9C00
                bname8031S5320-28X-SI(537191),              --S5320-28X-SI               Metro Service Platform for V2R9C00
                bname8031S5320-52X-SI(537192),              --S5320-52X-SI               Metro Service Platform for V2R9C00
                bname8031S5320-36C-EI(537193),              --S5320-36C-EI               Metro Service Platform for V2R9C00
                bname8031S5320-56C-EI(537194),              --S5320-56C-EI               Metro Service Platform for V2R9C00
                bname8031S5320-36C-EI-28S(537195),          --S5320-36C-EI-28S           Metro Service Platform for V2R9C00

                bname8031Huawei-S5700-8P-G(537196),            --S5720-10T-PWR-LI         Metro Service Platform for V2R10C00 modify to  bname8031Huawei-S5700-8P-G
                bname8031S5720-12TP-LI-AC(537197),            --S5720-12TP-LI-AC         Metro Service Platform for V2R10C00
                bname8031S5720S-12TP-LI-AC(537198),           --S5720S-12TP-LI-AC        Metro Service Platform for V2R10C00
                bname8031S5320-12TP-LI-AC(537199),            --S5320-12TP-LI-AC         Metro Service Platform for V2R10C00
                bname8031S1720-10GW-2P(537200),               --S1720-10GW-2P           Metro Service Platform for V2R10C00
                bname8031S5720-12TP-PWR-LI-AC(537201),        --S5720-12TP-PWR-LI-AC     Metro Service Platform for V2R10C00
                bname8031S5720S-12TP-PWR-LI-AC(537202),       --S5720S-12TP-PWR-LI-AC    Metro Service Platform for V2R10C00
                bname8031S5320-12TP-PWR-LI-AC(537203),        --S5320-12TP-PWR-LI-AC     Metro Service Platform for V2R10C00
                bname8031S1720-10GW-PWR-2P(537204),           --S1720-10GW-PWR-2P       Metro Service Platform for V2R10C00
                bname8031S5720-28P-LI-AC(537205),             --S5720-28P-LI-AC          Metro Service Platform for V2R10C00
                bname8031S5720S-28P-LI-AC(537206),            --S5720S-28P-LI-AC         Metro Service Platform for V2R10C00
                bname8031S5320-28P-LI-AC(537207),             --S5320-28P-LI-AC          Metro Service Platform for V2R10C00
                bname8031S1720-28GWR-4P(537208),              --S1720-28GWR-4P           Metro Service Platform for V2R10C00
                bname8031S5720-28X-LI-AC(537209),             --S5720-28X-LI-AC          Metro Service Platform for V2R10C00
                bname8031S5720-28X-LI-DC(537210),             --S5720-28X-LI-DC          Metro Service Platform for V2R10C00
                bname8031S5320-28X-LI-AC(537211),             --S5320-28X-LI-AC          Metro Service Platform for V2R10C00
                bname8031S5320-28X-LI-DC(537212),             --S5320-28X-LI-DC          Metro Service Platform for V2R10C00
                bname8031S5720S-28X-LI-AC(537213),            --S5720S-28X-LI-AC         Metro Service Platform for V2R10C00
                bname8031S628X-E(537214),                     --S628X-E                  Metro Service Platform for V2R10C00
                bname8031S1720-28GWR-4X(537215),              --S1720-28GWR-4X           Metro Service Platform for V2R10C00
                bname8031S5720-28P-PWR-LI-AC(537216),         --S5720-28P-PWR-LI-AC      Metro Service Platform for V2R10C00
                bname8031S5720S-28P-PWR-LI-AC(537217),        --S5720S-28P-PWR-LI-AC     Metro Service Platform for V2R10C00
                bname8031S5320-28P-PWR-LI-AC(537218),         --S5320-28P-PWR-LI-AC      Metro Service Platform for V2R10C00
                bname8031S5720-28P-PWR-LI-ACF(537219),        --S5720-28P-PWR-LI-ACF     Metro Service Platform for V2R10C00
                bname8031S1720-28GWR-PWR-4P(537220),          --S1720-28GWR-PWR-4P       Metro Service Platform for V2R10C00
                bname8031S5720-28X-PWR-LI-AC(537221),         --S5720-28X-PWR-LI-AC      Metro Service Platform for V2R10C00
                bname8031S5320-28X-PWR-LI-AC(537222),         --S5320-28X-PWR-LI-AC      Metro Service Platform for V2R10C00
                bname8031S5720-28X-PWR-LI-ACF(537223),        --S5720-28X-PWR-LI-ACF     Metro Service Platform for V2R12,modify to   V2R*,on 2016.12.24
                bname8031S5320-28X-PWR-LI-ACF(537224),        --S5320-28X-PWR-LI-ACF     Metro Service Platform for V2R12,modify to   V2R*,on 2016.12.24
                bname8031S5720S-28X-PWR-LI-AC(537225),        --S5720S-28X-PWR-LI-AC     Metro Service Platform for V2R10C00
                bname8031S628X-PWR-E(537226),                 --S628X-PWR-E              Metro Service Platform for V2R10C00
                bname8031S1720-28GWR-PWR-4X(537227),          --S1720-28GWR-PWR-4X       Metro Service Platform for V2R10C00
                bname8031S5720-52P-LI-AC(537228),             --S5720-52P-LI-AC          Metro Service Platform for V2R10C00
                bname8031S5720S-52P-LI-AC(537229),            --S5720S-52P-LI-AC         Metro Service Platform for V2R10C00
                bname8031S5320-52P-LI-AC(537230),             --S5320-52P-LI-AC          Metro Service Platform for V2R10C00
                bname8031S652-E(537231),                      --S652-E                   Metro Service Platform for V2R10C00
                bname8031S5720S-52X-LI-AC(537232),            --S5720S-52X-LI-AC         Metro Service Platform for V2R10C00
                bname8031S652X-E(537233),                     --S652X-E                  Metro Service Platform for V2R10C00
                bname8031S5720-52X-LI-AC(537234),             --S5720-52X-LI-AC          Metro Service Platform for V2R10C00
                bname8031S5720-52X-LI-DC(537235),             --S5720-52X-LI-DC          Metro Service Platform for V2R10C00
                bname8031S5320-52X-LI-AC(537236),             --S5320-52X-LI-AC          Metro Service Platform for V2R10C00
                bname8031S5320-52X-LI-DC(537237),             --S5320-52X-LI-DC          Metro Service Platform for V2R10C00
                bname8031S1720-52GWR-4P(537238),              --S1720-52GWR-4P           Metro Service Platform for V2R10C00
                bname8031S1720-52GWR-4X(537239),              --S1720-52GWR-4X           Metro Service Platform for V2R10C00
                bname8031S5720-52P-PWR-LI-AC(537240),         --S5720-52P-PWR-LI-AC      Metro Service Platform for V2R10C00
                bname8031S5720S-52P-PWR-LI-AC(537241),        --S5720S-52P-PWR-LI-AC     Metro Service Platform for V2R10C00
                bname8031S5320-52P-PWR-LI-AC(537242),         --S5320-52P-PWR-LI-AC      Metro Service Platform for V2R10C00
                bname8031S652-PWR-E(537243),                  --S652-PWR-E               Metro Service Platform for V2R10C00
                bname8031S5720-52P-PWR-LI-ACF(537244),        --S5720-52P-PWR-LI-ACF     Metro Service Platform for V2R10C00
                bname8031S5720S-52X-PWR-LI-AC(537245),        --S5720S-52X-PWR-LI-AC     Metro Service Platform for V2R10C00
                bname8031S652X-PWR-E(537246),                 --S652X-PWR-E              Metro Service Platform for V2R10C00
                bname8031S5720-52X-PWR-LI-AC(537247),         --S5720-52X-PWR-LI-AC      Metro Service Platform for V2R10C00
                bname8031S5320-52X-PWR-LI-AC(537248),         --S5320-52X-PWR-LI-AC      Metro Service Platform for V2R10C00
                bname8031S5720-52X-PWR-LI-ACF(537249),        --S5720-52X-PWR-LI-ACF     Metro Service Platform for V2R12,modify to   V2R*,on 2016.12.24
                bname8031S5320-52X-PWR-LI-ACF(537250),        --S5320-52X-PWR-LI-ACF     Metro Service Platform for V2R12,modify to   V2R*,on 2016.12.24
                bname8031S1720-52GWR-PWR-4P(537251),          --S1720-52GWR-PWR-4P       Metro Service Platform for V2R10C00
                bname8031S1720-52GWR-PWR-4X(537252),          --S1720-52GWR-PWR-4X       Metro Service Platform for V2R10C00
                bname8031S5720-28X-SI-24S-AC(537253),         --S5720-28X-SI-24S-AC      Metro Service Platform for V2R10C00
                bname8031S5720-28X-SI-24S-DC(537254),         --S5720-28X-SI-24S-DC      Metro Service Platform for V2R10C00
                bname8031S5321-28X-SI-24S-AC(537255),         --S5321-28X-SI-24S-AC      Metro Service Platform for V2R10C00
                bname8031S5321-28X-SI-24S-DC(537256),         --S5321-28X-SI-24S-DC      Metro Service Platform for V2R10C00
                bname8031S5720-28X-LI-24S-AC(537257),         --S5720-28X-LI-24S-AC      Metro Service Platform for V2R10C00
                bname8031S5720S-28X-LI-24S-AC(537258),        --S5720S-28X-LI-24S-AC     Metro Service Platform for V2R10C00
                bname8031S5720-28X-LI-24S-DC(537259),         --S5720-28X-LI-24S-DC      Metro Service Platform for V2R10C00
                bname8031S5320-28X-LI-24S-AC(537260),         --S5320-28X-LI-24S-AC      Metro Service Platform for V2R10C00
                bname8031S5320-28X-LI-24S-DC(537261),         --S5320-28X-LI-24S-DC      Metro Service Platform for V2R10C00
                bname8031S5720-28TP-PWR-LI-ACL(537262),       --S5720-28TP-PWR-LI-ACL    Metro Service Platform for V2R10C00
                bname8031S5720S-28TP-PWR-LI-ACL(537263),      --S5720S-28TP-PWR-LI-ACL   Metro Service Platform for V2R10C00
                bname8031S1720-28GWR-PWR-4TP(537264),         --S1720-28GWR-PWR-4TP      Metro Service Platform for V2R10C00
                bname8031S5720-28TP-PWR-LI-AC(537265),        --S5720-28TP-PWR-LI-AC     Metro Service Platform for V2R10C00
                bname8031S628-PWR-E(537266),                  --S628-PWR-E               Metro Service Platform for V2R10C00
                bname8031S5720-28TP-LI-AC(537267),            --S5720-28TP-LI-AC         Metro Service Platform for V2R10C00
                bname8031S628-E(537268),                      --S628-E                   Metro Service Platform for V2R10C00
                bname8031S1700-28GR-4X(537269),               --S1700-28GR-4X            Metro Service Platform for V2R11
                bname8031S1700-52GR-4X(537270),               --S1700-52GR-4X            Metro Service Platform for V2R11
                bname8031S5720-28X-SI-12S-AC(537271),         --S5720-28X-SI-12S-AC      Metro Service Platform for V2R12,modify to   V2R*,on 2016.12.24
                bname8031S5720S-28X-SI-12S-AC(537272),        --S5720S-28X-SI-12S-AC     Metro Service Platform for V2R12,modify to   V2R*,on 2016.12.24
                bname8031S5720-30C-LI-AC(537273),             --S5720-30C-LI-AC          Metro Service Platform for V2R12,modify to   V2R*,on 2016.12.24
                bname8031S5720-30C-LI-DC(537274),             --S5720-30C-LI-DC          Metro Service Platform for V2R10C00
                bname8031S5720-54C-LI-AC(537275),             --S5720-54C-LI-AC          Metro Service Platform for V2R12,modify to   V2R*,on 2016.12.24
                bname8031S5720-54C-LI-DC(537276),             --S5720-54C-LI-DC          Metro Service Platform for V2R10C00
                bname8031S5720-30C-PWR-LI-AC(537277),         --S5720-30C-PWR-LI-AC      Metro Service Platform for V2R12,modify to   V2R*,on 2016.12.24
                bname8031S5720-30C-PWR-LI-DC(537278),         --S5720-30C-PWR-LI-DC      Metro Service Platform for V2R10C00
                bname8031S5720-54C-PWR-LI-AC(537279),         --S5720-54C-PWR-LI-AC      Metro Service Platform for V2R12,modify to   V2R*,on 2016.12.24
                bname8031S5720-54C-PWR-LI-DC(537280),         --S5720-54C-PWR-LI-DC      Metro Service Platform for V2R10C00
                bname8031S5720-28X-SI-C(537281),              --S5720-28X-SI-C           Metro Service Platform for V2R10C00
                bname8031S5720-52X-SI-C(537282),              --S5720-52X-SI-C           Metro Service Platform for V2R10C00
                bname8031S5720-28X-PWR-SI-C(537283),          --S5720-28X-PWR-SI-C       Metro Service Platform for V2R10C00
                bname8031S5720-52X-PWR-SI-C(537284),          --S5720-52X-PWR-SI-C       Metro Service Platform for V2R10C00
                bname8031S5320-28X-PWR-SI-DC(537285),         --S5320-28X-PWR-SI-DC      Metro Service Platform for V2R10C00
                bname8031S5320-52X-PWR-SI-DC(537286),         --S5320-52X-PWR-SI-DC      Metro Service Platform for V2R10C00
                bname8031S5320-28P-SI-DC(537287),             --S5320-28P-SI-DC          Metro Service Platform for V2R10C00
                bname8031S5320-52P-SI-DC(537288),             --S5320-52P-SI-DC          Metro Service Platform for V2R10C00
                bname8031S5320-56C-PWR-EI-ACF(537289),        --S5320-56C-PWR-EI-ACF     Metro Service Platform for V2R10C00
                bname8031S5320-12TP-LI-DC(537290),            --S5320-12TP-LI-DC         Metro Service Platform for V2R10C00
                bname8031S5321-52X-LI-AC(537291),             --S5321-52X-LI-AC          Metro Service Platform for V2R10C00
                bname8031S5320-28X-PWR-SI(537292),            --S5320-28X-PWR-SI         Metro Service Platform for V2R10C00
                bname8031S5320-52X-PWR-SI(537293),            --S5320-52X-PWR-SI         Metro Service Platform for V2R10C00
                bname8031S5320-28P-SI(537294),                --S5320-28P-SI             Metro Service Platform for V2R10C00
                bname8031S5322-52X-LI-AC(537295),             --S5322-52X-LI-AC          Metro Service Platform for V2R10C00
                bname8031S6320-54C-EI-48S(537296),            --S6320-54C-EI-48S         Metro Service Platform for V2R10C00
                bname8031S5720-16X-PWH-LI-AC(537297),         --S5720-16X-PWH-LI-AC      Metro Service Platform for V2R10C00

                bname8031S5720-28X-PWH-LI-AC(537298),        --S5720-28X-PWH-LI-AC        Metro Service Platform for V2R11C00
                bname8031S5320-28X-PWH-LI-AC(537299),        --S5320-28X-PWH-LI-AC        Metro Service Platform for V2R11C00 del

                bname8031S1720-28GWR-4P-E(537300),           --S1720-28GWR-4P-E           Metro Service Platform for V2R10C00 TR6
                bname8031S1720-28GWR-4X-E(537301),           --S1720-28GWR-4X-E           Metro Service Platform for V2R10C00 TR6
                bname8031S1720-28GWR-PWR-4P-E(537302),       --S1720-28GWR-PWR-4P-E       Metro Service Platform for V2R10C00 TR6
                bname8031S1720-28GWR-PWR-4X-E(537303),       --S1720-28GWR-PWR-4X-E       Metro Service Platform for V2R10C00 TR6
                bname8031S1720-52GWR-4P-E(537304),           --S1720-52GWR-4P-E           Metro Service Platform for V2R10C00 TR6
                bname8031S1720-52GWR-4X-E(537305),           --S1720-52GWR-4X-E           Metro Service Platform for V2R10C00 TR6
                bname8031S1720-52GWR-PWR-4P-E(537306),       --S1720-52GWR-PWR-4P-E       Metro Service Platform for V2R10C00 TR6
                bname8031S1720-52GWR-PWR-4X-E(537307),       --S1720-52GWR-PWR-4X-E       Metro Service Platform for V2R10C00 TR6
                bname8031S1720-28GWR-PWR-4TP-E(537308),      --S1720-28GWR-PWR-4TP-E      Metro Service Platform for V2R10C00 TR6
                bname8031S1720-10GW-2P-E(537309),            --S1720-10GW-2P-E            Metro Service Platform for V2R10C00 TR6
                bname8031S1720-10GW-PWR-2P-E(537310),        --S1720-10GW-PWR-2P-E        Metro Service Platform for V2R10C00 TR6

                bname8031S5720-12X-LI-AC(537311),                 --S5720-12X-LI-AC            Metro Service Platform for   V2R*,on 2016.12.24
                bname8031S5320-12X-LI-AC(537312),                 --S5320-12X-LI-AC            Metro Service Platform for   V2R*,on 2016.12.24
                bname8031S5720-12X-PWR-LI-AC(537313),             --S5720-12X-PWR-LI-AC        Metro Service Platform for   V2R*,on 2016.12.24
                bname8031S5320-12X-PWR-LI-AC(537314),             --S5320-12X-PWR-LI-AC        Metro Service Platform for V2R11
                bname8031S5320-28TP-LI-AC(537315),                --S5320-28TP-LI-AC           Metro Service Platform for V2R11
                bname8031S5721-28X-SI-24S-AC(537316),             --S5721-28X-SI-24S-AC        Metro Service Platform for V2R11
                bname8031S5320-28X-SI-24S-AC(537317),             --S5320-28X-SI-24S-AC        Metro Service Platform for V2R11
                bname8031S5320-28X-SI-24S-DC(537318),             --S5320-28X-SI-24S-DC        Metro Service Platform for V2R11
                bname8031S2720-12TP-EI(537319),                --S2720-12TP-EI           Metro Service Platform for V2R11,modify name
                bname8031S2320-12TP-EI-AC(537320),                --S2320-12TP-EI-AC           Metro Service Platform for V2R11
                bname8031S2320-12TP-EI-DC(537321),                --S2320-12TP-EI-DC           Metro Service Platform for V2R11
                bname8031S2720-12TP-PWR-EI(537322),            --S2720-12TP-PWR-EI       Metro Service Platform for V2R11,modify name
                bname8031S2320-12TP-PWR-EI-AC(537323),            --S2320-12TP-PWR-EI-AC       Metro Service Platform for V2R11
                bname8031S2720-52TP-EI(537324),                --S2720-52TP-EI           Metro Service Platform for V2R11,modify name
                bname8031S2320-52TP-EI-AC(537325),                --S2320-52TP-EI-AC           Metro Service Platform for V2R11
                bname8031S2720-52TP-PWR-EI(537326),            --S2720-52TP-PWR-EI-AC       Metro Service Platform for V2R11,modify name
                bname8031S2320-52TP-PWR-EI-AC(537327),            --S2320-52TP-PWR-EI-AC       Metro Service Platform for V2R11
                bname8031S2720-28TP-PWR-EI-L(537328),           --S2720-28TP-PWR-EI-L      Metro Service Platform for V2R11,modify name
                bname8031S2720-28TP-EI(537329),             --S2720-28TP-EI        Metro Service Platform for V2R11,modify name
                bname8031S2320-28TP-EI-AC(537330),                --S2320-28TP-EI-AC           Metro Service Platform for V2R11
                bname8031S2320-28TP-EI-DC(537331),                --S2320-28TP-EI-DC           Metro Service Platform for V2R11
                bname8031S2720-28TP-PWR-EI(537332),            --S2720-28TP-PWR-EI       Metro Service Platform for V2R11,modify name
                bname8031S2320-28TP-PWR-EI-AC(537333),            --S2320-28TP-PWR-EI-AC       Metro Service Platform for V2R11
                bname8031S2320-28P-PWR-EI-ACF(537334),            --S2320-28P-PWR-EI-ACF       Metro Service Platform for V2R11

                bname8031S6720-26Q-LI-24S-AC(537335),             --S6720-26Q-LI-24S-AC        Metro Service Platform for V2R11
                bname8031S6720S-26Q-LI-24S-AC(537336),            --S6720S-26Q-LI-24S-AC       Metro Service Platform for V2R11
                bname8031S6321-26Q-SI-24S-AC(537337),             --S6321-26Q-SI-24S-AC        Metro Service Platform for   V2R*,on 2016.12.24
                bname8031S6320-26Q-SI-24S-AC(537338),             --S6320-26Q-SI-24S-AC        Metro Service Platform for   V2R*,on 2016.12.24
                bname8031S6720S-26Q-SI-24S-AC(537339),            --S6720S-26Q-SI-24S-AC       Metro Service Platform for V2R11
                bname8031S6720-26Q-SI-24S-AC(537340),             --S6720-26Q-SI-24S-AC        Metro Service Platform for V2R11
                bname8031S6720-16X-LI-16S-AC(537341),             --S6720-16X-LI-16S-AC        Metro Service Platform for V2R11
                bname8031S6720S-16X-LI-16S-AC(537342),            --S6720S-16X-LI-16S-AC       Metro Service Platform for V2R11
                bname8031S1720X-16XWR(537343),                    --S1720X-16XWR               Metro Service Platform for V2R11
                bname8031S1720X-16XWR-E(537344),                  --S1720X-16XWR-E             Metro Service Platform for V2R11
                bname8031S6720-32X-LI-32S-AC(537345),             --S6720-32X-LI-32S-AC        Metro Service Platform for V2R11
                bname8031S6720S-32X-LI-32S-AC(537346),            --S6720S-32X-LI-32S-AC       Metro Service Platform for V2R11
                bname8031S6720-32X-SI-32S-AC(537347),             --S6720-32X-SI-32S-AC        Metro Service Platform for V2R11
                bname8031S6320-32X-SI-32S-AC(537348),             --S6320-32X-SI-32S-AC        Metro Service Platform for   V2R*,on 2016.12.24
                bname8031S1720X-32XWR(537349),                    --S1720X-32XWR               Metro Service Platform for V2R11
                bname8031S1720X-32XWR-E(537350),                  --S1720X-32XWR-E             Metro Service Platform for V2R11
                bname8031S6720-32C-SI-AC(537351),                 --S6720-32C-SI-AC            Metro Service Platform for V2R11
                bname8031S6720-32C-SI-DC(537352),                 --S6720-32C-SI-DC            Metro Service Platform for V2R11
                bname8031S6320-32C-SI-AC(537353),                 --S6320-32C-SI-AC            Metro Service Platform for   V2R*,on 2016.12.24
                bname8031S6320-32C-SI-DC(537354),                 --S6320-32C-SI-DC            Metro Service Platform for   V2R*,on 2016.12.24
                bname8031S6720-32C-PWH-SI-AC(537355),             --S6720-32C-PWH-SI-AC        Metro Service Platform for V2R11
                bname8031S6720-32C-PWH-SI(537356),                --S6720-32C-PWH-SI           Metro Service Platform for V2R11
                bname8031S6320-32C-PWH-SI-AC(537357),             --S6320-32C-PWH-SI-AC        Metro Service Platform for   V2R*,on 2016.12.24
                bname8031S6320-32C-PWH-SI(537358),                --S6320-32C-PWH-SI           Metro Service Platform for   V2R*,on 2016.12.24
                bname8031S6720-56C-PWH-SI-AC(537359),             --S5730-56C-PWH-SI-AC        Metro Service Platform for V2R11,modify from S5730-56C-PWH-SI-AC to S6720-56C-PWH-SI-AC
                bname8031S6720-56C-PWH-SI(537360),                --S5730-56C-PWH-SI           Metro Service Platform for V2R11,modify from S5730-56C-PWH-SI to S6720-56C-PWH-SI
                bname8031S6320-56C-PWH-SI-AC(537361),             --S5330-56C-PWH-SI-AC        Metro Service Platform for V2R11,modify from S5330-56C-PWH-SI-AC to S6320-56C-PWH-SI-AC
                bname8031S6320-56C-PWH-SI(537362),                --S5330-56C-PWH-SI           Metro Service Platform for V2R11,modify from S5330-56C-PWH-SI to S6320-56C-PWH-SI

                bname8031S6720-48Q-SI-48S-AC(537363),         --S6720-48Q-SI-48S-AC        Metro Service Platform for V2R11,del on 2017.4.11
                bname8031S6720S-48Q-SI-48S-AC(537364),        --S6720S-48Q-SI-48S-AC       Metro Service Platform for V2R11,del on 2017.4.11
                bname8031S6320-48Q-SI-48S-AC(537365),         --S6320-48Q-SI-48S-AC        Metro Service Platform for   V2R*,on 2016.12.24
                bname8031S5730-48C-SI-AC(537366),             --S5730-48C-SI-AC            Metro Service Platform for V2R11
                bname8031S5330-48C-SI-AC(537367),             --S5330-48C-SI-AC            Metro Service Platform for   V2R*,on 2016.12.24
                bname8031S5730-48C-PWR-SI-AC(537368),         --S5730-48C-PWR-SI-AC        Metro Service Platform for V2R11
                bname8031S5730-68C-SI-AC(537369),             --S5730-68C-SI-AC            Metro Service Platform for V2R11
                bname8031S5330-68C-SI-AC(537370),             --S5330-68C-SI-AC            Metro Service Platform for V2R11
                bname8031S5730-68C-PWR-SI-AC(537371),         --S5730-68C-PWR-SI-AC        Metro Service Platform for V2R11
                bname8031S6720-52X-PWH-SI-ACF(537372),        --S6720-52X-PWH-SI-ACF       Metro Service Platform for V2R11
                bname8031S6720-52X-PWH-SI(537373),            --S6720-52X-PWH-SI           Metro Service Platform for V2R11
                bname8031S6320-52X-PWH-SI-ACF(537374),        --S6320-52X-PWH-SI-ACF       Metro Service Platform for   V2R*,on 2016.12.24
                bname8031S6320-52X-PWH-SI(537375),            --S6320-52X-PWH-SI           Metro Service Platform for   V2R*,on 2016.12.24

                bname8031S5720-28P-LI-AC-SEA(537376),         -- Real name S5720-28P-LI-AC     for LSW V2R11 support license for oversea
                bname8031S5720-28P-PWR-LI-AC-SEA(537377),     -- Real name S5720-28P-PWR-LI-AC for LSW V2R11 support license for oversea
                bname8031S5320-28P-LI-AC-SEA(537378),         -- Real name S5320-28P-LI-AC     for LSW V2R11 support license for oversea
                bname8031S5320-28P-PWR-LI-AC-SEA(537379),     -- Real name S5320-28P-PWR-LI-AC for LSW V2R11 support license for oversea
                bname8031S5720-52P-LI-AC-SEA(537380),         -- Real name S5720-52P-LI-AC     for LSW V2R11 support license for oversea
                bname8031S5320-52P-LI-AC-SEA(537381),         -- Real name S5320-52P-LI-AC     for LSW V2R11 support license for oversea
                bname8031S5720-52P-PWR-LI-AC-SEA(537382),     -- Real name S5720-52P-PWR-LI-AC for LSW V2R11 support license for oversea
                bname8031S5320-52P-PWR-LI-AC-SEA(537383),     -- Real name S5320-52P-PWR-LI-AC for LSW V2R11 support license for oversea

                bname8031S5320-12P-LI-BAT(537384),            --S5320-12P-LI-BAT  add for LSW V2R11C10
                bname8031S5330-68C-SI(537385),                --S5330-68C-SI      add for LSW V2R11C10
                bname8031S5730-68C-PWR-SI(537386),            --S5730-68C-PWR-SI  add for LSW V2R11C10

                bname8031S5730-52X-PWH-SI-ACF(537387),       --98010786	S5730-52X-PWH-SI-ACF add for lsw v2r11c10
                bname8031S5730-56C-PWH-SI-AC(537388),        --98010785	S5730-56C-PWH-SI-AC  add for lsw v2r11c10
                bname8031S5730-32C-PWH-SI-AC(537389),        --98010787	S5730-32C-PWH-SI-AC  add for lsw v2r11c10

                bname8031S2320-52TP-EI-DC(537390),      --98010788 S2320-52TP-EI-DC  for lsw v2r11c10
                bname8031S5330-68C-SI-DC(537391),       --98010789 S5330-68C-SI-DC   for lsw  v2r11c10
                bname8031S5730S-48C-EI-AC(537392),     --98010790 S5730S-48C-EI-AC   for lsw  v2r11c10
                bname8031S5730S-48C-PWR-EI(537393),    --98010791 S5730S-48C-PWR-EI  for lsw  v2r11c10
                bname8031S5730S-68C-EI-AC(537394),     --98010792 S5730S-68C-EI-AC   for lsw  v2r11c10
                bname8031S5730S-68C-PWR-EI(537395),    --98010793 S5730S-68C-PWR-EI  for lsw  v2r11c10

                bname8031S5735-S24U4X(537964),    --S5735-S24U4X (24*10/100/1000BASE-T ports, 4*10GE SFP+ ports, PoE++, without power module)
                bname8031S5735-S48U4X(537965),    --S5735-S48U4X (48*10/100/1000BASE-T ports, 4*10GE SFP+ ports, PoE++, without power module)
                bname8031S5735S-S24S4X-A(537966),    --S5735S-S24S4X bundle (24*GE SFP ports, 4*10GE SFP+ ports, 1*AC power module)
                bname8031S5735S-S48S4X-A(537967),    --S5735S-S48S4X bundle (48*GE SFP ports, 4*10GE SFP+ ports, 1*AC power module)
                bname8031S6720S-S36S16X-A(537968),    --S6720S-S36S16X-A (36*GE SFP ports, 16*10GE SFP+ ports, AC power supply, front access)
                bname8031S5735S-S24T4S-XA(537969),    --S5735S-S24T4S-X Bundle (24*10/100/1000BASE-T ports, 4*GE SFP ports, 1*AC power)

                bname8031S5330-36C-HI(537400),          --02351MQK S5330-36C-HI      for lsw  v2r11c50
                bname8031S5730-36C-HI(537401),          --02351MQJ S5730-36C-HI      for lsw  v2r11c50
                bname8031S5730-44C-HI(537402),          --02351MQG S5730-44C-HI      for lsw  v2r11c50
                bname8031S5330-36C-PWH-HI(537403),      --02351MQM S5330-36C-PWH-HI  for lsw  v2r11c50
                bname8031S5730-36C-PWH-HI(537404),      --02351MQN S5730-36C-PWH-HI  for lsw  v2r11c50
                bname8031S5730-44C-PWH-HI(537405),      --02351LKB S5730-44C-PWH-HI  for lsw  v2r11c50
                bname8031S5330-60C-HI(537406),          --02351MQP S5330-60C-HI      for lsw  v2r11c50
                bname8031S5730-60C-HI(537407),          --02351MQR S5730-60C-HI      for lsw  v2r11c50
                bname8031S5730-68C-HI(537408),          --02351MQT S5730-68C-HI      for lsw  v2r11c50
                bname8031S5730-60C-PWH-HI(537409),      --02351MQV S5730-60C-PWH-HI  for  lsw v2r11c50
                bname8031S5730-68C-PWH-HI(537410),      --02351LKE S5730-68C-PWH-HI  for lsw  v2r11c50
                bname8031S6720-50L-HI-48S(537411),      --02351MXN S6720-50L-HI-48S  for lsw  v2r11c50
                bname8031S6320-50L-HI-48S(537412),      --02351MXP S6320-50L-HI-48S  for  lsw v2r11c50
                bname8031S6720-30L-HI-24S(537413),      --02351MXR S6720-30L-HI-24S  for lsw  v2r11c50
                bname8031S6320-30L-HI-24S(537414),      --02351MXS S6320-30L-HI-24S  for lsw  v2r11c50

                bname8031S5720I-12X-SI-AC(537415),            --98010794 S5720I-12X-SI-AC for lsw v2r12c00
                bname8031S5720I-12X-PWH-SI-DC(537416),  --98010795 S5720I-12X-PWH-SI-DC for lsw v2r12c00
                bname8031S5720I-28X-SI-AC(537417),            --98010796 S5720I-28X-SI-AC for lsw v2r12c00
                bname8031S5720I-28X-PWH-SI-AC(537418),  --98010797 S5720I-28X-PWH-SI-AC for lsw v2r12c00
                bname8031S5320-52X-SI-AC-V1(537419),          -- Real name S5320-52X-SI-AC for LSW V2R11C10 from S5320-52X-LI-AC
                bname8031S5320-52X-SI-DC-V1(537420),          -- Real name S5320-52X-SI-DC for LSW V2R11C10 from S5320-52X-LI-DC
                bname8031S5320-52P-SI-AC-V1(537421),          -- Real name S5320-52P-SI-AC for LSW V2R11C10 from S5320-52P-LI-AC
                bname8031S5320-52P-SI-DC-V1(537422),          -- Real name S5320-52P-SI-DC for LSW V2R11C10 from S5320-52P-LI-AC
                bname8031S5300-52P-LI-DC-V1(537423),          -- Real name S5300-52P-LI-DC for LSW V2R11C10 from S5320-52P-LI-AC
                bname8031S5320-36C-EI-28S-AC-V1(537424),      -- Real name S5320-36C-EI-28S-AC for LSW V2R11C10 from S5320-28X-LI-24S-AC
                bname8031S5320-36C-EI-28S-DC-V1(537425),      -- Real name S5320-36C-EI-28S-DC for LSW V2R11C10 from S5320-28X-LI-24S-DC
                bname8031S5730-44C-HI-24S(537426),            --02351XFR S5730-44C-HI-24S     for lsw v2r13c00
                bname8031S5730-60C-HI-48S(537427),            --02351XFS S5730-60C-HI-48S     for lsw v2r13c00
                bname8031S5730-68C-HI-48S(537428),            --02351XFT S5730-68C-HI-48S     for lsw v2r13c00
                bname8031S5730-36C-HI-24S(537429),            --02351XFQ S5730-36C-HI-24S     for lsw v2r13c00
                bname8031S5720I-12X-PWH-SI-AC(537430),        --98010811 S5720I-12X-PWH-SI-AC for lsw v2r13c00
                bname8031S5720I-10X-PWH-SI-AC(537431),        --S5720I-10X-PWH-SI-AC for lsw v2r13c00

               bname8031S1600-8(537432),                 -- Real name s1700-8G-AC               for LSW V2R12C10
               bname8031S1600-16(537433),               -- Real name s1700-16G                 for LSW V2R12C10
               bname8031S1600-24(537434),               -- Real name s1724G-AC                 for LSW V2R12C10
               bname8031S2600-10P(537435),             -- Real name s1720-10GW-2P             for LSW V2R12C10
               bname8031S2600-10P-PWR(537436),         -- Real name s1720-10GW-PWR-2P         for LSW V2R12C10
               bname8031S2600-28P(537437),                  -- Real name s1720-28GWR-4P            for LSW V2R12C10
               bname8031S2600-28P-PWR(537438),        -- Real name s1720-28GWR-PWR-4P        for LSW V2R12C10
               bname8031S3600-28P(537439),                  -- Real name s1720-28GWR-4P-E          for LSW V2R12C10
               bname8031S3600-28P-PWR(537440),         -- Real name s1720-28GWR-PWR-4P-E      for LSW V2R12C10
               bname8031S3600-52P(537441),                  -- Real name s1720-52GWR-4P-E          for LSW V2R12C10
               bname8031S3600-52P-PWR(537442),         -- Real name s1720-52GWR-PWR-4P-E9     for LSW V2R12C10
               bname8031S1700-16-AC(537443),              -- Real name s1700-24-AC               for LSW V2R12C10
               bname8031S1700-24R(537444),                 -- Real name s1700-24-AC               for LSW V2R12C10
               bname8031S5330-60C-HI-48S(537445),               --S5330-60C-HI-48S for V2R13C00
               bname8031S5330-36C-HI-24S(537446),               --S5330-36C-HI-24S for V2R13C00
               bname8031S5720-52X-LI-48S-AC(537447),          --S5720-52X-LI-48S-AC for V2R13C00
               bname8031S5320-52X-LI-48S-AC(537448),          --S5320-52X-LI-48S-AC for V2R13C00
               bname8031S5320-52X-LI-48S-DC(537449),          --S5320-52X-LI-48S-DC for V2R13C00
               bname8031S5320-52X-SI-48S(537450),                --S5320-52X-SI-48S for V2R13C00
               bname8031S5720-52X-SI-48S(537451),                --S5720-52X-SI-48S for V2R13C00
               bname8031S6320-26Q-LI-24S(537452),                --S6320-26Q-LI-24S for V2R12C00
               bname8031S5720I-10X-PWH-SI-AC-Sea(537453),     --S5720I-10X-PWH-SI-AC oversea for V2R13C00
               bname8031S5720I-6X-PWH-SI-AC(537454),              --5720I-6X-PWH-SI-AC for V2R13C00

               bname8031S1820EC-8G(537455),                    --S1820EC-8G           for LSW V2R12C20
               bname8031S1820EC-24G(537456),                   --S1820EC-24G          for LSW V2R12C20
               bname8031S5820EC-10P(537457),                   --S5820EC-10P          for LSW V2R12C20
               bname8031S5820EC-10P-PWR(537458),               --S5820EC-10P-PWR      for LSW V2R12C20
               bname8031S5820EC-28P(537459),                   --S5820EC-28P          for LSW V2R12C20
               bname8031S5820EC-28P-PWR(537460),               --S5820EC-28P-PWR      for LSW V2R12C20
               bname8031S1720-10GF-2P(537461),                 --S1720-10GF-2P        for LSW V2R12C20
               bname8031S1720-10GF-PWR-2P(537462),             --S1720-10GF-PWR-2P    for LSW V2R12C20
               bname8031S1720-28GFR-4P(537463),                --S1720-28GFR-4P       for LSW V2R12C20
               bname8031S1720-28GFR-PWR-4P(537464),            --S1720-28GFR-PWR-4P   for LSW V2R12C20
               bname8031S1720-52GFR-4P(537465),                --S1720-52GFR-4P       for LSW V2R12C20
               bname8031S1720-52GFR-PWR-4P(537466),            --S1720-52GFR-PWR-4P   for LSW V2R12C20
               bname8031S5720SV2-28P-LI-AC(537467),            --S5720SV2-28P-LI-AC   for LSW V2R12C20
               bname8031S5720SV2-52P-LI-AC(537468),            --S5720SV2-52P-LI-AC   for LSW V2R12C20
               bname8031S6730-H48X6C(537469),                --S6730-H48X6C for LSW V2R19C00
               bname8031S6330-H48X6C(537470),                --S6330-H48X6C for LSW V2R19C00
               bname8031S6730-H24X6C(537471),                --S6730-H24X6C for LSW V2R19C00
               bname8031S6330-H24X6C(537472),               --S6330-H24X6C for LSW V2R19C00
               bname8031S5720-28X-PWR-LI-ACF-740(537473),      ---S5720-28X-PWR-LI-ACF(740W) for LSW V2R13C00
               --bnam8031S6750-36L-HI-36S(537474),              S6750-36L-HI-36S (36*100GE QSFP28 ports, without power modules) for V2R19C00
               --bnam8031S6350-36L-HI-36S(537475),              S6350-36L-HI-36S (36*100GE QSFP28 ports, without power modules) for V2R19C00
               --bname8031S2720S-12TP-EI-AC(537476),                  S2720S-12TP-EI-AC for V2R19C00
               --bname8031S2720S-12TP-PWR-EI-AC(537477),         S2720S-12TP-PWR-EI-AC for V2R19C00
               --bname8031S2720S-52TP-EI-AC(537478),                   S2720S-52TP-EI-AC for V2R19C00
               --bname8031S2720S-52TP-PWR-EI-AC(537479),         S2720S-52TP-PWR-EI-AC for V2R19C00
               --bname8031S2720S-28TP-PWR-EI-L-AC(537480),       S2720S-28TP-PWR-EI-L-AC for V2R19C00
               --bname8031S2720S-28TP-PWR-EI-AC(537481),         S2720S-28TP-PWR-EI-AC for V2R19C00
               --bname8031S2720S-28TP-EI-AC(537482),             S2720S-28TP-EI-AC for V2R19C00
               --bname8031S5730-32C-PWH-SI(537483),             S5730-32C-PWH-SI for V2R19C00
               bname8031S5731-H24T4XC(537484),                    --S5731-H24T4XC for V2R19C00
               bname8031S5731-H48T4XC(537485),                    --S5731-H48T4XC for V2R19C00
               bname8031S5731-H24P4XC(537486),                    --S5731-H24P4XC for V2R19C00
               bname8031S5731-H48P4XC(537487),                    --S5731-H48P4XC for V2R19C00
               bname8031S5720I-S4T2S-A(537488),                    --S5720I-S4T2S-A for V2R19C00
               bname8031S5720I-S8U2X-A(537489),                   --S5720I-S8U2X-A for V2R19C00
               bname8031S5720I-S8U2X-A1(537490),                 --S5720I-S8U2X-A1 for V2R19C00
               bname8031S5731-S24T4X(537491),                      --S5731-S24T4X(24*10/100/1000BASE-T ports,4*10GE SFP+ ports,without power module)
               bname8031S5731S-S24T4X-A(537492), 	--S5731S-S24T4X-A(24*10/100/1000BASE-T ports,4*10GE SFP+ ports,1*600W AC power)
               bname8031S5331-H24T4XC(537493),   	--S5331-H24T4XC(24*10/100/1000BASE-T ports,4*10GE SFP+ ports,1*expansion slot,without power module)
               bname8031S5731-S24P4X(537494),    	--S5731-S24P4X(24*10/100/1000BASE-T ports,4*10GE SFP+ ports,1*expansion slot,PoE+, without power module)
               bname8031S5731S-S24P4X-A(537495), 	--S5731S-S24P4X-AA (24*10/100/1000BASE-T ports,4*10GE SFP+ ports,1*expansion slot,PoE+,1*1000W PoE AC power)
               bname8031S5331-H24P4XC(537496),   	--S5331-H24P4XC(24*10/100/1000BASE-T ports,4*10GE SFP+ ports,1*expansion slot,PoE+,without power module)
               bname8031S5731-S48T4X(537497),    	--S5731-S48T4X(48*10/100/1000BASE-T ports,4*10GE SFP+ ports,1*expansion slot,without power module)
               bname8031S5731S-S48T4X-A(537498), 	--S5731S-S48T4X-A(48*10/100/1000BASE-T ports,4*10GE SFP+ ports,1*expansion slot,1*600W AC power)
               bname8031S5331-H48T4XC(537499),   	--S5331-H48T4XC(48*10/100/1000BASE-T ports,4*10GE SFP+ ports,1*expansion slot,without power module)
               bname8031S5731-S48P4X(537500),    	--S5731-S48P4X (48*10/100/1000BASE-T ports,4*10GE SFP+ ports,1*expansion slot,PoE+,without power module)
               bname8031S5731S-S48P4X-A(537501), 	--S5731S-S48P4X-A(48*10/100/1000BASE-T ports,4*10GE SFP+ ports,1*expansion slot,PoE+,1*1000W PoE AC power)
               bname8031S5331-H48P4XC(537502),   	--S5331-H48P4XC(48*10/100/1000BASE-T ports,4*10GE SFP+ ports,1*expansion slot,PoE+,without power module)
               bname8031S5732-H24S6Q(537503),    	--S5732-H24S6Q (20*GE SFP ports,4*10GE SFP+ ports,6*40GE QSFP ports,without power module)
               bname8031S5332-H24S6Q(537504),    	--S5332-H24S6Q (20*GE SFP ports,4*10GE SFP+ ports,6*40GE QSFP ports,without power module)
               bname8031S5732-H48S6Q(537505),    	--S5732-H48S6Q (44*GE SFP ports,4*10GE SFP+ ports,6*40GE QSFP ports,without power module)
               bname8031S5332-H48S6Q(537506),    	--S5332-H48S6Q (44*GE SFP ports,4*10GE SFP+ ports,6*40GE QSFP ports,without power module)
               bname8031S6730-S24X6Q(537507),    	--S6730-S24X6Q (24*10GE SFP+ ports,6*40GE QSFP ports,without power module)
               bname8031S6730S-S24X6Q-A(537508), 	--S6730S-S24X6Q-A (24*10GE SFP+ ports,6*40GE QSFP ports,without power module)
               bname8031S5731S-H24T4XC-A(537509),	--S5731S-H24T4XC-A (24*10/100/1000BASE-T ports,4*10GE SFP+ ports,1*expansion slot,1*600W AC power)
               bname8031S5731S-H48T4XC-A(537510),	--S5731S-H48T4XC-A (48*10/100/1000BASE-T ports,4*10GE SFP+ ports,1*expansion slot,1*600W AC power)

               bname8031S5735-L24T4S-A(537511),                     --S5735-L24T4S-A(24*10/100/1000BASE-T ports,4*GE SFP ports,AC 110/220V)
               bname8031S5735S-L24T4S-A(537512),                    --S5735S-L24T4S-A(24*10/100/1000BASE-T ports,4*GE SFP ports,AC 110/220V)
               bname8031S1730S-S24T4S-A(537514),                    --S1730S-S24T4S-A(24*10/100/1000BASE-T ports,4*GE SFP ports,AC 110/220V)
               bname8031S5735S-L24T4S-MA(537513),                   --S5735S-L24T4S-MA (24*10/100/1000BASE-T ports,4*GE SFP ports,AC 110/220V)
               bname8031S5735S-L24FT4S-A(537515),                   --S5735S-L24FT4S-A(12 Ethernet 10/100 ports,12 Ethernet 10/100/1000 ports,4*GE SFP ports,AC 110/220V)
               bname8031S5735-L12T4S-A(537516),                     --S5735-L12T4S-A(12*10/100/1000BASE-T ports,4*GE SFP ports,AC 110/220V)
               bname8031S5735S-L12T4S-A(537517),                    --S5735S-L12T4S-A(12*10/100/1000BASE-T ports,4*GE SFP ports,AC 110/220V)
               bname8031S5335-L12T4S-A(537518),                      --S5335-L12T4S-A(12*10/100/1000BASE-T ports,4*GE SFP ports,AC 110/220V)
               bname8031S5735-L24T4X-A(537519),                      --S5735-L24T4X-A(24*10/100/1000BASE-T ports,4*10GE SFP+ ports,AC 110/220V)
               bname8031S5735S-L24T4X-A(537520),                     --S5735S-L24T4X-A(24*10/100/1000BASE-T ports,4*10GE SFP+ ports,AC 110/220V)
               bname8031S5335-L24T4X-A(537521),                      --S5335-L24T4X-A(24*10/100/1000BASE-T ports,4*10GE SFP+ ports4,AC power support,front access)
               bname8031S5735-L12P4S-A(537522),                      --S5735-L12P4S-A(12*10/100/1000BASE-T ports,4*GE SFP ports,PoE+,AC 110/220V)
               bname8031S5735S-L12P4S-A(537523),                     --S5735S-L12P4S-A(12*10/100/1000BASE-T ports,4*GE SFP ports,PoE+,AC 110/220V)
               bname8031S5335-L12P4S-A(537524),                      --S5335-L12P4S-A(12*10/100/1000BASE-T ports,4*GE SFP ports,PoE+,AC 110/220V)
               bname8031S5735-L24P4S-A(537525),                      --S5735-L24P4S-A(24*10/100/1000BASE-T ports,4*GE SFP ports,PoE+,AC 110/220V)
               bname8031S5735S-L24P4S-A(537526),                     --S5735S-L24P4S-A(24*10/100/1000BASE-T ports,4*GE SFP ports,PoE+,AC 110/220V)
               bname8031S1730S-S24P4S-A(537528),                     --S1730S-S24P4S-A(24*10/100/1000BASE-T ports,4*GE SFP ports,PoE+,AC 110/220V)
               bname8031S5735S-L24P4S-MA(537527),                    --S5735S-L24P4S-MA(24*10/100/1000BASE-T ports,4*GE SFP ports,PoE+,AC 110/220V)
               bname8031S5735-L24P4X-A(537529),                      --S5735-L24P4X-A(24*10/100/1000BASE-T ports,4*10GE SFP+ ports,PoE+,AC 110/220V)
               bname8031S5735S-L24P4X-A(537530),                     --S5735S-L24P4X-A(24*10/100/1000BASE-T ports,4*10GE SFP+ ports,PoE+,AC 110/220V)
               bname8031S5335-L24P4X-A(537531),                      --S5335-L24P4X-A(24*10/100/1000BASE-T ports,4*10GE SFP+ ports,PoE+,AC 110/220V)
               bname8031S5335-L32ST4X-A(537532),                     --S5335-L32ST4X-A(24*GE SFP ports,8*10/100/1000BASE-T ports,4*10GE SFP+ ports,AC power support,front access)
               bname8031S5735-L32ST4X-A(537533),                     --S5735-L32ST4X-A(24*GE SFP ports,8*10/100/1000BASE-T ports,4*10GE SFP+ ports,AC 110/220V)
               bname8031S5735S-L32ST4X-A(537534),                   --S5735S-L32ST4X-A(24*GE SFP ports,8*10/100/1000BASE-T ports,4*10GE SFP+ ports,AC 110/220V)
               bname8031S5735-S32ST4X(537535),                       --S5735-S32ST4X(24*GE SFP ports,8*10/100/1000BASE-T ports,4*10GE SFP+ ports,without power module)
               bname8031S5735S-S32ST4X-A(537537),                    --S5735-S32ST4X(24*GE SFP ports,8*10/100/1000BASE-T ports,4*10GE SFP+ ports,without power module)
               bname8031S5335-S32ST4X(537536),                       --S5335-S32ST4X(24*GE SFP ports,8*10/100/1000BASE-T ports,4*10GE SFP+ ports,without power module)
               bname8031S5735-L48T4S-A(537538),                      --S5735-L48T4S-A(48*10/100/1000BASE-T ports,4*GE SFP ports,AC 110/220V)
               bname8031S5735S-L48T4S-A(537539),                     --S5735S-L48T4S-A(12 Ethernet 10/100 ports,12 Ethernet 10/100/1000 ports,4*GE SFP ports,AC 110/220V)
               bname8031S1730S-S48T4S-A(537540),                     --S1730S-S48T4S-A(48*10/100/1000BASE-T ports,4*GE SFP ports,AC 110/220V)
               bname8031S5735S-L48FT4S-A(537541),                   --S5735S-L48FT4S-A(24 Ethernet 10/100 ports,24 Ethernet 10/100/1000 ports,4*GE SFP ports,AC 110/220V)
               bname8031S5735-L48T4X-A(537542),                      --S5735-L48T4X-A(24*10/100/1000BASE-T ports,(24*10/100BASE-T ports,4*10GE SFP+ ports,AC 110/220V)
               bname8031S5735S-L48T4X-A(537543),                     --S5735S-L48T4X-A(48*10/100/1000BASE-T ports,4*10GE SFP+ ports,AC 110/220V)
               bname8031S5735-S24T4X(537544),                        --S5735-S24T4X(24*10/100/1000BASE-T ports,4*10GE SFP+ ports,without power module)
               bname8031S5335-S24T4X(537545),                        --S5335-S24T4X(24*10/100/1000BASE-T ports,4*10GE SFP+ ports,without power module)
               bname8031S5735S-S24T4S-A(537546),                     --S5735S-S24T4S-A(24*10/100/1000BASE-T ports,4*10GE SFP+ ports,1*60W AC power)
               bname8031S5735-S24P4X(537547),                        --S5735-S24P4X(24*10/100/1000BASE-T ports,4*GE SFP ports, PoE+,without power module)
               bname8031S5335-S24P4X(537548),                        --S5335-S24P4X(24*10/100/1000BASE-T ports,4*10GE SFP+ ports,PoE+,without power module)
               bname8031S5735-S48T4X(537549),                        --S5735-S48T4X(48*10/100/1000BASE-T ports,4*10GE SFP+ ports,without power module)
               bname8031S5335-S48T4X(537550),                       --S5335-S48T4X(48*10/100/1000BASE-T ports,4*10GE SFP+ ports,without power module)
               bname8031S5735S-S48T4S-A(537551),                     --S5735S-S48T4S-A(48*10/100/1000BASE-T ports,4*GE SFP ports,1*60W AC power)
               bname8031S5735-S48P4X(537552),                        --S5735-S48P4X(48*10/100/1000BASE-T ports,4*GE SFP ports,PoE+,without power module)
               bname8031S5335-S48P4X(537553),                        --S5335-S48P4X(48*10/100/1000BASE-T ports,4*10GE SFP+ ports,PoE+,without power module)
               bname8031S5735-L48P4X-A(537554),                      --S5735-L48P4X-A(48*10/100/1000BASE-T ports,4*10GE SFP+ ports,PoE+,1*1000W PoE AC power)
               bname8031S5735S-L48P4X-A(537555),                     --S5735S-L48P4X-A(48*10/100/1000BASE-T ports,4*10GE SFP+ ports,PoE+,1*1000W PoE AC power)
               bname8031S5735S-L48P4S-A(537556),                     --S5735S-L48P4S-A(48*10/100/1000BASE-T ports,4*GE SFP ports,PoE+,1*1000W PoE AC power)
               bname8031S5735-S48S4X(537557),                        --S5735-S48S4X(48*GE SFP ports,,4*10GE SFP+ ports,PoE+,without power module)
               bname8031S5335-S48S4X(537558),                        --S5335-S48S4X(48*GE SFP ports,,4*10GE SFP+ ports,PoE+,without power module)
               bname8031S5735-S4T2X-IA150G1(537559),                 --S5735-S4T2X-IA150G1 (4*10/100/1000BASE-T ports, 2*10GE SFP+ ports, AC power supply)
               bname8031S5735-S8P2X-IA200G1(537560),                 --S5735-S8P2X-IA200G1 (8*10/100/1000BASE-T ports, 2*10GE SFP+ ports, PoE+, AC power supply)
               bname8031S5735-S8P2X-IA200H1(537561),                 --S5735-S8P2X-IA200H1 (8*10/100/1000BASE-T ports, 2*10GE SFP+ ports, PoE+, support for solar power, AC power supply)
               bname8031S5731S-H24T4S-A(537562),                     --S5731S-H24T4S-A(24*10/100/1000BASE-T ports,4*GE SFP ports,1*150W AC power)
               bname8031S5731S-H48T4S-A(537563),                     --S5731S-H48T4S-A(48*10/100/1000BASE-T ports,4*GE SFP ports,1*150W AC power)
               bname8031S1700-8-AC(537564),                                --S1700-8-AC(8 Ethernet 10/100/1000 ports,AC 110/220V,China Power Adapter) for V2R19C00
               bname8031S5731S-H24T4X-A(537565),                      --S5731S-H24T4X-A(24*10/100/1000BASE-T ports,4*10GE SFP+ ports,1*150W AC power)
               bname8031S5731S-H48T4X-A(537566),                      --S5731S-H48T4X-A(48*10/100/1000BASE-T ports,4*10GE SFP+ ports,1*150W AC power)
               bname8031S6730S-H24X6C-A(537567),                      --S6730S-H24X6C-A(24*10GE SFP+ ports,6*100GE QSFP28 ports,1*600W AC power)
               bname8031S1730S-H24T4S-A(537568),                       --S1730S-H24T4S-A(24*10/100/1000BASE-T ports, 4*GE SFP ports, AC 110/220V)
               bname8031S1730S-S24T4X-A(537569),                       --S1730S-S24T4X-A(24*10/100/1000BASE-T ports, 4*10GE SFP+ ports, AC 110/220V)
               bname8031S1730S-H48T4S-A(537570),                       --S1730S-H48T4S-A(48*10/100/1000BASE-T ports, 4*GE SFP ports, AC 110/220V)
               bname8031S5335-L48T4X-A(537571),                          --S5335-L48T4X-A(48*10/100/1000BASE-T ports, 4*10GE SFP+ ports, AC 110/220V)
               bname8031S1730S-S48P4S-A(537572),                       --S1730S-S48P4S-A(48*10/100/1000BASE-T ports,4*GE SFP ports,PoE+,1*1000W PoE AC power)
               bname8031S6730-H48X6C-K(537573),                         --S6730-H48X6C-K (48*10GE SFP+ ports, 6*40GE QSFP28 ports, optional license for upgrade to 6*100GE QSFP28, without power module) for V2R19C!0
               bname8031S6730-H24X6C-K(537574),                         --S6730-H24X6C-K (24*10GE SFP+ ports, 6*100GE QSFP28 ports, without power module) for V2R19C!0
               bname8031S5731-H48P4XC-K(537575),                        --S5731-H48P4XC-K(48*10/100/1000BASE-T ports, 4*10GE SFP+ ports, 1*expansion slot, PoE+, without power module) for V2R19C!0
               bname8031S5731-H24T4XC-K(537576),                        --S5731-H24T4XC-K (24*10/100/1000BASE-T ports, 4*10GE SFP+ ports, 1*expansion slot, without power module) for V2R19C!0
               bname8031S5731-H24P4XC-K(537577),                        --S5731-H24P4XC-K (24*10/100/1000BASE-T ports, 4*10GE SFP+ ports, 1*expansion slot, PoE+, without power module) for V2R19C!0
               bname8031S5732-H24S6Q-K(537578),                          --S5732-H24S6Q-K (20*GE SFP ports,4*10GE SFP+ ports,6*40GE QSFP ports,with Pluggable dual power module) for V2R19C!0
               bname8031S5732-H48S6Q-K(537579),                          --S5732-H48S6Q-K (44*GE SFP ports,4*10GE SFP+ ports,6*40GE QSFP ports,with pluggable dual power module) for V2R19C!0

               bnameS5736-S24UM4XC(537613), --S5736-S24UM4XC Base(24*100M/1G Ethernet ports,Optional RTU upgrade to 2.5/5/10G, 4*10GE SFP+ ports, 1*expansion slot, PoE++, without power module) for V2R20C00
               bnameS5336-S24UM4XC(537614), --S5336-S24UM4XC Base(24*100M/1G Ethernet ports,Optional RTU upgrade to 2.5/5/10G, 4*10GE SFP+ ports, 1*expansion slot, PoE++, without power module) for V2R20C00
               bnameS5736-S24T4XC(537615), --S5736-S24T4XC (24*10/100/1000BASE-T ports, 4*10GE SFP+ ports, 1*expansion slot, without power module) for V2R20C00
               bnameS5336-S24T4XC(537616), --S5336-S24T4XC (24*10/100/1000BASE-T ports, 4*10GE SFP+ ports, 1*expansion slot, without power module) for V2R20C00
               bnameS5735S-H24T4XC-A(537617), --S5735S-H24T4XC bundle(24*10/100/1000BASE-T ports, 4*10GE SFP+ ports, 1*expansion slot, one AC power module) for V2R20C00
               bnameS5736-S48T4XC(537618), --S5736-S48T4XC (48*10/100/1000BASE-T ports, 4*10GE SFP+ ports, 1*expansion slot, without power module) for V2R20C00
               bnameS5336-S48T4XC(537619), --S5336-S48T4XC (48*10/100/1000BASE-T ports, 4*10GE SFP+ ports, 1*expansion slot, without power module) for V2R20C00
               bnameS5735S-H48T4XC-A(537620), --S5735S-H48T4XC bundle(48*10/100/1000BASE-T ports, 4*10GE SFP+ ports, 1*expansion slot, one AC power module) for V2R20C00
               bnameS5736-S24U4XC(537621), --S5736-S24U4XC (24*10/100/1000BASE-T ports, 4*10GE SFP+ ports, 1*expansion slot, PoE++, without power module) for V2R20C00
               bnameS5336-S24U4XC(537622), --S5336-S24U4XC (24*10/100/1000BASE-T ports, 4*10GE SFP+ ports, 1*expansion slot, PoE++, without power module) for V2R20C00
               bnameS5735S-H24U4XC-A(537623), --S5735S-H24U4XC bundle(24*10/100/1000BASE-T ports, 4*10GE SFP+ ports, 1*expansion slot, PoE++, one AC power module) for V2R20C00
               bnameS5736-S48U4XC(537624), --S5736-S48U4XC (48*10/100/1000BASE-T ports, 4*10GE SFP+ ports, 1*expansion slot, PoE++, without power module) for V2R20C00
               bnameS5336-S48U4XC(537625), --S5336-S48U4XC (48*10/100/1000BASE-T ports, 4*10GE SFP+ ports, 1*expansion slot, PoE++, without power module) for V2R20C00
               bnameS5735S-H48U4XC-A(537626), --S5735S-H48U4XC bundle(48*10/100/1000BASE-T ports, 4*10GE SFP+ ports, 1*expansion slot, PoE++, one AC power module) for V2R20C00
               bnameS5736-S24S4XC(537627), --S5736-S24S4XC (24*GE SFP ports, 4*10GE SFP+ ports, 1*expansion slot, without power module) for V2R20C00
               bnameS5336-S24S4XC(537628), --S5336-S24S4XC (24*GE SFP ports, 4*10GE SFP+ ports, 1*expansion slot, without power module) for V2R20C00
               bnameS5735S-H24S4XC-A(537629), --S5735S-H24S4XC bundle(24*GE SFP ports, 4*10GE SFP+ ports, 1*expansion slot, one AC power module) for V2R20C00
               bnameS5736-S48S4XC(537630), --S5736-S48S4XC (48*GE SFP ports, 4*10GE SFP+ ports, 1*expansion slot, without power module) for V2R20C00
               bnameS5336-S48S4XC(537631), --S5336-S48S4XC (48*GE SFP ports, 4*10GE SFP+ ports, 1*expansion slot, without power module) for V2R20C00
               bnameS5336-S48S4X-A(537632), --S5336-S48S4X-A Base(48*GE SFP ports,Optional RTU upgrade to 10G, 4*10GE SFP+ ports, AC power, front access) for V2R20C00
               bnameS5336-S48S4X-D(537633), --S5336-S48S4X-D Base(48*GE SFP ports,Optional RTU upgrade to 10G, 4*10GE SFP+ ports, DC power, front access) for V2R20C00
               bnameS6720S-S52X-A(537634), --S6720S-S52X-A(52*10GE SFP+ ports, AC power, front access) for V2R20C00
               bnameS6720S-S24S28X-A(537635), --S6720S-S24S28X-A(24*GE SFP ports,28*10GE SFP+ ports, AC power, front access) for V2R20C00
               bnameS5720-52X-LI-48S-AC1(537636), --S5720-52X-LI-48S-AC1 (46*GE SFP ports, 2 of which are 10/100/1000BASE-T + SFP combo ports, 4*10GE SFP+ ports, AC power supply) for V2R20C00
               bnameS5720-52X-LI-48S-DC1(537637), --S5720-52X-LI-48S-DC1 (46*GE SFP ports, 2 of which are 10/100/1000BASE-T + SFP combo ports, 4*10GE SFP+ ports, DC power supply) for V2R20C00
               bnameS5720-52X-LI-24S-AC1(537638), --S5720-52X-LI-24S-AC1 (24*FE SFP ports,22*GE SFP ports, 2 of which are 10/100/1000BASE-T + SFP combo ports, 4*10GE SFP+ ports, AC power supply) for V2R20C00
               bnameS5720S-52X-LI-24S-AC1(537639), --S5720S-52X-LI-24S-AC1 (24*FE SFP ports,22*GE SFP ports, 2 of which are 10/100/1000BASE-T + SFP combo ports, 4*10GE SFP+ ports, AC power supply) for V2R20C00
               bnameS5320-52X-LI-48S-AC1(537640), --S5320-52X-LI-48S-AC1 (46*GE SFP ports, 2 of which are 10/100/1000BASE-T + SFP combo ports, 4*10GE SFP+ ports, AC power supply) for V2R20C00
               bnameS5320-52X-LI-48S-DC1(537641), --S5320-52X-LI-48S-DC1 (46*GE SFP ports, 2 of which are 10/100/1000BASE-T + SFP combo ports, 4*10GE SFP+ ports, DC power supply) for V2R20C00
               bnameS5320-52X-LI-24S-AC1(537642), --S5320-52X-LI-24S-AC1 (24*FE SFP ports,22*GE SFP ports, 2 of which are 10/100/1000BASE-T + SFP combo ports, 4*10GE SFP+ ports, AC power supply) for V2R20C00
               bnameS5735-L8T4X-A1(537644), --S5735-L8T4X-A1 (8*10/100/1000BASE-T ports, 4*10GE SFP+ ports, AC power) for V2R20C10
               bnameS5335-L8T4X-A1(537645), --S5335-L8T4X-A1 (8*10/100/1000BASE-T ports, 4*10GE SFP+ ports, AC power) for V2R20C10
               bnameS5735-L8T4S-A1(537646), --S5735-L8T4S-A1 (8*10/100/1000BASE-T ports, 4*GE SFP ports, AC power) for V2R20C10
               bnameS5735S-L8T4S-A1(537647), --S5735S-L8T4S-A1 (8*10/100/1000BASE-T ports, 4*GE SFP ports, AC power) for V2R20C10
               bnameS1730S-S8T4S-A1(537648), --S1730S-S8T4S-A1 (8*10/100/1000BASE-T ports, 4*GE SFP ports, AC power) for V2R20C10
               bnameS2730S-S8FT4S-A(537649), --S2730S-S8FT4S-A (4*10/100BASE-TX ports, 4*10/100/1000BASE-T ports, 4*GE SFP ports, AC power) for V2R20C10
               bnameS500-8T4S(537650), --S500-8T4S (8*10/100/1000BASE-T ports, 4*GE SFP ports, AC power) for V2R20C10
               bnameS300-8T4S(537651), --S300-8T4S (8*10/100/1000BASE-T ports, 4*GE SFP ports, AC power) for V2R20C10
               bnameS200-8T4S(537652), --S200-8T4S (8*10/100/1000BASE-T ports, 4*GE SFP ports, AC power) for V2R20C10
               bnameS5735-L8P4X-A1(537653), --S5735-L8P4X-A1 (8*10/100/1000BASE-T ports, 4*10GE SFP+ ports, PoE+, AC power) for V2R20C10
               bnameS5735-L8T4X-D1(537654), --S5735-L8T4X-D1 (8*10/100/1000BASE-T ports, 4*10GE SFP+ ports, DC power) for V2R20C10
               bnameS5335-L8P4X-A1(537655), --S5335-L8P4X-A1 (8*10/100/1000BASE-T ports, 4*10GE SFP+ ports, PoE+, AC power) for V2R20C10
               bnameS5335-L8T4X-D1(537656), --S5335-L8T4X-D1 (8*10/100/1000BASE-T ports, 4*10GE SFP+ ports, DC power) for V2R20C10
               bnameS5735-L8P4S-A1(537657), --S5735-L8P4S-A1 (8*10/100/1000BASE-T ports, 4*GE SFP ports, PoE+, AC power) for V2R20C10
               bnameS5735S-L8P4S-A1(537658), --S5735S-L8P4S-A1 (8*10/100/1000BASE-T ports, 4*GE SFP ports, PoE+, AC power) for V2R20C10
               bnameS1730S-S8P4S-A1(537659), --S1730S-S8P4S-A1 (8*10/100/1000BASE-T ports, 4*GE SFP ports, PoE+, AC power) for V2R20C10
               bnameS2730S-S8FP4S-A(537660), --S2730S-S8FP4S-A (4*10/100BASE-TX ports, 4*10/100/1000BASE-T ports, 4*GE SFP ports, PoE+, AC power) for V2R20C10
               bnameS500-8P4S(537661), --S500-8P4S (8*10/100/1000BASE-T ports, 4*GE SFP ports, PoE+, AC power) for V2R20C10
               bnameS300-8P4S(537662), --S300-8P4S (8*10/100/1000BASE-T ports, 4*GE SFP ports, PoE+, AC power) for V2R20C10
               bnameS200-8P4S(537663), --S200-8P4S (8*10/100/1000BASE-T ports, 4*GE SFP ports, PoE+, AC power) for V2R20C10
               bnameS5735-L24T4X-A1(537664), --S5735-L24T4X-A1 (24*10/100/1000BASE-T ports, 4*10GE SFP+ ports, AC power) for V2R20C10
               bnameS5335-L24T4X-A1(537665), --S5335-L24T4X-A1 (24*10/100/1000BASE-T ports, 4*10GE SFP+ ports, AC power, front access) for V2R20C10
               bnameS5735-L24T4X-D1(537666), --S5735-L24T4X-D1 (24*10/100/1000BASE-T ports, 4*10GE SFP+ ports, DC power) for V2R20C10
               bnameS5335-L24T4X-D1(537667), --S5335-L24T4X-D1 (24*10/100/1000BASE-T ports, 4*10GE SFP+ ports, DC power, front access) for V2R20C10
               bnameS5735-L24T4S-A1(537668), --S5735-L24T4S-A1 (24*10/100/1000BASE-T ports, 4*GE SFP ports, AC power) for V2R20C10
               bnameS5735S-L24T4S-A1(537669), --S5735S-L24T4S-A1 (24*10/100/1000BASE-T ports, 4*GE SFP ports, AC power) for V2R20C10
               bnameS1730S-S24T4S-A1(537670), --S1730S-S24T4S-A1 (24*10/100/1000BASE-T ports, 4*GE SFP ports, AC power) for V2R20C10
               bnameS2730S-S24FT4S-A(537671), --S2730S-S24FT4S-A (12*10/100BASE-TX ports, 12*10/100/1000BASE-T ports, 4*GE SFP ports, AC power) for V2R20C10
               bnameS5735S-L24T4X-A1(537672), --S5735S-L24T4X-A1 (24*10/100/1000BASE-T ports, 4*XGE SFP+ ports, AC power) for V2R20C10
               bnameS1730S-S24T4X-A1(537673), --S1730S-S24T4X-A1 (24*10/100/1000BASE-T ports, 4*XGE SFP+ ports, AC power) for V2R20C10
               bnameS500-24T4S(537674), --S500-24T4S (24*10/100/1000BASE-T ports, 4*GE SFP ports, AC power) for V2R20C10
               bnameS300-24T4S(537675), --S300-24T4S (24*10/100/1000BASE-T ports, 4*GE SFP ports, AC power) for V2R20C10
               bnameS200-24T4S(537676), --S200-24T4S (24*10/100/1000BASE-T ports, 4*GE SFP ports, AC power) for V2R20C10
               bnameS2730S-S16FT4S-A(537677), --S2730S-S16FT4S-A (8*10/100BASE-TX ports, 8*10/100/1000BASE-T ports, 4*GE SFP ports, AC power) for V2R20C10
               bnameS500-16T4S(537678), --S500-16T4S (16*10/100/1000BASE-T ports, 4*GE SFP ports, AC power) for V2R20C10
               bnameS300-16T4S(537679), --S300-16T4S (16*10/100/1000BASE-T ports, 4*GE SFP ports, AC power) for V2R20C10
               bnameS5735-L24P4X-A1(537680), --S5735-L24P4X-A1 (24*10/100/1000BASE-T ports, 4*10GE SFP+ ports, PoE+, AC power) for V2R20C10
               bnameS5335-L24P4X-A1(537681), --S5335-L24P4X-A1 (24*10/100/1000BASE-T ports, 4*10GE SFP+ ports, PoE+, AC power) for V2R20C10
               bnameS5735-L24P4S-A1(537682), --S5735-L24P4S-A1 (24*10/100/1000BASE-T ports, 4*GE SFP ports, PoE+, AC power) for V2R20C10
               bnameS5735S-L24P4S-A1(537683), --S5735S-L24P4S-A1 (24*10/100/1000BASE-T ports, 4*GE SFP ports, PoE+, AC power) for V2R20C10
               bnameS1730S-S24P4S-A1(537684), --S1730S-S24P4S-A1 (24*10/100/1000BASE-T ports, 4*GE SFP ports, PoE+, AC power) for V2R20C10
               bnameS2730S-S24FP4S-A(537685), --S2730S-S24FP4S-A (12*10/100BASE-TX ports, 12*10/100/1000BASE-T ports, 4*GE SFP ports, PoE+, AC power) for V2R20C10
               bnameS500-24P4S(537686), --S500-24P4S (24*10/100/1000BASE-T ports, 4*GE SFP ports, PoE+, AC power) for V2R20C10
               bnameS300-24P4S(537687), --S300-24P4S (24*10/100/1000BASE-T ports, 4*GE SFP ports, PoE+, AC power) for V2R20C10
               bnameS200-24P4S(537688), --S200-24P4S (24*10/100/1000BASE-T ports, 4*GE SFP ports, PoE+, AC power) for V2R20C10
               bnameS5735S-L24P4X-A1(537689), --S5735S-L24P4X-A1 (24*10/100/1000BASE-T ports, 4*10GE SFP+ ports, PoE+, AC power) for V2R20C10
               bnameS2730S-S16FP4S-A(537690), --S2730S-S16FP4S-A1 (8*10/100BASE-TX ports, 8*10/100/1000BASE-T ports,, 4*GE SFP ports, PoE+, AC power) for V2R20C10
               bnameS500-16P4S(537691), --S500-16P4S (16*10/100/1000BASE-T ports, 4*GE SFP ports, PoE+, AC power) for V2R20C10
               bnameS300-16P4S(537692), --S500-16P4S (16*10/100/1000BASE-T ports, 4*GE SFP ports, PoE+, AC power) for V2R20C10
               bnameS5735-L48T4X-A1(537693), --S5735-L48T4X-A1 (48*10/100/1000BASE-T ports, 4*10GE SFP+ ports, AC power) for V2R20C10
               bnameS5335-L48T4X-A1(537694), --S5335-L48T4X-A1 (48*10/100/1000BASE-T ports, 4*10GE SFP+ ports, AC power) for V2R20C10
               bnameS5735-L48T4S-A1(537695), --S5735-L48T4S-A1 (48*10/100/1000BASE-T ports, 4*GE SFP ports, AC power) for V2R20C10
               bnameS5735S-L48T4S-A1(537696), --S5735S-L48T4S-A1 (48*10/100/1000BASE-T ports, 4*GE SFP ports, AC power) for V2R20C10
               bnameS1730S-S48T4S-A1(537697), --S1730S-S48T4S-A1 (48*10/100/1000BASE-T ports, 4*GE SFP ports, AC power) for V2R20C10
               bnameS2730S-S48FT4S-A(537698), --S2730S-S48FT4S-A (24*10/100BASE-TX ports, 24*10/100/1000BASE-T ports, 4*GE SFP ports, AC power) for V2R20C10
               bnameS5735S-L48T4X-A1(537699), --S5735S-L48T4X-A1 (48*10/100/1000BASE-T ports, 4*10GE SFP+ ports, AC power) for V2R20C10
               bnameS1730S-S48T4X-A1(537700), --S1730S-S48T4X-A1 (48*10/100/1000BASE-T ports, 4*10GE SFP+ ports, AC power) for V2R20C10
               bnameS500-48T4S(537701), --S500-48T4S (48*10/100/1000BASE-T ports, 4*GE SFP ports, AC power) for V2R20C10
               bnameS300-48T4S(537702), --S300-48T4S (48*10/100/1000BASE-T ports, 4*GE SFP ports, AC power) for V2R20C10
               bnameS200-48T4S(537703), --S200-48T4S (48*10/100/1000BASE-T ports, 4*GE SFP ports, AC power) for V2R20C10
               bnameS5735-L48P4X-A1(537704), --S5735-L48P4X-A1 (48*10/100/1000BASE-T ports, 4*10GE SFP+ ports, PoE+, AC power) for V2R20C10
               bnameS5335-L48P4X-A1(537705), --S5335-L48P4X-A1 (48*10/100/1000BASE-T ports, 4*10GE SFP+ ports, PoE+, AC power) for V2R20C10
               bnameS5735-L48P4S-A1(537706), --S5735-L48P4S-A1 (48*10/100/1000BASE-T ports, 4*GE SFP ports, PoE+, AC power) for V2R20C10
               bnameS5735S-L48P4S-A1(537707), --S5735S-L48P4S-A1 (48*10/100/1000BASE-T ports, 4*GE SFP ports, PoE+, AC power) for V2R20C10
               bnameS5735S-L48P4X-A1(537708), --S5735S-L48P4X-A1 (48*10/100/1000BASE-T ports, 4*10GE SFP+ ports, PoE+, AC power) for V2R20C10
               bnameS1730S-S48P4S-A1(537709), --S1730S-S48P4S-A1 (48*10/100/1000BASE-T ports, 4*GE SFP ports, PoE+, AC power) for V2R20C10
               bnameS2730S-S48FP4S-A(537710), --S2730S-S48FP4S-A (24*10/100BASE-TX ports, 24*10/100/1000BASE-T ports, 4*GE SFP ports, PoE+, AC power) for V2R20C10
               bnameS5336-S24S4X-A(537711), --S5336-S24S4X-A base (24*GE SFP ports, optional RTU upgrade to 10G, 4*10GE SFP+ ports, AC power supply, front access) for V2R20C10
               bnameS5336-S24S4X-D(537712), --S5336-S24S4X-D base (24*GE SFP ports, optional RTU upgrade to 10G, 4*10GE SFP+ ports, AC power supply, front access) for V2R20C10
               bnameS5735-L32ST4X-A1(537715), --S5735-L32ST4X-A1 (24*GE SFP ports, 8*10/100/1000BASE-T ports, 4*10GE SFP+ ports, AC power) for V2R20C10
               bnameS5335-L32ST4X-A1(537716), --S5335-L32ST4X-A1 (24*GE SFP ports, 8*10/100/1000BASE-T ports, 4*10GE SFP+ ports, AC power, front access) for V2R20C10
               bnameS5735S-L32ST4X-A1(537717), --S5735S-L32ST4X-A1 (24*GE SFP ports, 8*10/100/1000BASE-T ports, 4*10GE SFP+ ports, AC power) for V2R20C10
               bnameS500-32ST4X(537718), --S500-32ST4X (24*GE SFP ports, 8*10/100/1000BASE-T ports, 4*10GE SFP+ ports, AC power) for V2R20C10
               bnameS5735-L32ST4X-D1(537719), --S5735-L32ST4X-V2 (24*GE SFP ports, 8*10/100/1000BASE-T ports, 4*10GE SFP+ ports, DC power) for V2R20C10
               bnameS5335-L32ST4X-D1(537720), --S5335-L32ST4X-V2 (24*GE SFP ports, 8*10/100/1000BASE-T ports, 4*10GE SFP+ ports, DC power, front access) for V2R20C10
               bnameS5700W-H24T4XC1(537713), --S5700W-H24T4XC1 (24*10/100/1000BASE-T ports, 4*10GE SFP+ ports, 1*expansion slot, without power module) for V2R20C10
               bnameS5700W-H48T4XC1(537714), --S5700W-H48T4XC1 (48*10/100/1000BASE-T ports, 4*10GE SFP+ ports, 1*expansion slot, without power module) for V2R20C10
               bname8031S5735S-H24T4X-A(537726), --S5735S-H24T4X bundle(24*10/100/1000BASE-T ports, 4*10GE SFP+ ports, 1*AC power module) for V2R20C30
               bname8031S5735S-H48T4X-A(537727), --S5735S-H48T4X bundle (48*10/100/1000BASE-T ports, 4*10GE SFP+ ports, 1*AC power module) for V2R20C30
               bname8031S5735S-H24U4X-A(537728), --S5735S-H24U4X bundle (24*10/100/1000BASE-T ports, 4*10GE SFP+ ports, PoE++, 1*AC power module) for V2R20C30
               bname8031S5735S-H48U4X-A(537729), --S5735S-H48U4X bundle (48*10/100/1000BASE-T ports, 4*10GE SFP+ ports, PoE++, 1*AC power module) for V2R20C30
               bname8031S5735S-H24S4X-A(537730), --S5735S-H24S4X bundle (24*GE SFP ports, 4*10GE SFP+ ports, 1*AC power module) for V2R20C30
               bname8031S5735S-H48S4X-A(537731), --S5735S-H48S4X bundle (48*GE SFP ports, 4*10GE SFP+ ports, 1*AC power module) for V2R20C30
               bname8031S5735S-H48S4XC-A(537732), --S5735S-H48S4XC bundle (48*GE SFP ports, 4*10GE SFP+ ports, 1*expansion slot, 1*AC power module) for V2R20C30
               bname8031S5735R-8P4S(537733), --S5735R-8P4S (8*10/100/1000BASE-T ports, 4*GE SFP ports, PoE+, AC power) for V2R20C30
               bname8031S5735R-24T4X(537734), --S5735R-24T4X (24*10/100/1000BASE-T ports, 4*10GE SFP+ ports, AC power) for V2R20C30
               bname8031S5735R-24T4S(537735), --S5735R-24T4S (24*10/100/1000BASE-T ports, 4*GE SFP ports, AC power) for V2R20C30
               bname8031S5735R-24P4X(537736), --S5735R-24P4X (24*10/100/1000BASE-T ports, 4*10GE SFP+ ports, PoE+, AC power) for V2R20C30
               bname8031S5735R-24P4S(537737), --S5735R-24P4S (24*10/100/1000BASE-T ports, 4*GE SFP ports, PoE+, AC power) for V2R20C30
               bname8031S5735R-48T4S(537738), --S5735R-48T4S (48*10/100/1000BASE-T ports, 4*GE SFP ports, AC power) for V2R20C30
               bname8031S5736-S48S4X-A(537739), --S5736-S48S4X-A base (48*GE SFP ports, optional RTU upgrade to 10G, 4*10GE SFP+ ports, AC power supply, front access) for V2R20C30
               bname8031S5736-S48S4X-D(537740), --S5736-S48S4X-D base (48*GE SFP ports, optional RTU upgrade to 10G, 4*10GE SFP+ ports, DC power supply, front access) for V2R20C30
               bname8031S5735-L8T4X-IA1(537741), --S5735-L8T4X-IA1 (8*10/100/1000BASE-T ports, 4*10GE SFP+ ports, AC power) for V2R21C00
               bname8031S5735-L8P4X-IA1(537742), --S5735-L8P4X-IA1 (8*10/100/1000BASE-T ports, 4*10GE SFP+ ports, PoE+, AC power) for V2R21C00
               bname8031S5735-L24T4X-IA1(537743), --S5735-L24T4X-IA1 (24*10/100/1000BASE-T ports, 4*10GE SFP+ ports, AC power) for V2R21C00
               bname8031S5735-L8T4S-QA1(537744), --S5735-L8T4S-QA1 (8*10/100/1000BASE-T ports, 4*GE SFP ports, AC power, Fanless) for V2R21C00
               bname8031S5735-L24T4X-QA1(537745), --S5735-L24T4X-QA1 (24*10/100/1000BASE-T ports, 4*10GE SFP+ ports, AC power, Fanless) for V2R21C00
               bname8031S5735-L24T4S-QA1(537746), --S5735-L24T4S-QA1 (24*10/100/1000BASE-T ports, 4*GE SFP ports, AC power, Fanless) for V2R21C00
               bname8031S6730-H48X6C-V2(537724), --S6730-H48X6C-V2(48*10GE SFP+ ports, 6*40GE QSFP28 ports, optional license for upgrade to 6*100GE QSFP28, without power module) for V6R21C00
               bname8031S6730-H24X6C-V2(537725), --S6730-H24X6C-V2(24*10GE SFP+ ports, 6*40GE QSFP28 ports, optional license for upgrade to 6*100GE QSFP28, without power module) for V6R21C00
               bname8031S6730-H48X6C-TV2(537747), --S6730-H48X6C-TV2(48*10GE SFP+ ports, 6*40GE QSFP28 ports, optional license for upgrade to 6*100GE QSFP28, without power module) for V6R21C10(TPM)
               bname8031S6730-H24X6C-TV2(537748), --S6730-H24X6C-TV2(24*10GE SFP+ ports, 6*40GE QSFP28 ports, optional license for upgrade to 6*100GE QSFP28, without power module) for V6R21C10(TPM)
               bname8031S6730-H48Y6C-V2(537749),  --S6730-H48Y6C-V2(48*25GE SFP28 ports, 6*100GE QSFP28 ports, without power module) for V6R21C10
               bname8031S6730-H48Y6C-TV2(537750), --S6730-H48Y6C-TV2(48*25GE SFP28 ports, 6*100GE QSFP28 ports, without power module) for V6R21C10(TPM)
               bname8031S5735-L8P4S-QA1(537751), --S5735-L8P4S-QA1 (8*10/100/1000BASE-T ports, 4*GE SFP ports, PoE+, AC power, Fanless) for V2R21C00

               bname8031S5735-L8T4S-QA2(537771),   --S5735-L8T4S-QA2 (8*10/100/1000BASE-T ports, 4*GE SFP ports, AC power) for V2R21C01
               bname8031S5735S-L8T4S-QA2(537772),  --S5735S-L8T4S-QA2 (8*10/100/1000BASE-T ports, 4*GE SFP ports, AC power) for V2R21C01
               bname8031S300-8T4S-QA2(537773),     --S300-8T4S-QA2 (8*10/100/1000BASE-T ports, 4*GE SFP ports, AC power) for V2R21C01
               bname8031S5735S-L8T4S-MA2(537774),  --S5735S-L8T4S-MA2 (8*10/100/1000BASE-T ports, 4*GE SFP ports, AC power) for V2R21C01
               bname8031S1730S-S8T4S-QA2(537775),  --S1730S-S8T4S-QA2 (8*10/100/1000BASE-T ports, 4*GE SFP ports, AC power) for V2R21C01
               bname8031S200-8T4S-QA2(537776),     --S200-8T4S-QA2 (8*10/100/1000BASE-T ports, 4*GE SFP ports, AC power) for V2R21C01
               bname8031S5735-L8P4S-QA2(537777),   --S5735-L8P4S-QA2 (8*10/100/1000BASE-T ports, 4*GE SFP ports, PoE+, AC power) for V2R21C01
               bname8031S5735S-L8P4S-QA2(537778),  --S5735S-L8P4S-QA2 (8*10/100/1000BASE-T ports, 4*GE SFP ports, PoE+, AC power) for V2R21C01
               bname8031S300-8P4S-QA2(537779),     --S300-8P4S-QA2 (8*10/100/1000BASE-T ports, 4*GE SFP ports, PoE+, AC power) for V2R21C01
               bname8031S5735S-L8P4S-MA2(537780),  --S5735S-L8P4S-MA2 (8*10/100/1000BASE-T ports, 4*GE SFP ports, PoE+, AC power) for V2R21C01
               bname8031S1730S-S8P4S-QA2(537781),  --S1730S-S8P4S-QA2 (8*10/100/1000BASE-T ports, 4*GE SFP ports, PoE+, AC power) for V2R21C01
               bname8031S200-8P4S-QA2(537782),     --S200-8P4S-QA2 (8*10/100/1000BASE-T ports, 4*GE SFP ports, PoE+, AC power) for V2R21C01
               bname8031S5735-L24T4X-QA2(537783),  --S5735-L24T4X-QA2 (24*10/100/1000BASE-T ports, 4*10GE SFP+ ports, AC power) for V2R21C01
               bname8031S5735S-L24T4X-QA2(537784), --S5735S-L24T4X-QA2 (24*10/100/1000BASE-T ports, 4*10GE SFP+ ports, AC power) for V2R21C01
               bname8031S1730S-S24T4X-QA2(537785), --S1730S-S24T4X-QA2 (24*10/100/1000BASE-T ports, 4*10GE SFP+ ports, AC power) for V2R21C01
               bname8031S5735-L24T4S-QA2(537786),  --S5735-L24T4S-QA2 (24*10/100/1000BASE-T ports, 4*GE SFP ports, AC power) for V2R21C01
               bname8031S5735S-L24T4S-QA2(537787), --S5735S-L24T4S-QA2 (24*10/100/1000BASE-T ports, 4*GE SFP ports, AC power) for V2R21C01
               bname8031S5735S-L24T4S-MA2(537788), --S5735S-L24T4S-MA2 (24*10/100/1000BASE-T ports, 4*GE SFP ports, AC power) for V2R21C01
               bname8031S1730S-S24T4S-QA2(537789), --S1730S-S24T4S-QA2 (24*10/100/1000BASE-T ports, 4*GE SFP ports, AC power) for V2R21C01
               bname8031S300-24T4S-QA2(537790),    --S300-24T4S-QA2 (24*10/100/1000BASE-T ports, 4*GE SFP ports, AC power) for V2R21C01
               bname8031S200-24T4S-QA2(537791),    --S200-24T4S-QA2 (24*10/100/1000BASE-T ports, 4*GE SFP ports, AC power) for V2R21C01
               bname8031S5735-L24P4X-A2(537794),   --S5735-L24P4X-A2 (24*10/100/1000BASE-T ports, 4*10GE SFP+ ports, PoE+, AC power) for V2R21C01
               bname8031S5735S-L24P4X-A2(537795),  --S5735S-L24P4X-A2 (24*10/100/1000BASE-T ports, 4*10GE SFP+ ports, PoE+, AC power) for V2R21C01
               bname8031S1730S-S24P4X-A2(537796),  --S1730S-S24P4X-A2 (24*10/100/1000BASE-T ports, 4*10GE SFP+ ports, PoE+, AC power) for V2R21C01
               bname8031S5735-L24P4S-A2(537797),   --S5735-L24P4S-A2 (24*10/100/1000BASE-T ports, 4*GE SFP ports, PoE+, AC power) for V2R21C01
               bname8031S5735S-L24P4S-A2(537798),  --S5735S-L24P4S-A2 (24*10/100/1000BASE-T ports, 4*GE SFP ports, PoE+, AC power) for V2R21C01
               bname8031S5735S-L24P4S-MA2(537799), --S5735S-L24P4S-MA2 (24*10/100/1000BASE-T ports, 4*GE SFP ports, PoE+, AC power) for V2R21C01
               bname8031S1730S-S24P4S-A2(537800),  --S1730S-S24P4S-A2 (24*10/100/1000BASE-T ports, 4*GE SFP ports, PoE+, AC power) for V2R21C01
               bname8031S300-24P4S-A2(537801),     --S300-24P4S-A2 (24*10/100/1000BASE-T ports, 4*GE SFP ports, PoE+, AC power) for V2R21C01
               bname8031S200-24P4S-A2(537802),     --S200-24P4S-A2 (24*10/100/1000BASE-T ports, 4*GE SFP ports, PoE+, AC power) for V2R21C01
               bname8031S5700W-S24P4X1(537803), --S5700W-S24P4X1 (24*10/100/1000BASE-T ports,4*10GE SFP+ ports,PoE+, without power module) for V2R21C00
               bname8031S5700W-S48P4X1(537804), --S5700W-S48P4X1 (48*10/100/1000BASE-T ports,4*10GE SFP+ ports,PoE+,without power module) for V2R21C00
               bname8031S6700W-S24X6Q1(537805), --S6700W-S24X6Q1 (24*10GE SFP+ ports, 6*40GE QSFP ports, without power module) for V2R21C00
               bname8031S5700W-L24T4X-A1(537806), --S5700W-L24T4X-A1 (24*10/100/1000BASE-T ports, 4*10GE SFP+ ports, AC power) for V2R21C00
               bname8031S5700W-L48T4X-A1(537807), --S5700W-L48T4X-A1 (48*10/100/1000BASE-T ports, 4*10GE SFP+ ports, AC power) for V2R21C00
               bname8031S5735-S24T4X-X(537809),   --S5735-S24T4X-X (24*10/100/1000BASE-T ports, 4*10GE SFP+ ports, without power module) for V2R21C01
               bname8031S5735S-S24T4X-XA(537810), --S5735S-S24T4X-XA (24*10/100/1000BASE-T ports, 4*10GE SFP+ ports, 1*60W AC power module) for V2R21C01
               bname8031S6735-S48X6C(537767), --S6735-S48X6C(48 10 Gig SFP+,6 100 Gig QSFP28 interface,with 1 interface slot,without power module) for V2R21C01
               bname8031S6735S-S48X6C-A(537768), --S6735S-S48X6C Bundle(48 10 Gig SFP+,6 100 Gig QSFP28 interface,with 1 interface slot,with 600W AC power supply) for V2R21C01
               bname8031S6735-S24X6C(537769), --S6735-S24X6C Bundle(48 10 Gig SFP+,2 100 Gig QSFP28 interface,with 1 interface slot,without power module) for V2R21C01
               bname8031S6735S-S24X6C-A(537770), --S6735S-S24X6C Bundle(24 10 Gig SFP+,6 100 Gig QSFP28 interface,with 1 interface slot,with 600W AC power supply) for V2R21C01
               bname8031S5735S-H24S4X-MA(537811),  --S5735S-H24S4X-M bundle (24*GE SFP ports, 4*10GE SFP+ ports, 1*AC power module) for V2R21C01
               bname8031S5731-S48S4X-A(537752),  --S5731-S48S4X-A(48*GE SFP ports, 4*10GE SFP+ ports, AC power, front access) for V2R21C01
               bname8031S5731S-S48S4X-A1(537753),  --S5731S-S48S4X-A1(48*GE SFP ports, 12*10GE SFP+ ports, AC power, front access) for V2R21C01
               bname8031S5331-S48S4X-A(537754),  --S5331-S48S4X-A(48*GE SFP ports, 4*10GE SFP+ ports, AC power, front access) for V2R21C01
               bname8031S5331-S48S4X-D(537755),  --S5331-S48S4X-D(48*GE SFP ports, 4*10GE SFP+ ports, DC power, front access) for V2R21C01
               bname8031S5731-S48S4X(537756),  --S5731-S48S4X(48*GE SFP ports,  4*10GE SFP+ ports, without power module) for V2R21C01
               bname8031S5731S-S48S4X-A(537757),  --S5731S-S48S4X-A(48*GE SFP ports,  4*10GE SFP+ ports, with AC power supply) for V2R21C01
               bname8031S5331-S48S4X(537758),  --S5331-S48S4X(48*GE SFP ports,  4*10GE SFP+ ports, without power module) for V2R21C01
               bname8031S5731-S32ST4X-A(537759),  --S5731-S32ST4X-A(8*10/100/1000BASE-T ports, 24*GE SFP ports, 4*10GE SFP+ ports, AC power, front access) for V2R21C01
               bname8031S5731S-S32ST4X-A1(537760),  --S5731S-S32ST4X-A1(8*10/100/1000BASE-T ports, 24*GE SFP ports, 4*10GE SFP+ ports, AC power, front access) for V2R21C01
               bname8031S5731-S32ST4X-D(537761),  --S5731-S32ST4X-D(8*10/100/1000BASE-T ports, 24*GE SFP ports, 4*10GE SFP+ ports, DC power, front access) for V2R21C01
               bname8031S5331-S32ST4X-A(537762),  --S5331-S32ST4X-A(8*10/100/1000BASE-T ports, 24*GE SFP ports, 4*10GE SFP+ ports, AC power, front access) for V2R21C01
               bname8031S5331-S32ST4X-D(537763),  --S5331-S32ST4X-D(8*10/100/1000BASE-T ports, 24*GE SFP ports, 4*10GE SFP+ ports, DC power, front access) for V2R21C01
               bname8031S5731-S32ST4X(537764),  --S5731-S32ST4X(8*10/100/1000BASE-T ports, 24*GE SFP ports, 4*10GE SFP+ ports, without power module) for V2R21C01
               bname8031S5731S-S32ST4X-A(537765),  --S5731S-S32ST4X-A(8*10/100/1000BASE-T ports, 24*GE SFP ports, 4*10GE SFP+ ports, with AC power supply) for V2R21C01
               bname8031S5331-S32ST4X(537766),  --S5331-S32ST4X(8*10/100/1000BASE-T ports, 24*GE SFP ports, 4*10GE SFP+ ports, without power module) for V2R21C01
               bname8031S5700W-S32ST4X1(537808),  --S5700W-S32ST4X1 (24*GE SFP ports, 8*10/100/1000BASE-T ports, 4*10GE SFP+ ports, without power module) for V2R21C01
               bname8031S5731-H48HB4XZ(537812), --S5731-H48HB4XZ(44*Hybrid GE SFP ports, 4*Hybrid 10GE SFP+ ports, 4*10GE SFP+ ports, 1*expansion slot, PoE++, without power module) for V2R21C10
               bname8031S5731S-H48HB4XZ-A(537813), --S5731S-H48HB4XZ Bundle(44*Hybrid GE SFP ports, 4*Hybrid 10GE SFP+ ports, 4*10GE SFP+ ports, 1*expansion slot, PoE++, 1*AC power) for V2R21C10
               bname8031S5731-H24HB4XZ(537814), --S5731-H24HB4XZ(20*Hybrid GE SFP ports, 4*Hybrid 10GE SFP+ ports, 4*10GE SFP+ ports, 1*expansion slot, PoE++, without power module) for V2R21C10
               bname8031S5731S-H24HB4XZ-A(537815), --S5731S-H24HB4XZ Bundle(20*Hybrid GE SFP ports, 4*Hybrid 10GE SFP+ ports, 4*10GE SFP+ ports, 1*expansion slot, PoE++, 1*AC power) for V2R21C10
               bname8031S5731S-S48P4X-A1(537816), --S5731S-S48T4X Bundle(48*10/100/1000BASE-T ports, 4*10GE SFP+ ports, PoE+,single power, 1*AC power)for v2r21c10
               bname8031S5331-S48T4X(537818), --S5331-S48T4X (48*10/100/1000BASE-T ports, 4*10GE SFP+ ports, without power module)for v2r21c10
               bname8031S5731-S48T4X-A(537822), --S5731-S48T4X-A (48*10/100/1000BASE-T ports, 4*10GE SFP+ ports, AC power)for v2r21c10
               bname8031S5731S-S48T4X-A1(537823), --S5731S-S48T4X-A1 (48*10/100/1000BASE-T ports, 4*10GE SFP+ ports, AC power)for v2r21c10
               bname8031S5331-S48T4X-A(537824), --S5331-S48T4X-A (48*10/100/1000BASE-T ports, 4*10GE SFP+ ports, AC power)for v2r21c10
               bname8031S5731-S24T4X-A(537825), --S5731-S24T4X-A (24*10/100/1000BASE-T ports, 4*10GE SFP+ ports, AC power)for v2r21c10
               bname8031S5731S-S24T4X-A1(537826), --S5731S-S24T4X-A1 (24*10/100/1000BASE-T ports, 4*10GE SFP+ ports, AC power)for v2r21c10
               bname8031S5731-S24T4X-D(537827), --S5731-S24T4X-D (24*10/100/1000BASE-T ports, 4*10GE SFP+ ports, DC power)for v2r21c10
               bname8031S5331-S24T4X-A(537828), --S5331-S24T4X-A (24*10/100/1000BASE-T ports, 4*10GE SFP+ ports, AC power,front access)for v2r21c10
               bname8031S5331-S24T4X-D(537829), --S5331-S24T4X-D (24*10/100/1000BASE-T ports, 4*10GE SFP+ ports, DC power,front access)for v2r21c10
               bname8031S5731-S48P4X-A(537830), --S5731-S48P4X Bundle(48*10/100/1000BASE-T ports, 4*10GE SFP+ ports, PoE+,single power, 1*AC power)for v2r21c10
               bname8031S5331-S48P4X(537831), --S5331-S48P4X (48*10/100/1000BASE-T ports, 4*10GE SFP+ ports, PoE+, without power module)for v2r21c10
               bname8031S5331-S24P4X(537832), --S5331-S24P4X (24*10/100/1000BASE-T ports, 4*10GE SFP+ ports, PoE+, without power module)for v2r21c10
               bname8031S200-48T4X(537833), --S200-48T4X (48*10/100/1000BASE-T ports, 4*10GE SFP+ ports, AC power) for V2R21C10
               bname8031S200-48P4X(537834), --S200-48P4X (48*10/100/1000BASE-T ports, 4*10GE SFP+ ports, PoE+, AC power) for V2R21C10
               bname8031S200-32ST4X(537835), --S200-32ST4X (24*GE SFP ports, 8*10/100/1000BASE-T ports, 4*10GE SFP+ ports, AC power, front access) for V2R21C10
               bname8031S200-24T4X-QA2(537836), --S200-24T4X-QA2 (24*10/100/1000BASE-T ports, 4*10GE SFP+ ports, AC power) for V2R21C10
               bname8031S200-24P4X-A2(537837), --S200-24P4X-A2 (24*10/100/1000BASE-T ports, 4*10GE SFP+ ports, PoE+, AC power) for V2R21C10
               bname8031S600-S24S28X(537838), --S600-S24S28X (24*GE SFP ports, 28*10GE SFP+ ports, AC power supply, front access) for V2R21C10
               bname8031S6730-H28X6CZ-V2(537851), --S6730-H28X6C-V2 (28*10GE SFP+ ports, 6*100GE QSFP28, 1*expansion slot, without power module) for V6R22C00
               bname8031S6730-H28X6CZ-TV2(537852), --S6730-H28X6C-TV2 (28*10GE SFP+ ports, 6*100GE QSFP28, 1*expansion slot, HTM, without power module) for V6R22C00
               bname8031S5732-H24S4X6QZ-V2(537853), --S5732-H24S4X6QZ-V2 (24*GE SFP ports,4*10GE SFP+ ports,6*40GE QSFP ports, 1*expansion slot, without power module) for V6R22C00
               bname8031S5732-H24S4X6QZ-TV2(537854), --S5732-H24S4X6QZ-TV2 (24*GE SFP ports,4*10GE SFP+ ports,6*40GE QSFP ports, 1*expansion slot, HTM, without power module) for V6R22C00
               bname8031S5732-H48UM4Y2CZ-V2(537855), --S5732-H48UM4Y2CZ-V2 2.5G Bundle(48*100M/1G/2.5G Ethernet ports, Optional RTU upgrade to 5/10G, 4*25GE SFP28, 2*100GE QSFP28 ports, 1*expansion slot, PoE++, with AC power supply) for V6R22C00
               bname8031S5732-H48UM4Y2CZ-TV2(537856), --S5732-H48UM4Y2CZ-TV2 2.5G Bundle(48*100M/1G/2.5G Ethernet ports, Optional RTU upgrade to 5/10G, 4*25GE SFP28, 2*100GE QSFP28 ports, 1*expansion slot, PoE++, HTM, with AC power supply) for V6R22C00
               bname8031S5731-S24N4X2Q-A(537857), --S5731-S24N4X2Q-A(24*100M/1G/2.5G Ethernet ports, 4*10GE SFP+ ports, 2*40GE QSFP ports, AC power, front access)
               bname8031S5331-S24N4X2Q-A(537858), --S5331-S24N4X2Q-A(24*100M/1G/2.5G Ethernet ports, 4*10GE SFP+ ports, 2*40GE QSFP ports, AC power, front access)
               bname8031S5731S-S24N4X2Q-A1(537859), --S5731S-S24N4X2Q-A1(24*100M/1G/2.5G Ethernet ports, 4*10GE SFP+ ports, 2*40GE QSFP ports, AC power, front access)
               bname8031S5731-S24UN4X2Q(537860), --S5731-S24NU4X2Q (24*100M/1G/2.5G Ethernet ports, 4*10GE SFP+ ports, 2*40GE QSFP ports, without power module)
               bname8031S5731S-S24UN4X2Q(537861), --S5731S-S24NU4X2Q Bundle(24*100M/1G/2.5G/5G Ethernet ports, 4*10GE SFP+ ports or 2*40GE QSFP ports, with AC power supply)
               bname8031S5731-S24UR2Q(537862), --S5731-S24RU2Q (24*100M/1G/2.5G/5G Ethernet ports, 4*10GE SFP+ ports or 2*40GE QSFP ports, without power module)
               bname8031S5731S-S24UR2Q(537863), --S5731S-S24NU4X2Q Bundle(24*100M/1G/2.5G Ethernet ports, 4*10GE SFP+ ports, 2*40GE QSFP ports, with AC power supply)
               bname8031S5731-S8UM16UN2Q(537864), --S5731-S8UM16UN2Q (8*100M/1G/2.5G/5G/10G,16*100M/1G/2.5G Ethernet ports, 2*40GE QSFP ports, switch to 16*100M/1G/2.5G/5G/10G,8*100M/1G Ethernet ports, 4*10GE SFP+ ports, without power module)
               bname8031S5731S-S8UM16UN2Q(537865), --S5731-S8UM16UN2Q Bundle(8*100M/1G/2.5G/5G/10G,16*100M/1G/2.5G Ethernet ports, 2*40GE QSFP ports, switch to 16*100M/1G/2.5G/5G/10G,8*100M/1G Ethernet ports, 4*10GE SFP+ ports, with AC power supply)
               bname8031S5732-H48UM4Y2CZ-KV2(537866),  --S5732-H48UM4Y2CZ-KV2 for V6R22C00 
               bname8031S5732-H24UM4Y2CZ-V2(537867),   --S5732-H24UM4Y2CZ-V2  for V6R22C00
               bname8031S5732-H24UM4Y2CZ-TV2(537868),  --S5732-H24UM4Y2CZ-TV2 for V6R22C00
               bname8031S5732-H24UM4Y2CZ-KV2(537869),  --S5732-H24UM4Y2CZ-KV2 for V6R22C00
               bname8031S6730-H48X6CZ-V2(537870),      --S6730-H48X6CZ-V2     for V6R22C00
               bname8031S6730-H48X6CZ-TV2(537871),     --S6730-H48X6CZ-TV2    for V6R22C00
               bname8031S5732-H44S4X6QZ-V2(537872),    --S5732-H44S4X6QZ-V2   for V6R22C00
               bname8031S5732-H44S4X6QZ-TV2(537873),   --S5732-H44S4X6QZ-TV2  for V6R22C00
               bname8031S5735-L8T4X-QA-V2(537874),        --S5735-L8T4X-QA-V2   for V6R22C01
               bname8031S5735-L8T4S-A-V2(537875),         --S5735-L8T4S-A-V2    for V6R22C01
               bname8031S5735-L10T4X-A-V2(537876),        --S5735-L10T4X-A-V2   for V6R22C01
               bname8031S5735-L10T4X-TA-V2(537877),       --S5735-L10T4X-TA-V2  for V6R22C01
               bname8031S5335-L10T4X-A-V2(537878),        --S5335-L10T4X-A-V2   for V6R22C01
               bname8031S5735-L8P4X-QA-V2(537880),        --S5735-L8P4X-QA-V2   for V6R22C01
               bname8031S5735-L8P4S-A-V2(537881),         --S5735-L8P4S-A-V2    for V6R22C01
               bname8031S5735-L8P2T4X-A-V2(537882),        --S5735-L8P2T4X-A-V2   for V6R22C01
               bname8031S5735-L8P2T4X-TA-V2(537883),       --S5735-L8P2T4X-TA-V2  for V6R22C01
               bname8031S5335-L8P2T4X-A-V2(537884),        --S5335-L8P2T4X-A-V2   for V6R22C01
               bname8031S5335-L10T4X-D-V2(537885),        --S5335-L10T4X-D-V2   for V6R22C01
               bname8031S5735-L16T4X-QA-V2(537886),       --S5735-L16T4X-QA-V2  for V6R22C01
               bname8031S5735-L16T4S-A-V2(537887),        --S5735-L16T4S-A-V2   for V6R22C01
               bname8031S5335-L16T4X-A-V2(537888),        --S5335-L16T4X-A-V2   for V6R22C01
               bname8031S5735-L24T4X-QA-V2(537889),       --S5735-L24T4X-QA-V2  for V6R22C01
               bname8031S5735-L24T4S-A-V2(537890),        --S5735-L24T4S-A-V2   for V6R22C01
               bname8031S5735-L24T4XE-A-V2(537891),       --S5735-L24T4XE-A-V2  for V6R22C01
               bname8031S5335-L24T4XE-A-V2(537892),       --S5335-L24T4XE-A-V2  for V6R22C01
               bname8031S5735-L24T4XE-D-V2(537893),       --S5735-L24T4XE-D-V2  for V6R22C01
               bname8031S5335-L24T4XE-D-V2(537894),       --S5335-L24T4XE-D-V2  for V6R22C01
               bname8031S5735-L24T4XE-TA-V2(537895),      --S5735-L24T4XE-TA-V2  for V6R22C01
               bname8031S5735-S24T4XE-V2(537896),         --S5735-S24T4XE-V2    for V6R22C01
               bname8031S5335-S24T4XE-V2(537897),         --S5335-S24T4XE-V2    for V6R22C01
               bname8031S5735I-S24T4XE-V2(537898),        --S5335I-S24T4XE-V2   for V6R22C01
               bname8031S5735I-S24T4XE-T-V2(537899),      --S5335I-S24T4XE-T-V2 for V6R22C01
               bname8031S5735-L24P4S-A-V2(537900),        --S5735-L24P4S-A-V2   for V6R22C01
               bname8031S5735-L24P4XE-A-V2(537901),       --S5735-L24P4XE-A-V2  for V6R22C01
               bname8031S5735-L24P4XE-TA-V2(537902),      --S5735-L24P4XE-TA-V2 for V6R22C01
               bname8031S5335-L24P4XE-A-V2(537903),       --S5335-L24P4XE-A-V2  for V6R22C01
               bname8031S5735-S24P4XE-V2(537905),         --S5735-S24P4XE-V2    for V6R22C01
               bname8031S5335-S24P4XE-V2(537906),         --S5335-S24P4XE-V2    for V6R22C01
               bname8031S5735-L48T4S-A-V2(537907),        --S5735-L48T4S-A-V2   for V6R22C01
               bname8031S5735-L48T4XE-A-V2(537908),       --S5735-L48T4XE-A-V2  for V6R22C01
               bname8031S5335-L48T4XE-A-V2(537909),       --S5335-L48T4XE-A-V2  for V6R22C01
               bname8031S5735-L48T4XE-TA-V2(537910),      --S5735-L48T4XE-TA-V2 for V6R22C01
               bname8031S5735-L48T4XE-D-V2(537911),       --S5735-L48T4XE-D-V2  for V6R22C01
               bname8031S5735-S48T4XE-V2(537912),         --S5735-S48T4XE-V2    for V6R22C01
               bname8031S5335-S48T4XE-V2(537913),         --S5335-S48T4XE-V2    for V6R22C01
               bname8031S5735-L48LP4S-A-V2(537914),       --S5735-L48LP4S-A-V2  for V6R22C01
               bname8031S5735-L48LP4XE-A-V2(537915),      --S5735-L48LP4XE-A-V2 for V6R22C01
               bname8031S5735-L48P4XE-A-V2(537916),       --S5735-L48P4XE-A-V2  for V6R22C01
               bname8031S5735-S48P4XE-V2(537917),         --S5735-S48P4XE-V2    for V6R22C01
               bname8031S5335-S48P4XE-V2(537918),         --S5335-S48P4XE-V2    for V6R22C01
               bname8031S5735-S24U4XE-V2(537919),         --S5735-S24U4XE-V2    for V6R22C01
               bname8031S5335-S24U4XE-V2(537920),         --S5335-S24U4XE-V2    for V6R22C01
               bname8031S5735-S48U4XE-V2(537921),         --S5735-S48U4XE-V2    for V6R22C01
               bname8031S5335-S48U4XE-V2(537922),         --S5335-S48U4XE-V2    for V6R22C01
               bname8031S5735I-S24U4XE-V2(537923),        --S5735I-S24U4XE-V2   for V6R22C01
               bname8031S5735I-S24U4XE-T-V2(537924),      --S5735I-S24U4XE-T-V2 for V6R22C01
               bname8031S5735I-S8T4XN-V2(537925),         --S5735I-S8T4XN-V2    for V6R22C01
               bname8031S5735I-S8T4XN-T-V2(537926),       --S5735I-S8T4XN-T-V2  for V6R22C01
               bname8031S5735I-S8T4SN-V2(537927),         --S5735I-S8T4SN-V2    for V6R22C01
               bname8031S5735I-S8U4XN-V2(537928),         --S5735I-S8U4XN-V2    for V6R22C01
               bname8031S5735I-L8P4X-A-V2(537975),        --S5735I-L8P4X-A-V2     for V6R22C10
               bname8031S5735I-L10T4X-A-V2(537976),       --S5735I-L10T4X-A-V2    for V6R22C10
               bname8031S6330-H24X4Y(537977),             --S6330-H24X4Y    for V2R22C10
               bname8031S3710-H24T4S-A(537978),           --S3710-H24T4S-A       for V6R22C10
               bname8031S3710-H24P4S-A(537979),           --S3710-H24P4S-A       for V6R22C10
               bname8031S3710-H48T4S-A(537980),           --S3710-H48T4S-A       for V6R22C10
               bname8031S3710-H48LP4S-A(537981),          --S3710-H48LP4S-A      for V6R22C10
               bname8031S5331-S24T4X-A-V1(537982),        --S5331-S24T4X-A-V1    for V6R22C10
               bname8031S5331-H24P4XC-V1(537983),         --S5331-H24P4XC-V1     for V6R22C10
               bname8031S5331-H48T4XC-V1(537984),         --S5331-H48T4XC-V1     for V6R22C10
               bname8031S310-24P4S(537985),               --S310-24P4S           for V6R22C10
               bname8031S310-24T4S(537986),               --S310-24T4S           for V6R22C10
               bname8031S310-48T4S(537987),               --S310-48T4S           for V6R22C10
               bname8031S5331-S24S8T4X-A(537988),         --S5331-S24S8T4X-A for V2R22C10
               bname8031S5331-S24S8T4X-D(537989),         --S5331-S24S8T4X-D for V2R22C10
               bname8031S5755-H48T4Y2CZ(537991),           --S5755-H48T4Y2CZ
               bname8031S5755-H48P4Y2CZ(537992),           --S5755-H48P4Y2CZ
               bname8031S5755-H48U4Y2CZ(537993),           --S5755-H48U4Y2CZ
               bname8031S5755-H24T4Y2CZ(537994),           --S5755-H24T4Y2CZ
               bname8031S5755-H24P4Y2CZ(537995),           --S5755-H24P4Y2CZ
               bname8031S5755-H24U4Y2CZ(537996),           --S5755-H24U4Y2CZ
               bname8031S5755-H24UTM4X4Y2C(537997),        --S5755-H24UTM4X4Y2C
               bname8031S5755-H48UTM4X4Y2C(537998),        --S5755-H48UTM4X4Y2C
               bname8031S5755-H24N4Y-A(537999),            --S5755-H24N4Y-A
               bname8031S5355-H24N4Y-A(538000),            --S5355-H24N4Y-A
               bname8031S5755-H48N4Y-A(538001),            --S5755-H48N4Y-A
               bname8031S5355-H48N4Y-A(538002),            --S5355-H48N4Y-A
               bname8031S5755-H24UN4Y2CZ(538003),          --S5755-H24UN4Y2CZ
               bname8031S5755-H48UN4Y2CZ(538004),          --S5755-H48UN4Y2CZ
               bname8031S5735-L24ST4XE-A-V2(538005),       --S5735-L24ST4XE-A-V2
               bname8031S5735-L48S4XE-A-V2(538006),        --S5735-L48S4XE-A-V2
               bname8031S5331-S32ST4X-A-V1(538008),        --S5331-S32ST4X-A-V1
               bname8031S5335-L48S4X-A-V2(538009),         --S5335-L48S4X-A-V2
               bname8031S5735-S48S4XE-V2(538011),          --S5735-S48S4XE-V2
               bname8031S5335-S48S4X-V2(538013),           --S5335-S48S4X-V2
               bname8031S5331-S48S4X-V1(538014),           --S5331-S48S4X-V1
               bname8031S5735-L14P2S-QA-V2(538015),        --S5735-L14P2S-QA-V2
               bname8031S5735-L16LP2X-QA-V2(538016),       --S5735-L16LP2X-QA-V2
               bname8031S5735-L16P2UM2X-QA-V2(538017),     --S5735-L16P2UM2X-QA-V2
               bname8031S5735-L16LP2UM2X-QA-V2(538018),    --S5735-L16LP2UM2X-QA-V2
               bname8031S5335-L16LP2UM2X-QA-V2(538019),    --S5335-L16LP2UM2X-QA-V2
               bname8031S5735-L48P4X-A2(538020),          --S5735-L48P4X-A2 for V2R23C00
               bname8031S5735-L48P4S-A2(538021),          --S5735-L48P4S-A2 for V2R23C00
               bname8031S5735S-L48P4X-A2(538022),         --S5735S-L48P4X-A2 for V2R23C00
               bname8031S5735S-L48P4S-A2(538023),         --S5735S-L48P4S-A2 for V2R23C00
               bname8031S5735-L48T4X-A2(538024),          --S5735-L48T4X-A2 for V2R23C00
               bname8031S5735-L48T4S-A2(538025),          --S5735-L48T4S-A2 for V2R23C00
               bname8031S5735S-L48T4X-A2(538026),         --S5735S-L48T4X-A2 for V2R23C00
               bname8031S5735S-L48T4S-A2(538027),         --S5735S-L48T4S-A2 for V2R23C00
               bname8031S5531-H48HB4XZ(538028),           --S5531-H48HB4XZ for V2R22C10
               bname8031S5531-S32ST4X(538029),            --S5531-S32ST4X  for V2R22C10
               bname8031S5335-L24ST4XE-A-V2(538031),       --S5335-L24ST4XE-A-V2
               bname8031S5735-S24HS4XE-V2(538032),         --S5735-S24HS4XE-V2
               bname8031S5735-S24ST4XE-V2(538033),         --S5735-S24ST4XE-V2
               bname8031S5335-S24ST4XE-V2(538034),         --S5335-S24ST4XE-V2
               bname8031S5735-S48HS4XE-V2(538035),         --S5735-S48HS4XE-V2
               bname8031S5735I-H8T4S2XN-V2(538036),           --S5735I-H8T4S2XN-V2
               bname8031S5755-H24UTM4X4Y2C-T(538037),      --S5755-H24UTM4X4Y2C-T  
               bname8031S5755-H48UTM4X4Y2C-T(538038),      --S5755-H48UTM4X4Y2C-T  
               bname8031S5735-L14P2S-TQA-V2(538039),       --S5735-L14P2S-TQA-V2   
               bname8031S5535-L16LP2UM2X-QA-V2(538040),    --S5535-L16LP2UM2X-QA-V2
               bname8031S5535-L24ST4XE-A-V2(538041),       --S5535-L24ST4XE-A-V2   
               bname8031S5535-S24HS4XE-V2(538042),         --S5535-S24HS4XE-V2     
               bname8031S5335-L8T4X-QA-V2(538043),         --S5335-L8T4X-QA-V2     
               bname8031S5335-L8T4S-A-V2(538044),          --S5335-L8T4S-A-V2      
               bname8031S5335-L8P4X-QA-V2(538045),         --S5335-L8P4X-QA-V2     
               bname8031S5335-L24T4X-QA-V2(538046),        --S5335-L24T4X-QA-V2       
               bname8031S5735-L48S4X-A-V2(538047),         --S5735-L48S4X-A-V2
               bname8031eKitEngineS5735S-L48P4X-A1(538056), --S5735S-L48P4X-A1 for V2R23C00
               bname8031eKitEngineS5735S-L48P4S-A1(538057), --S5735S-L48P4S-A1 for V2R23C00
               bname8031eKitEngineS5735S-L48T4X-A1(538058), --S5735S-L48T4X-A1 for V2R23C00
               bname8031eKitEngineS5735S-L48T4S-A2(538059), --S5735S-L48T4S-A1 for V2R23C00
               bname8031S5735R-48T4S-A2(538050),           --S5735R-48T4S-A2 for V2R23C00
               bname8031S5735R-8P4S-QA2(538051),           --S5735R-8P4S-QA2 for V2R23C00
               bname8031S5735R-24T4X-QA2(538052),          --S5735R-24T4X-QA2 for V2R23C00
               bname8031S5735R-24T4S-QA2(538053),          --S5735R-24T4S-QA2 for V2R23C00
               bname8031S5735R-24P4X-A2(538054),           --S5735R-24P4X-A2 for V2R23C00
               bname8031S5735R-24P4S-A2(538055),           --S5735R-24P4S-A2 for V2R23C00
               bname8031S220-24T4X(538060),                --S220-24T4X
               bname8031S220-24P4X(538061),                --S220-24P4X
               bname8031S220-48T4X(538062),                --S220-48T4X
               bname8031S220-48P4X(538063),                --S220-48P4X
               bname8031S220-48P4S(538064),                --S220-48P4S
               bname8031S220-48T4S(538065),                --S220-48T4S
               bname8031S310-24T4X(538066),                --S310-24T4X
               bname8031S310-24P4X(538067),                --S310-24P4X
               bname8031S310-48T4X(538068),                --S310-48T4X
               bname8031S310-48P4S(538069),                --S310-48P4S
               bname8031S310-48P4X(538070),                --S310-48P4X
               bname8031S5735I-H24U8S4XE-QA-V2(538071),    --S5735I-H24U8S4XE-QA-V2
               bname8031S5735I-S24T8S4XE-QA-V2(538072),    --S5735I-S24T8S4XE-QA-V2
               bname8031S5735I-S16T8S4XE-QD-V2(538073),    --S5735I-S16T8S4XE-QD-V2
               bname8031S5732-H48XUM2CC(537583),
	             bname8031S6730-S48X6Q(538074),              --S6730-S48X6Q for V2R23C10
	             bname8031S6330-S48X6Q(538083),              --S6330-S48X6Q for V2R23C10    
               bname8031S6750-H48Y8C(538048),              --S6750-H48Y8C          
               bname8031S6750-H36C(538049),                --S6750-H36C            
               bname8031S5735-L48LPN4XE-A-V2(538075),      --S5735-L48LPN4XE-A-V2  
               bname8031S5735-L24PN4XE-A-V2(538076),       --S5735-L24PN4XE-A-V2   
               bname8031S5735-S48PN4XE-V2(538077),         --S5735-S48PN4XE-V2     
               bname8031S5735-S24PN4XE-V2(538078),         --S5735-S24PN4XE-V2     
               bname8031S5735-L24LU8S4XE-QA-V2(538079),    --S5735-L24LU8S4XE-QA-V2
               bname8031S5335-L24ST4XE-D-V2(538080),       --S5335-L24ST4XE-D-V2   
               bname8031S5735-S48T4XE-C-V2(538081),        --S5735-S48T4XE-C-V2    
               bname8031S5735-S24T4XE-C-V2(538082),        --S5735-S24T4XE-C-V2    
               bname8031S6750-S16X8YZ(538084),             --S6750-S16X8YZ
               bname8031S6750-S24T16X8Y2CZ(538085),        --S6750-S24T16X8Y2CZ
               bname8031S6750-S16X10Y2CZ(538086),           --S6750-S16X10Y2CZ
               bname8031S5755-H24HB2Y2CZ(538087),          --S5755-H24HB2Y2CZ
               bname8031S6730-H6FX4Y2CZ-V2(538088),        --S6730-H6FX4Y2CZ-V2
               bname8031S5735-L24T8J4XE-A-V2(538089),      --S5735-L24T8J4XE-A-V2
               bname8031S5735-S24T8J4XE-XA-V2(538090),     --S5735-S24T8J4XE-XA-V2
               bname8031S5735-S24T4XEZ-V2(538091),         --S5735-S24T4XEZ-V2
               bname8031S5735-S24T8J4XEZ-V2(538092),       --S5735-S24T8J4XEZ-V2
               bname8031S5735-S24P4XEZ-V2(538093),         --S5735-S24P4XEZ-V2
               bname8031S5735-S24P8J4XEZ-V2(538094),       --S5735-S24P8J4XEZ-V2
               bname8031S5735-S48T4XE-XA-V2(538095),       --S5735-S48T4XE-XA-V2
               bname8031S5735-S48T4XEZ-V2(538096),         --S5735-S48T4XEZ-V2
               bname8031S5735-S48P4XEZ-V2(538097),         --S5735-S48P4XEZ-V2
               bname8031S5535-S48HS4XE-V2(538098),         --S5535-S48HS4XE-V2
               bname8031S5335-L24T4S-A-V2(538099),         --S5335-L24T4S-A-V2
               bname8031S5335-L24P4S-A-V2(538100),         --S5335-L24P4S-A-V2
               bname8031S5755-H48T4Y2CZ-B(538101),         --S5755-H48T4Y2CZ-B
               bname8031S5535-S48PN4XE-V2(538102),         --S5535-S48PN4XE-V2
               bname8031S5535-S24PN4XE-V2(538103),         --S5535-S24PN4XE-V2
               bname8031S6780-H4Z(538104),                 --S6780-H4Z
               bname8031S5735I-S8T8P2S4XN-V2(538133),      --S5735I-S8T8P2S4XN-V2
               bname8031S5735I-S16T2S4XN-V2(538134),       --S5735I-S16T2S4XN-V2
               bname8031S310-24ST4X(538124),               --S310-24ST4X
               bname8031S310-24PN4X(538125),               --S310-24PN4X
               bname8031S5735S-L24ST4X-A3(538127),         --S5735S-L24ST4X-A3
               bname8031S5735S-L48S4X-A3(538128),          --S5735S-L48S4X-A3
               bname8031S1730S-S48T4S-A3(538131),          --S1730S-S48T4S-A3
               bname8031S1730S-S48P4S-A3(538132),          --S1730S-S48P4S-A3
               bname8031S220-8T4S(538135),                 --S220-8T4S
               bname8031S220-8P4S(538136),                 --S220-8P4S
               bname8031S530-24T4XE(538137),               --S530-24T4XE
               bname8031S530-24ST4XE(538138),              --S530-24ST4XE
               bname8031S530-48S4XE(538139),               --S530-48S4XE
               bname8031S220S-8T2J(538105),                --S220S-8T2J
               bname8031S220S-8T2X(538106),                --S220S-8T2X
               bname8031S310S-8T2X(538107),                --S310S-8T2X
               bname8031S220S-8P4J(538108),                --S220S-8P4J
               bname8031S220S-8P4JX(538109),               --S220S-8P4JX
               bname8031S220S-10PN4JX(538110),             --S220S-10PN4JX
               bname8031S310S-8P4JX(538111),               --S310S-8P4JX
               bname8031S310S-10PN4JX(538112),             --S310S-10PN4JX
               bname8031S220S-24T4J(538113),               --S220S-24T4J
               bname8031S220S-24T4JX(538114),              --S220S-24T4JX
               bname8031S310S-24T4J(538115),               --S310S-24T4J
               bname8031S310S-24T4JX(538116),              --S310S-24T4JX
               bname8031S220S-24P4J(538117),               --S220S-24P4J
               bname8031S220S-24P4JX(538118),              --S220S-24P4JX
               bname8031S220S-24LP4JX(538119),             --S220S-24LP4JX
               bname8031S220S-26PN4JX(538120),             --S220S-26PN4JX
               bname8031S310S-24P4J(538121),               --S310S-24P4J
               bname8031S310S-24P4JX(538122),              --S310S-24P4JX
               bname8031S310S-26PN4JX(538123),             --S310S-26PN4JX
               bname8031S620-24T16X8Y2CZ(538126),          --S620-24T16X8Y2CZ
               bname8031S5735S-S24P4X-A3(538129),          --S5735S-S24P4X-A3
               bname8031S5735S-S48P4X-A3(538130),          --S5735S-S48P4X-A3
               bname8031S5731I-L8T2SN(538159),             --S5731I-L8T2SN
               bname8031S5731I-L8T2S2XN(538160),           --S5731I-L8T2S2XN
               bname8031S5731I-L8P2S2XN(538161),           --S5731I-L8P2S2XN
               bname8031S5731I-L16T2S2XN(538162),          --S5731I-L16T2S2XN
               bname8031S5735-L48PN4XE-A-V2(538140),       --S5735-L48PN4XE-A-V2    
               bname8031S5735R-L8T4S-A-V2(538141),         --S5735R-L8T4S-A-V2      
               bname8031S5735R-L8T4X-QA-V2(538142),        --S5735R-L8T4X-QA-V2     
               bname8031S5735R-L8P4S-A-V2(538143),         --S5735R-L8P4S-A-V2      
               bname8031S5735R-L8P4X-QA-V2(538144),        --S5735R-L8P4X-QA-V2     
               bname8031S5735R-L16LP2S-QA-V2(538145),      --S5735R-L16LP2S-QA-V2   
               bname8031S5735R-L16LP2X-QA-V2(538146),      --S5735R-L16LP2X-QA-V2   
               bname8031S5735R-L16LP2UM2X-QA-V2(538147),   --S5735R-L16LP2UM2X-QA-V2
               bname8031S5735R-L16T4S-A-V2(538148),        --S5735R-L16T4S-A-V2     
               bname8031S5735R-L16T4X-QA-V2(538149),       --S5735R-L16T4X-QA-V2    
               bname8031S5735R-L24T4S-A-V2(538150),        --S5735R-L24T4S-A-V2     
               bname8031S5735R-L24T4X-QA-V2(538151),       --S5735R-L24T4X-QA-V2    
               bname8031S5735R-L24P4S-A-V2(538152),        --S5735R-L24P4S-A-V2     
               bname8031S5735R-L24P4X-A-V2(538153),        --S5735R-L24P4X-A-V2     
               bname8031S5735R-L48T4S-A-V2(538154),        --S5735R-L48T4S-A-V2     
               bname8031S5735R-L48T4X-A-V2(538155),        --S5735R-L48T4X-A-V2     
               bname8031S5735R-L48LP4S-A-V2(538156),       --S5735R-L48LP4S-A-V2    
               bname8031S5735R-L48LP4X-A-V2(538157),       --S5735R-L48LP4X-A-V2    
               bname8031S5735R-L48P4X-A-V2(538158),        --S5735R-L48P4X-A-V2     
               bname8031S5735I-H8T2XN-V2(538163),          --S5735I-H8T2XN-V2
               bname8031S5735I-H8U2XN-V2(538164),          --S5735I-H8U2XN-V2
               bname8031S5735I-S8U2XN-V2(538165),          --S5735I-S8U2XN-V2
               bname8031S5735I-S48T4XE-V2(538224),         --S5735I-S48T4XE-V2

               bname8031S5755-S24T8J8YZ(538166),           --S5755-S24T8J8YZ                        
               bname8031S5755-S24T8Y(538167),              --S5755-S24T8Y                           
               bname8031S5755-S24P8J8YZ(538168),           --S5755-S24P8J8YZ                        
               bname8031S5755-S24P8Y(538169),              --S5755-S24P8Y                           
               bname8031S5755-S24U8J8YZ(538170),           --S5755-S24U8J8YZ                        
               bname8031S5755-S24U8Y(538171),              --S5755-S24U8Y                           
               bname8031S5755-S48T8YZ(538172),             --S5755-S48T8YZ                          
               bname8031S5755-S48T8Y(538173),              --S5755-S48T8Y                           
               bname8031S5755-S48P8YZ(538174),             --S5755-S48P8YZ                          
               bname8031S5755-S48P8Y(538175),              --S5755-S48P8Y                           
               bname8031S5755-S48U8YZ(538176),             --S5755-S48U8YZ                          
               bname8031S5755-S48U8Y(538177),              --S5755-S48U8Y                           
               bname8031S5755-H24UM4Y2CZ(538178),          --S5755-H24UM4Y2CZ                       
               bname8031S5755-H24UM4Y2CZ-T(538179),        --S5755-H24UM4Y2CZ-T                     
               bname8031S5755-H48UM4Y2CZ(538180),          --S5755-H48UM4Y2CZ                       
               bname8031S5755-H48UM4Y2CZ-T(538181),        --S5755-H48UM4Y2CZ-T                     
               bname8031S5751R-L8T2X-QA(538182),           --S5751R-L8T2X-QA                        
               bname8031S5751R-L8T2J-QA(538183),           --S5751R-L8T2J-QA                        
               bname8031S5751R-L8P2X-QA(538184),           --S5751R-L8P2X-QA                        
               bname8031S5751R-L8P2J-QA(538185),           --S5751R-L8P2J-QA                        
               bname8031S5751R-L8P2PN2X-QA(538186),        --S5751R-L8P2PN2X-QA                     
               bname8031S5751R-L24T4J-QA(538187),          --S5751R-L24T4J-QA                       
               bname8031S5751R-L24T2J2X-QA(538188),        --S5751R-L24T2J2X-QA                     
               bname8031S5751R-L24P4J-A(538189),           --S5751R-L24P4J-A                        
               bname8031S5751R-L24P2J2X-A(538190),         --S5751R-L24P2J2X-A                      
               bname8031S5751R-L24P2PN2J2X-A(538191),      --S5751R-L24P2PN2J2X-A                   
               bname8031S5735R-S24T8J4X-XA-V2(538192),     --S5735R-S24T8J4X-XA-V2                  
               bname8031S5735R-S48T4X-XA-V2(538193),       --S5735R-S48T4X-XA-V2                    
               bname8031S5735R-S24P4X-V2(538194),          --S5735R-S24P4X-V2                       
               bname8031S5735R-S48P4X-V2(538195),          --S5735R-S48P4X-V2                       
               bname8031S3510-S8P2PN2X-A(538196),          --S3510-S8P2PN2X-A                       
               bname8031S310-48S4X(538197),                --S310-48S4X                             
               bname8031S310-48HP4X(538198),               --S310-48HP4X                            
               bname8031S310-48PN4X(538199),               --S310-48PN4X                            
               bname8031S310-24T8J4X(538200),              --S310-24T8J4X                           
               bname8031S620-16X8YZ(538201),               --S620-16X8YZ                            
               bname8031S6730S-S48X6Q-A1(538202),          --S6730S-S48X6Q-A1                       
               bname8031S6730S-H48X6C-A1(538203),          --S6730S-H48X6C-A1                       
               bname8031S5735S-L8T4X-QA3(538204),          --S5735S-L8T4X-QA3                       
               bname8031S5735S-L8P4X-QA3(538205),          --S5735S-L8P4X-QA3                       
               bname8031S5735S-L24T4S-QA3(538206),         --S5735S-L24T4S-QA3                      
               bname8031S5735S-L24T4X-QA3(538207),         --S5735S-L24T4X-QA3                      
               bname8031S5735S-L24T8J4XE-A3(538208),       --S5735S-L24T8J4XE-A3                    
               bname8031S5735S-L24P4S-A3(538209),          --S5735S-L24P4S-A3                       
               bname8031S5735S-L24P4XE-A3(538210),         --S5735S-L24P4XE-A3                      
               bname8031S5735S-L48T4S-A3(538211),          --S5735S-L48T4S-A3                       
               bname8031S5735S-L48T4XE-A3(538212),         --S5735S-L48T4XE-A3                      
               bname8031S5735S-L48P4S-A3(538213),          --S5735S-L48P4S-A3                       
               bname8031S5735S-L48P4XE-A3(538214),         --S5735S-L48P4XE-A3                      
               bname8031S5735S-L24PN4XE-A3(538215),        --S5735S-L24PN4XE-A3                     
               bname8031S5735S-L48PN4XE-A3(538216),        --S5735S-L48PN4XE-A3                     
               bname8031S1730S-S8T4X-QA3(538217),          --S1730S-S8T4X-QA3                       
               bname8031S1730S-S8P4X-QA3(538218),          --S1730S-S8P4X-QA3                       
               bname8031S1730S-S24T4S-QA3(538219),         --S1730S-S24T4S-QA3                      
               bname8031S1730S-S24T4X-QA3(538220),         --S1730S-S24T4X-QA3                      
               bname8031S1730S-S24P4S-A3(538221),          --S1730S-S24P4S-A3                       
               bname8031S1730S-S24P4X-A3(538222),          --S1730S-S24P4X-A3                       
               bname8031S1730S-S48T4X-A3(538223),          --S1730S-S48T4X-A3
               bname8031S5735-L24P4XE-A-V2-BJEX(538225),   --S5735-L24P4XE-A-V2-BJEX
               bname8031S5735-L24P4XE-A-V2-SHEX(538226),   --S5735-L24P4XE-A-V2-SHEX
               bname8031S5735-L24P4XE-A-V2-GDEX(538227),   --S5735-L24P4XE-A-V2-GDEX
               bname8031S5735-L24P4XE-A-V2-JSEX(538228),   --S5735-L24P4XE-A-V2-JSEX
               bname8031S5735-L24P4XE-A-V2-ZJEX(538229),   --S5735-L24P4XE-A-V2-ZJEX
               bname8031S5735-L48T4XE-A-V2-BJEX(538230),   --S5735-L48T4XE-A-V2-BJEX
               bname8031S5735-L48T4XE-A-V2-SHEX(538231),   --S5735-L48T4XE-A-V2-SHEX
               bname8031S5735-L48T4XE-A-V2-GDEX(538232),   --S5735-L48T4XE-A-V2-GDEX
               bname8031S5735-L48T4XE-A-V2-JSEX(538233),   --S5735-L48T4XE-A-V2-JSEX
               bname8031S5735-L48T4XE-A-V2-ZJEX(538234),   --S5735-L48T4XE-A-V2-ZJEX
               bname8031S5735E-L8T4X-QA-V2(538235),        --S5735E-L8T4X-QA-V2     
               bname8031S5735E-L8P4X-QA-V2(538236),        --S5735E-L8P4X-QA-V2     
               bname8031S5735E-L24T4XE-A-V2(538237),       --S5735E-L24T4XE-A-V2    
               bname8031S5735E-L24P4S-A-V2(538238),        --S5735E-L24P4S-A-V2     
               bname8031S5735E-L24P4XE-A-V2(538239),       --S5735E-L24P4XE-A-V2    
               bname8031S5735E-L48T4XE-A-V2(538240),       --S5735E-L48T4XE-A-V2    
               bname8031S5735E-L48LP4S-A-V2(538241),       --S5735E-L48LP4S-A-V2    
               bname8031S5735E-L48LP4XE-A-V2(538242),      --S5735E-L48LP4XE-A-V2   
               bname8031S5735E-S24HS4XE-V2(538243),        --S5735E-S24HS4XE-V2     
               bname8031S5735E-L24ST4XE-A-V2(538244),      --S5735E-L24ST4XE-A-V2   
               bname8031S5735E-S48HS4XE-V2(538245),        --S5735E-S48HS4XE-V2     
               bname8031S5735E-L48S4XE-A-V2(538246),       --S5735E-L48S4XE-A-V2    
               bname8031S5735E-L16LP2X-QA-V2(538247),      --S5735E-L16LP2X-QA-V2   
               bname8031S5735E-L16LP2UM2X-QA-V2(538248),   --S5735E-L16LP2UM2X-QA-V2
               bname8031S6750E-S24T16X8Y2CZ(538249),       --S6750E-S24T16X8Y2CZ    
               bname8031S6750E-S16X10Y2CZ(538250),         --S6750E-S16X10Y2CZ      
               bname8031S5755E-H24HB2Y2CZ(538251),         --S5755E-H24HB2Y2CZ      
               bname8031S6730E-H6FX4Y2CZ-V2(538252),       --S6730E-H6FX4Y2CZ-V2    
               bname8031S310-24U4X(538253),                --S310-24U4X             
               bname8031S530-24T8J4XE(538254),             --S530-24T8J4XE                    
               bname8031S530-48T4XE(538255),               --S530-48T4XE                       
               bname8031S550-24T8J8YZ(538256),             --S550-24T8J8YZ          
               bname8031S550-24T8Y(538257),                --S550-24T8Y             
               bname8031S550-48T8YZ(538258),               --S550-48T8YZ            
               bname8031S550-48T8Y(538259),                --S550-48T8Y             
               bname8031S5755-S24UN8YZ(538271),            --S5755-S24UN8YZ          
               bname8031S5755-S24N8YZ(538260),             --S5755-S24N8YZ           
               bname8031S5755-S48UN8YZ(538261),            --S5755-S48UN8YZ          
               bname8031S5755-S48N8YZ(538262),             --S5755-S48N8YZ           
               bname8031S5735-L24HJ4XE-A-V2(538263),       --S5735-L24HJ4XE-A-V2     
               bname8031S5735E-L24HJ4XE-A-V2(538264),      --S5735E-L24HJ4XE-A-V2    
               bname8031S5735-S24HJ4XE-V2(538265),         --S5735-S24HJ4XE-V2       
               bname8031S5735E-S24HJ4XE-V2(538266),        --S5735E-S24HJ4XE-V2      
               bname8031S5735-S48HJ4XE-V2(538267),         --S5735-S48HJ4XE-V2       
               bname8031S5735E-S48HJ4XE-V2(538268),        --S5735E-S48HJ4XE-V2      
               bname8031S5735-L24J4X-A-V2(538269),         --S5735-L24J4X-A-V2       
               bname8031S5735-L24J4X-D-V2(538270),         --S5735-L24J4X-D-V2       
               bname8031S5735-L48J4X-A-V2(538272),         --S5735-L48J4X-A-V2       
               bname8031S5735-L48J4X-D-V2(538273),         --S5735-L48J4X-D-V2       
               bname8031S5735-S24J4XE-V2(538275),          --S5735-S24J4XE-V2        
               bname8031S5735E-S24J4XE-V2(538276),         --S5735E-S24J4XE-V2       
               bname8031S5735-S48J4XE-V2(538278),          --S5735-S48J4XE-V2        
               bname8031S5735E-S48J4XE-V2(538279),         --S5735E-S48J4XE-V2       
               bname8031S6730-S24X6Q-V2(538281),           --S6730-S24X6Q-V2         
               bname8031S6730-S48X6Q-V2(538282),           --S6730-S48X6Q-V2         
               bname8031S6330-H24X6C-V2(538283),           --S6330-H24X6C-V2         
               bname8031S6330-H48X6C-V2(538284),           --S6330-H48X6C-V2         
               bname8031S6750-H48X8C(538285),              --S6750-H48X8C            
               bname8031S5735-L24T4S-A-V2-BJEX(538286),    --S5735-L24T4S-A-V2-BJEX  
               bname8031S5735-L24T4S-A-V2-SHEX(538287),    --S5735-L24T4S-A-V2-SHEX  
               bname8031S5735-L24T4S-A-V2-GDEX(538288),    --S5735-L24T4S-A-V2-GDEX  
               bname8031S5735-L24T4S-A-V2-JSEX(538289),    --S5735-L24T4S-A-V2-JSEX  
               bname8031S5735-L24T4S-A-V2-ZJEX(538290),    --S5735-L24T4S-A-V2-ZJEX  
               bname8031S5735-L24T4XE-A-V2-BJEX(538291),   --S5735-L24T4XE-A-V2-BJE  
               bname8031S5735-L24T4XE-A-V2-SHEX(538292),   --S5735-L24T4XE-A-V2-SHE  
               bname8031S5735-L24T4XE-A-V2-GDEX(538293),   --S5735-L24T4XE-A-V2-GDE  
               bname8031S5735-L24T4XE-A-V2-JSEX(538294),   --S5735-L24T4XE-A-V2-JSE  
               bname8031S5735-L24T4XE-A-V2-ZJEX(538295),   --S5735-L24T4XE-A-V2-ZJE  
               bname8031S5735-L24P4S-A-V2-BJEX(538296),    --S5735-L24P4S-A-V2-BJEX  
               bname8031S5735-L24P4S-A-V2-SHEX(538297),    --S5735-L24P4S-A-V2-SHEX  
               bname8031S5735-L24P4S-A-V2-GDEX(538298),    --S5735-L24P4S-A-V2-GDEX  
               bname8031S5735-L24P4S-A-V2-JSEX(538299),    --S5735-L24P4S-A-V2-JSEX  
               bname8031S5735-L24P4S-A-V2-ZJEX(538300),    --S5735-L24P4S-A-V2-ZJEX  
               bname8031S6750-S24T16X8Y2CZ-BJEX(538301),   --S6750-S24T16X8Y2CZ-BJEX 
               bname8031S6750-S24T16X8Y2CZ-SHEX(538302),   --S6750-S24T16X8Y2CZ-SHEX 
               bname8031S6750-S24T16X8Y2CZ-GDEX(538303),   --S6750-S24T16X8Y2CZ-GDEX 
               bname8031S6750-S24T16X8Y2CZ-JSEX(538304),   --S6750-S24T16X8Y2CZ-JSEX 
               bname8031S6750-S24T16X8Y2CZ-ZJEX(538305),   --S6750-S24T16X8Y2CZ-ZJEX 
               bname8031S210-24T4JX(538306),               --S210-24T4JX             
               bname8031S210-24P2J(538307),                --S210-24P2J              
               bname8031S210-24P4JX(538308),               --S210-24P4JX             
               bname8031S210I-8T4SX(538309),               --S210I-8T4SX             
               bname8031S210I-8P4SX(538310),               --S210I-8P4SX             
               bname8031S210-8T(538312),                   --S210-8T                 
               bname8031S210-8T2J(538313),                 --S210-8T2J               
               bname8031S210-8LP2J(538314),                --S210-8LP2J              
               bname8031S210-8P2J(538315),                 --S210-8P2J               
               bname8031S210-24T2J(538316),                --S210-24T2J              
               bname8031S5735S-S24T4SE-A3(538317),         --S5735S-S24T4SE-A3       
               bname8031S5735S-S24T4XE-A3(538318),         --S5735S-S24T4XE-A3       
               bname8031S5735S-S24T8J4XE-XA3(538319),      --S5735S-S24T8J4XE-XA3    
               bname8031S5735S-S48T4SE-A3(538320),         --S5735S-S48T4SE-A3       
               bname8031S5735S-S48T4XE-A3(538321),         --S5735S-S48T4XE-A3       
               bname8031S5735S-S24ST4XE-A3(538322),        --S5735S-S24ST4XE-A3      
               bname8031S5735S-S48S4XE-A3(538323),         --S5735S-S48S4XE-A3       
               bname8031S5751-L16T2X-RUA(538324),          --S5751-L16T2X-RUA        
               bname8031S5751R-L16T2X-QA(538325),          --S5751R-L16T2X-QA        
               bname8031S5751-L16T2J-RUA(538326),          --S5751-L16T2J-RUA        
               bname8031S5751R-L16T2J-QA(538327),          --S5751R-L16T2J-QA        
               bname8031S5751-L16LP2X-RUA(538328),         --S5751-L16LP2X-RUA       
               bname8031S5751R-L16LP2X-QA(538329),         --S5751R-L16LP2X-QA       
               bname8031S5751-L16LP2J-RUA(538330),         --S5751-L16LP2J-RUA       
               bname8031S5751R-L16LP2J-QA(538331),         --S5751R-L16LP2J-QA       
               bname8031S5751-L16LP4UN2X-RUA(538332),      --S5751-L16LP4UN2X-RUA    
               bname8031S5751R-L16LP4UN2X-QA(538333),      --S5751R-L16LP4UN2X-QA    
               bname8031S5751-L8LP4UN2X-RUA(538334),       --S5751-L8LP4UN2X-RUA     
               bname8031S5751R-L8LP4UN2X-QA(538335),       --S5751R-L8LP4UN2X-QA     
               bname8031S310S-8P4UN2X(538336),             --S310S-8P4UN2X
               bname8031S5751-L4LP8UN2X-RUA(538339),       --S5751-L4LP8UN2X-RUA     
               bname8031S5751R-L4LP8UN2X-QA(538340),       --S5751R-L4LP8UN2X-QA     
               bname8031S310S-4P8UN2X(538341),             --S310S-4P8UN2X           
               bname8031S5751-L24T2J-RUA(538344),          --S5751-L24T2J-RUA        
               bname8031S5751-L24T2X-RUA(538345),          --S5751-L24T2X-RUA        
               bname8031S5751-L24P2J-RUA(538346),          --S5751-L24P2J-RUA        
               bname8031S5751-L24P2X-RUA(538347),          --S5751-L24P2X-RUA        
               bname8031S5751-L24P2PN2X-RUA(538348),       --S5751-L24P2PN2X-RUA
               bname8031S5755-S48T8YZ-B(538349),           --S5755-S48T8YZ-B
               bname8031S5755-H24J8T4Y2CZ(538350),         --S5755-H24J8T4Y2CZ
               bname8031S5755-H48J4Y2CZ(538351),           --S5755-H48J4Y2CZ
               bname8031S5755-S48T4X4Y-HT(538352),         --S5755-S48T4X4Y-HT
               bname8031S5755-S48P4X4Y-HT(538353),         --S5755-S48P4X4Y-HT
               bname8031S5751-L8LP4JN-RUA(538354),         --S5751-L8LP4JN-RUA
               bname8031S5751-L8LP4XN-RUA(538355),         --S5751-L8LP4XN-RUA
               bname8031S5735-S24T4XE-Q-V2(538356),        --S5735-S24T4XE-Q-V2
               bname8031S6750-H48Y8C-B(538357),            --S6750-H48Y8C-B
               bname8031S5735I-S24F2T2XN-SPE-V2(538358),   --S5735I-S24F2T2XN-SPE-V2           
               bname8031S110E-24T(538359),                 --S110E-24T   
               bname8031S110E-24T2J(538360),               --S110E-24T2J 
               bname8031S110E-24LP2J(538361),              --S110E-24LP2J
               bname8031S110E-24P2J(538362),               --S110E-24P2J 
               bname8031S210-4P8UN2X(538363),              --S210-4P8UN2X
               bname8031S110E-24T-SEA(538364),             --S110E-24T oversea for V6R25C10
               bname8031S110E-24T2J-SEA(538365),           --S110E-24T2J oversea for V6R25C10
               bname8031S110E-24LP2J-SEA(538366),          --S110E-24LP2J oversea for V6R25C10
               bname8031S110E-24P2J-SEA(538367),           --S110E-24P2J oversea for V6R25C10

-- 8090:
                bname8090DEVUNKNOWN(561152),         -- Unknown board type
                bname8090DEVMPU(561153),             -- Main Processing Unit
                bname8090DEVSFU(561154),             -- Switch Fabric Unit for Full Capacity System
                bname8090DEVLPU(561155),             -- Flexible Card Line Processing Unit,obsolete
                bname8090DEVVSU(561998),             --CGN Versatile Service Flexible Card (VSUP-100)
                bname8090DEVCLK(561156),             -- system clk board on MPU board,obsolete
                bname8090DEVPOWER(561157),           -- DC/DC Power Module
                bname8090DEVPOWERAC(229032),         -- AC/AC Power Module
                bname8090DEVFAN(561158),             -- Fan Module
                bname8090DEVLCD(561159),             -- LCD Module
                bname8090DEVSRUMPU(561160),          -- MPU Module on SRU board,obsolete
                bname8090DEVSRUSFU(561161),          -- Switch Fabric Unit for Half & Halflow Frame System for SFUD
                bname8090DEVNETSTREAM(561162),       -- NETSTREAM Module
                bname8090DEVRAINIER(561163),      -- RAINIER Module
                bname8090DEVGRE(561164),              -- GRE Module
                bname8090DEVTSU(561165),              -- TSU Module
                bname8090DEVSFEA(561166),              -- Switch Fabric Unit for Full Capacity System
                bname8090DEVSRU(561167),             -- SRU  board
                bname8090DEVLPUA(561168),            -- LPUA Module
                bname8090DEVLPUB(561169),            -- LPUB Module
                bname8090DEVLPUC(561170),            -- LPUC Module
                bname8090DEVCR52LPUE(561171),        -- CR52LPUE Module
                bname8090DEVCR53LPUF(561172),        -- CR53LPUF Module
                bname8090DEVLPUG(561173),            -- LPUG Module
                bname8090DEVLPUH(561174),            -- LPUH Module
                bname8090DEVLPUK(561175),            -- LPUK Module
                bname8090DEVSPU(561176),             -- NETSTREAM Module
                bname8090DEVSFUG(561177),            -- SFUG Module
                bname8090DEVMPUA(561178),            -- Cluster Central Main Processing Unit A
                bname8090DEVSFUA(561179),            -- Cluster Central Switch Fabric Unit A
                bname8090DEVECUA(561180),            -- Cluster Electric Cross Unit A
                bname8090DEVICUA(561181),            -- Cluster Internal Communication Unit A
                bname8090DEVCR52LPUM(561182),        -- CR52LPUM Module
                bname8090DEVCR52LPUI(561183),        -- CR52LPUI Module
                bname8090DEVLPUK1(561184),           -- LPUF-20-B Module
                bname8090DEVLPUK2(561185),           -- LPUF-21-A Module
                bname8090DEVLPUK3(561186),           -- LPUF-21-B Module
                bname8090DEVMPUD(561187),            -- NE40E-3 Main Processing Unit
                bname8090DEVMPUC(561188),            -- MPUC Module,abandon
                bname8090DEVSRU40A(561189),          -- SRU40A Module,abandon
                bname8090DEVLPUN(561190),            -- LPUN Module
                bname8090DEVLPUR(561191),            -- LPUR Module
                bname8090DEVSFU40A(561192),          -- SFU40A Module
                bname8090DEVSFU40B(561193),          -- SFU40B Module
                bname8090DEVSFUI(561194),            -- SFUI Module
                bname8090DEVCR56RPUA(561195),        -- RPUA Module on MPUC or SRUC (X8,X16)
                bname8090DEVCR56MADA(561196),        -- MADA Module on MPUC(X16)
                bname8090DEVCR57FRA40A(561197),      -- FRA40A Module on MPUC(X8)
                bname8090DEVCR56SFUF100B(561198),      --CR56SFUF100B Module
                bname8090DEVCR52L4XXB(561199),       -- 4-Port 10GBase LAN/WAN-XFP Integrated  Line Processing Unit (LPUI-40)
                bname8090DEVCR52EKGFB(561200),       -- 40-Port 100/1000Base-X-SFP Integrated Line Processing Unit(LPUI-40)
                bname8090DEVCR52EKGFC(561201),       -- 40-Port 100/1000Base-X-SFP Switch Line Processing Unit(LPUS-20)
                bname8090DEVCR52EKGEB(561202),       -- 40-Port 10/100/1000Base-RJ45 Switch Line Processing Unit(LPUS-20)
                bname8090DEVCR52L4XXC(561203),       -- 4-Port 10GBase LAN/WAN-XFP Switch Line Processing Unit(LPUS-20)
                bname8090DEVCR55SFUI100A(561204),    -- CR55SFUI100A Module
                bname8090DEVCR55ECU100A(561205),     -- CR55ECU100A Module
                bname8090DEVCR52SFEB(561206),        -- Switch Fabric Unit for Full Capacity System (FE600)
                bname8090DEVCR52LPUF40B(561207),     -- CR5MLPUF402B(SBOM),Flexible Card Line Processing Unit(LPUF-40,2 sub-slots) B
                bname8090DEVCR52LPUF40A(561208),     -- CR5MLPUF402A(SBOM),Flexible Card Line Processing Unit(LPUF-40,2 sub-slots) A (L3VPN, MVPN, IPv6 Enhanced)

                bname8090DEVCR57FRA100A(561209),      -- FRA100A Module on MPUC(X8)
                bname8090DEVCR57FRA200A(561210),      -- FRA200A Module on MPUC(X8)

                bname8090DEVCR57LPUF41A(561211),     -- LPUF41A 40G LPU,SD58X2 Solution ,MIPS CPU
                bname8090DEVCR57LPUF101A(561212),    -- Double LPUF41A, 100G LPU

                bname8090DEVCR57SRU100A(561213),     -- Two piece 8890, 100G SFU, used with X8 SRUA100A MPU
                bname8090DEVCR57SRU200A(561214),     -- Two piece 5802, 200G SFU, used with X8 SRUA200A MPU

                bname8090DEVCR57SFU100C(561215),     -- Two piece 8890, X8 100G SFU
                bname8090DEVCR57SFU200B(561216),     -- Two piece 5802, X16 100G-200G SFU
                bname8090DEVCR57SFU200C(561217),     -- Two piece 5802, X8 100G-200G SFU
                bname8090DEVCR55MPUAB(561218),       -- CCC Main Processing Unit
                bname8090DEVCR56LPUF100B(561219),    -- NE5000E Line Processing Unit(NE5000E LPUF-100)
                bname8090DEVCR56SFUF100C(561220),    -- NetEngine5000E,CR56SFUF100C, 100G Switch Fabric Unit B(SFUF-100-C)
                bname8090DEVCR56SFU200A(561221),     -- NetEngine5000E,CR56SFU200A, 200G Switch Fabric Unit B(SFU-200-A)
                bname8090DEVCR52LPUR(561225),        -- NetEngine5000E,CR52EKGFY0,40-Port 1000Base-X-SFP Line Processing Unit
                bname8090DEVCR52SPUC(561226),        -- NetEngine5000E,CR52SPUC0, Versatile Service Process Unit C
                bname8090DEVCR56LPUF200A(561227),    -- NE5000E Line Processing Unit(NE5000E LPUF-200)
                bname8090DEVMPUH(561228),            -- NE40E-X3-NEW Main Processing Unit
                bname8090DEVCR57SFU100D(561229),     -- one piece 5802, X8 100G SFU
                bname8090DEVCR57SRU100D(561230),     -- one piece 5802, 100G SFU, used with X8 SRUA100A MPU
                bname8090DEVPMU(561231),             -- NE5000E PMU Unit
                bnameCX6M001FBX71(561232),           -- CX67FCBA Fan
                bnameCX6M002FBX72(561233),           -- CX67FCBB Fan
                bnameCX6M002FBX73(561234),           -- CX67FCBC Fan
                bname8090DEVPSU1200A(561235),        -- PSU1200A AC Power Module
                bname8090DEVPSU1600A(561236),        -- PSU1600A AC Power Module
                bname8090DEVPSU2400A(561237),        -- PSU2400A AC Power Module

                bnameNECXMEDEVHBOARD(565000),        --any MPU,SFU and LPU's MIB value in NE,CX,and ME for CCB result.{8090 : 0x00089000 ~ 0x00089fff }
                bname8090DEVCR58CMUC(562097),        -- Finished Board,NE9000,CR58CMUC,Centralized Monitoring Module
                bname8090DEVCR58LPU1TC(561995),      -- v8r9c10 NE9000 CR58LPU1TC
                bname8090DEVCR58LPU1TG(561996),      -- v8r9c10 NE9000 CR58LPU1TG
                bname8090DEVExX16Power(561990),      -- ExX16Power
                bname8090DEVNGX20POWER(561991),      -- NGX20POWER
                bname8090DEVExX16APower(561992),     -- ExX16APower
                bname8090DEVX3POWER(561993),         -- X3POWER
                bname8090DEVCOMPOWER(561994),        -- COMPOWER
                bname8090DEVBOARDSLOT(561997),        -- BOARDSLOT 
                bname8090DEVCFCARDSLOT(561999),        -- CFCARDSLOT 
                bname8090DEVPMUSLOT(561887),         -- PMUSLOT
                bname8090DEVFANSLOT(561888),         -- FANSLOT
                bname8090DEVPOWERSLOT(561889),       -- POWERSLOT
                bnameDP52PDC2K4A1(564504),    --V8R13C00 NetEngine-8000-M14 DP52PDC2K4A1, M14
                bnameDP32PDC1K6A1(229028),    --V8R13C00 NetEngine-8000-M14 DP32PDC1K6A1, M14
                bnamePAC1K5S53-AL(229030),    --V8R13C00 NetEngine-8000-M14 PAC1K5S53-AL, M14
                bnameCR8M002FBXC1(564505),    --V8R13C00 NetEngine-8000-M14 CR8M002FBXC1, M14
                bnameCR8MM82FBXC1(564507),    --V8R13C00 NetEngine-8000-M14 CR8MM82FBXC1, M14
                bnameCR8M002FBXZ1(564509),    --V8R13C00 NetEngine-8000-M14 CR8M002FBXZ1, M14
                bnameCR8MME2FBXK1(564510),    --V8R13C00 NetEngine-8000-M14 CR8MME2FBXK1, M14
                bnameCR8M002FBXC2(564511),    --V8R13C00 NetEngine-8000-M14 CR8M002FBXC2, M14
                bnameCR8MM82FBXK1(564512),    --V8R13C00 NetEngine-8000-M14 CR8MM82FBXK1, M14
                bnameCR8MM82FBXC2(564513),    --V8R13C00 NetEngine-8000-M14 CR8MM82FBXC2, M14
                bnameCR8MM62FBXK1(564528),    --V8R13C00 NetEngine-8000-M6K CR8MM62FBXK1, M6K
                bnameCR8M002FBX11(564533),    --V8R21C10 NetEngine-8000E-M14 CR8M002FBX11, M14
                bnameCR8MM82FBX11(564534),    --V8R21C10 NetEngine-8000E-M8 CR8MM82FBX11, M8
                bnameNE8KF8FAN(564535),       --V8R22C00 NetEngine-8000E-F8 NE8KF8FAN
                bnameNE8KF8PIU(564536),       --V8R22C00 NetEngine-8000E-F8 NE8KF8PIU
                bnameNE8KF8APIU(564537),       --V8R22C00 NetEngine-8000E-F8 NE8KF8APIU
                bnameDP22PDC1K2A1(229029),    --V8R22C00 NetEngine-8000-M4 DP22PDC1K2A1
                bnameANRD000FAN00(229015),    --V8R22C00 NetEngine-8000-M4 ANR1FAN01
                bnameTNRMM42FBXC1(564538),    --V8R22C10 PTN 6900-2-M4 TNRMM42FBXC1
                bnameGPFANCBE(564539),        --V8R23C00 NetEngine-8000-X GPFANCBE
                bnameDP5U2K4APIU(564540),     --V8R23C10 NetEngine-8000-M DP5U2K4APIU
                bnameAPIU3000W(564541),     --V8R24C00 NetEngine-8000-F8 APIU3000W
                bnameF2CPIU(564542),     --V8R24C00 NetEngine-8000-F2 F2CPIU
                bnameCR8M002FBXC3(564543),    --V8R23C10 NetEngine-8000-M14 CR8M002FBXC3, M14
                bnameTNRM002FBXC3(564544),    --V8R23C10 PTN6900-M4 TNRM002FBXC3
                bnameCR5M002FBXC3(564545),    --V8R23C10 NE40E-M14 CR5M002FBXC3
                bnameCR8M002FBXC4(564546),    --V8R23C10 NE8000E M14 CR8M002FBXC4
                bnameCR8MM60FBXC2(564548),    --V8R24C00 NetEngine-8000E-M6 CR8MM60FBXC2, M6
                bnameCR8MM82FBXC3(564549),    --V8R24C00 NetEngine 8000 M8 CR8MM82FBXC3, M8
                bnameTNRMM82FBXC3(564550),    --V8R24C00 PTN6900-2-M8C TNRMM82FBXC3, M8
                bnameCP8MM60FBXC0(564551),    --V8R24C00 NetEngine A835 T Fan Box
                bnameCR8M004FBXC0(564552),    --V8R24C00 NetEngine 8000 M4 Fan Box
                bnameANOD000FAN00(564553),    --V8R24C10 ATN980E Fan Box
                bnameCR8M002FBXC5(564514),    --V8R24C10 NetEngine XH16000 M14 Fan Box(E)
                bnameCR8M004FBXC1(564554),    --NetEngine 8000E M4 Fan Box
                bnameCR8MM82FBXC4(564555),    --NetEngine 8000E M8 Fan Box
                bnameGXCOMMPOWER(564556),    -- GXCOMMPOWER
                bnamePAC3K2S54(675966),        -- F2AAPIU
                bnamePDC2K2S54(675967),        -- F2APIU
                bnamePDC1000S12-CB(675968),    -- F1APIU
                bnamePAC600S12-CB(675969),     -- F1AAPIU
                bnamePAC1K2S12-CB(675970),     -- F1AAPIU_B
                bnameDACS(675971),             -- DACS Module
                bnameTPJ1PIU(675972),          -- TPJ1PIU
                bnameTNF5PIU(675973),          -- TNF5PIU
                bnameANJ000APIU00(675974),     -- TNF5APIU
                bnamePAH2K4S53-CL(675975),     --V8R23C10 NetEngine-8000-M DP5U2K4APIU
                bnamePDC3KS54-CF(675976),     --V8R24C00 NetEngine-8000-F2 F2CPIU
-- ME60:
                bnameME60UNKNOWN(159744),
                bnameME60MPUA(159745),                -- ME60-16 MPU Module
                bnameME60MPUB(159746),                -- ME60-8 MPU Module
                bnameME60SFUA(159747),                -- ME60-16 SFU Module
                bnameME60SFUB(159748),                -- ME60-8 SFU Module
                bnameME60CLK(159749),                 -- CLK Module
                bnameME60POWER(159750),               -- POWER Module
                bnameME60FAN(159751),                 -- FAN Module
                bnameME60LCD(159752),                 -- LCD Module
                bnameME60CR52LPUA(159753),            -- CR52LPUA Module
                bnameME60ME01LPUA(159754),            -- ME01LPUA Module
                bnameME60ME01TSUA0(159755),            --CR52TSU Module
                bnameME60ME01SSUA0(159756),            --CR52SSU Module
                bnameME60ME01SBCA0(159757),            --CR52SBC Module
                bnameME60ME01VSUA0TSU(159758),         --ME01TSU Module
                bnameME60ME01VSUA0SSU(159759),         --ME01SSU Module
                bnameME60ME01VSUA0SBC(159760),         --ME01SBC Module
                bnameME60ME01LPUE(159761),             --LPUE Module
                bnameME60RAINIER(159762),              --RAINIER Module

                bnameME60ME01VSUA0DPI(159763),         --ME01DPI Module
                bnameME60ME01LPUB0(159764),        --Ezchip LPUB Module
                bnameME60ME01LPUC0(159765),         --Ezchip LPUC Module

                bnameME60MPUC(159766),                 --ME60-16 MPU Module
                bnameME60SFUC(159767),                 --ME60-16 SFU Module
                bnameME60SFUD(159768),                  --ME60-16 SFU Module

-- S9300:       0x000A1000~0x000A1fff(659456~663551)
                bnameLE01SRUA(659456),                   --Switching and Routing Unit Board
                bnameLE01G48SA(659457),                  --48-Port 100/1000BASE-X Interface Card(EA,SFP)
                bnameLE01G24SA(659458),                  --E-product,LE01G24S,24Gig-Ethernet SFP Interface Board,1*1
                bnameLE01G48SE(659459),
                bnameLE01G48SC(659460),                  --48-Port 100/1000BASE-X Interface Card(EC,SFP)
                bnameLE01G48SD(659461),                  --48-Port 100/1000BASE-X Interface Card(ED,SFP)
                bnameLE01POWER(659462),                  --Quidway S9300,LE02CMUA,Centralized Monitoring Board,1*2
                bnameLE01FAN(659463),                    --Metro Ethernet E Product,LE02FCMA,Fan Monitor and Control Board,1*3
                bnameLE0MSRUA(659464),                   --Quidway S9300,LE02SRUA,Switch and Routing Unit(256G Switch Capacity),1*1
                bnameLE0D00SRUB00(659465),                    --Main Control Unit
                bnameLE0MMCUA(659466),                   --Main Control Unit
                bnameLE0DCMUA0000(659467),
                bnameLE0MG48TC(659468),                  --Quidway S9300,LE02G48TC,48-Port 1000BASE-T Interface Card(EC,RJ45),128K MAC,1*1
                bnameLE02G48VC(659469),
                bnameLE0MX4UXC(659470),                  --E-product,LE02X4UXC,40G Ethernet XFP Interface Board,1*1
                bnameLE0MX2UXC(659471),                  --E-product,LE02X2UXC,20G Ethernet XFP Interface Board,1*1
                bnameLE0D0S24XC00(659472),
                bnameLE02T24XC(659473),
                bnameLE02V24XC(659474),
                bnameLE0MG48SC(659475),                  --Quidway S9300,LE02G48SC,48-Port 1000BASE-X Interface Card(EC,SFP),128K MAC,1*1
                bnameLE0MG24SC(659476),                  --24-Port 100/1000BASE-X Interface Card(EC,SFP)
                bnameLE02G24TC(659477),
                bnameLE0MG48TD(659478),                  --Quidway S9300-LE02G48TD-48-Port 1000BASE-T Interface Card-512K MAC-1*1
                bnameLE02G48VD(659479),
                bnameLE0DX4UXED00(659480),
                bnameLE02X2UXD(659481),
                bnameLE02S24XD(659482),
                bnameLE02T24XD(659483),
                bnameLE02V24XD(659484),
                bnameLE0MG48SD(659485),                  --48-Port 1000BASE-X Interface
                bnameLE0MG24SD(659486),                  --24-Port 100/1000BASE-X Interface Card(ED,SFP)
                bnameLE0MG48SA(659487),                  --Quidway S9300,LE02G48SA,48-Port 1000BASE-X Interface Card(EA,SFP),32K MAC,1*1
                bnameLE0MG48TA(659488),                  --Quidway S9300,LE02G48TA,48-Port 1000BASE-T Interface Card(EA,RJ45),32K MAC,1*1
                bnameLE02G48VA(659489),
                bnameLE0MX4UXA(659490),                  --4-Port 10GBASE-X Interface Card(EA,XFP)
                bnameLE0MX2UXA(659491),                  --2-Port 10GBASE-X Interface Card(EA,XFP)
                bnameLE0DS24XEA00(659492),                  --24-Port 100/1000BASE-X and 2-Port 10GBASE-X Interface Card(EA,SFP/XFP)
                bnameLE0DT24XEA00(659493),                  --24-Port 100/1000BASE-T and 2-Port 10GBASE-X Interface Card(EA,RJ45/XFP)
                bnameLE02V24XA(659494),
                bnameLE0MG24SA(659495),                  --Quidway S9300,LE02G24SA,24-Port 1000BASE-X Interface Card(SI,SFP),32K MAC,1*1
                bnameLE02G24TA(659496),
                bnameLE0MG24CA(659497),                  --Quidway S9300,LE02G24CA,24-Port 1000BASE-X and 8-Port 1000BASE-T Combo Interface Card(SI,SFP/RJ45),1*1
                bnameLE0DX12XSA00(659498),                  --12-Port 10GBASE-X Interface Card(SA,SFP+)
                bnameLE02E4UAA(659499),
                bnameLE0D0E12GA00(659500),                  --12-Port EPON Interface and 12-Port 1000BASE-X Interface Card (SFP)
                bnameLE02X2NXA(659501),                  --2-Port 10GBASE-X NP Interface Card(NP,XFP)
                bnameLE02G24NA(659502),                  --24-Port 1000BASE-X NP Interface Card(NP,SFP)
                bnameLE01G48SB(659503),
                bnameLE01MCUA(659504),                  --Main Control Unit
                bnameLE0D00SRUB00VB(659505),                --LE02SRUB_VB
                bnameLE0MSRUAVB(659506),                --LE02SRUA_VB
                bnameLE0MF48SA(659507),                 --48-Port 100BASE-FX Interface Card(EA,SFP)
                bnameLE0MF48SC(659508),                 --48-Port 100BASE-FX Interface Card(EC,SFP)
                bnameLE02F48SD(659509),                 --48-Port 100BASE-FX Interface Card(ED,SFP)
                bnameLE0MF48TA(659510),                 --48-Port 100/1000BASE-T Interface Card(EA,RJ45)
                bnameLE0MF48TC(659511),                 --48-Port 100/1000BASE-T Interface Card(EC,RJ45)
                bnameLE02F48TD(659512),                 --48-Port 100/1000BASE-T Interface Card(ED,RJ45)
                bnameLE02T24SA(659513),                 --24-Port 100/1000BASE-T and 8-Port 100/1000BASE-X Interface Card(EA,RJ45/SFP)
                bnameLE0DSRUA(659514),                  --Main Control Unit(BITS/1588)
                bnameLE0DMCUA(659515),                  --Main Control Unit(BITS/1588)
                bnameLE0D0VAMPA00(659516), --Valude-added Services Unit
                bnameLE02G48TH(659517),
                bnameLE0DG48VEA00(659518),
                bnameLE0D0WMNPA00(659519),  --WAN Interface Services Process Unit
                bnameLE0DG48CEAT0(659520), --12-port 100/1000BASE-X and 36-port 100/1000BASE-T Interface Card (32K MAC)
                bnameLE0DF48TFA00(659521),  --48-Port 100BASE-T Interface Card(32K MAC)
                bnameLE0DG48SFA00(659522),  --48-Port 1000BASE-T Interface Card(32K MAC)
                bnameLE0DG48TFA00(659523),  --48-Port 1000BASE-T Interface Card(32K MAC)
                bnameLE02X48SSA(659524),  --48-Port 10GBASE-X Interface Card
                bnameLE02DPDA(659525),
                bnameLE02LEDA(659526),
                bnameLE0DG24CEAS0(659527), --24-Port 100/1000BASE-X and 8-Port 100/1000BASE-T Combo Interface Card(EA,SFP/RJ45,1588)
                bnameLE02L4UFFC(659528),  --4-Port 40GBASE-X Interface Card(FC,CFP)
                bnameLE0DG48TBC00(659529),  --48-Port 100/1000BASE-T Interface Card(BC,RJ45)
                bnameLE0DG48SBC00(659530),  --48-Port 100/1000BASE-X Interface Card(BC,SFP)
                bnameLE0DG24TFA00(659531),  --24-Port 100/1000BASE-T Interface Card(FA,RJ45)
                bnameLE02S24XEJ(659532),  --24-Por 100/1000BASE-X and 2-Port 10GBASE-X Interface Card(EC,SFP/XFP,1588)
                bnameLE0DX40SFC00(659533),  --40-Port 10GBASE-X Interface Card(FC,SFP+)
                bnameLE0DX16SFC00(659534),  --16-Port 10GBASE-X Interface Card(FC,SFP+)
                bnameLE2D2X08SED0(659535),  --8-Port 10GBASE-X Interface Card(ED,SFP+)
                bnameLE02L8UQFC(659536),  --8-Port 40GBASE-X Interface Card(FC,QSFP+)
                bnameLE2D2SRUDC00(659537),   --Quidway S9706/S9712,Main Control Unit D,Clock
                bnameLE2D2MB86S00(659538),   --X86 Service Process Mother board
                bnameLE1D2L02QFC0(659539),   --2-port 40GBASE-X interface card(FC,QSFP+)
                bnameLE2D2L08QFC0(659540),   --8-port 40GBASE-X interface card(FC,QSFP+)
                bnameLE2D2X08SED4(659541),   --8-Port 10GBASE-X Interface Card(ED,SFP+)
                bnameLE2D2X16SFC1(659542),   --16-Port 10GBASE-X Interface Card(FC,SFP+) FCC
                bnameLE2D2X40SFC1(659543),   --40-Port 10GBASE-X Interface Card(FC,SFP+) FCC
                bnameLE2D2X08SED1(659544),   --8-Port 10GBASE-X Interface Card(ED,SFP+) FCC
                bnameLE2D2X08SED5(659545),   --8-Port 10GBASE-X Interface Card(ED,SFP+) FCC
                bnameLE2D2SRUDC01(659546),   --Quidway S9706/S9712,Main Control Unit D,Clock FCC
                bnameLE1D2X12SEE0(659547),   --12-Port 10GBASE-X Interface Card(EE,SFP+)
                bnameLE1D2X24SEE0(659548),   --24-Port 10GBASE-X Interface Card(EE,SFP+)
                bnameLE1D2X12SED0(659549),   --12-Port 10GBASE-X Interface Card(ED,SFP+)
                bnameLE1D2X24SED0(659550),   --24-Port 10GBASE-X Interface Card(ED,SFP+)
                bnameLE02SRUC(659551),       --S9706/S9712,Main Control Unit C,Option clock
                bnameLH03MCUA(659552),
                bnameLH02SRUD0(659553),
                bnameLH02G48TC(659554),
                bnameLH02X4UXC(659555),
                bnameLH02S24XC(659556),
                bnameLH02G48SC(659557),
                bnameLH02X4UXD(659558),
                bnameLH02T24XA(659559),
                bnameLH02X12SA(659560),
                bnameLH1D2L02QFC0(659561),
                bnameLH1D2X08SED4(659562),
                bnameLE1D2X02XEC1(659563),      --S9300,LE1D2X02XEC1,2-Port 10GBASE-X Interface Card(EC,XFP),FCC,128K MAC-1*1
                bnameLE1D2X04XEC1(659564),      --S9300,LE1D2X04XEC1,4-Port 10GBASE-X Interface Card(EC,XFP),FCC,128K MAC-1*1
                bnameLE1D2G48TX1E(659565),      --S9300,48-Port 10/100/1000BASE-T Interface Card(XF,RJ45)
                bnameLE1D2G48SX1E(659566),      --S9300,48-Port 100/1000BASE-X Interface Card(XF,SFP)
                bnameLE1D2S04SX1E(659567),      --S9300,4-Port 10GBASE-X and 24-Port 100/1000BASE-X and 8-Port 10/100/1000BASE-T Combo Interface Card(XF,RJ45/SFP/SFP+)
                bnameLE1D2S08SX1E(659568),      --S9300,8-Port 10GBASE-X and 8-Port 100/1000BASE-X and 8-Port 10/100/1000BASE-T Combo Interface Card(XF,RJ45/SFP/SFP+)
                bnameLH2D2G48TX1E(659569),      --S9300E,48-Port 10/100/1000BASE-T Interface Card(XF,RJ45)
                bnameLH2D2G48SX1E(659570),      --S9300E,48-Port 100/1000BASE-X Interface Card(XF,SFP)
                bnameLH2D2S04SX1E(659571),      --S9300E,4-Port 10GBASE-X and 24-Port 100/1000BASE-X and 8-Port 10/100/1000BASE-T Combo Interface Card(XF,RJ45/SFP/SFP+)
                bnameLH2D2S08SX1E(659572),      --S9300E,8-Port 10GBASE-X and 8-Port 100/1000BASE-X and 8-Port 10/100/1000BASE-T Combo Interface Card(XF,RJ45/SFP/SFP+)
                bnameLE2D2X48SEC0(659573),      --S9300,48-Port 10GBASE-X Interface Card(EC,SFP+)  modify:LE2D2X48SED0 changed to LE2D2X48SEC0,the LE2D2X48SED0 does not support,and the 659573 was distribute to LE2D2X48SEC0 Actually
                bnameLH2D2X48SEC0(659574),      --S9300E,48-Port 10GBASE-X Interface Card(ED,SFP+)
                bnameLE1D2ACU2000(659575),      --S9300,ACU2
                bnameLH2D2ACU2000(659576),      --S9300E,ACU2
                bnameLE1D2FW00S01A(659577),     --S9300/S9300E,20G Firewall Unit
                bnameLE1D2SRUH000(659578),      --S9306/S9312,Main Control Unit H
                bnameLE2D2SRUC000(659579),      --S9306E/S9312E,Main Control Unit C,Option clock
                bnameLE1D2C02FEE0(659580),      --S9300/S9300E, 2-Port 100GBASE-X Interface Card(EE,CFP)
                bnameLE1D2X32SSC0(659581),      --S9300/S9300E, 32-Port 10GBASE-X Interface Card(SC,SFP+)
                bnameLE1D2X16SSC2(659582),      --S9300/S9300E, 16-Port 10GBASE-X Interface Card(SC,SFP+)
                bnameLE1D2G48VEA2(659583),      --S9300, 48-Port 10/100/1000BASE-T POE Interface Card(EA,RJ45,POE,EEE)
                bnameLE1D2X08SSC0(659584),      --S9300, 8-Port 10GBASE-X Interface Card(SC,SFP+)
                bnameLE1D2X12SSC0(659585),      --S9300  12-Port 10GBASE-X Interface Card(SC,SFP+)
                bnameLE1D2S24XED0(659586),      --S9300  24-Port 100/1000BASE-X and 2-Port 10GBASE-X Interface Card(ED,SFP/XFP)
                bnameLE1D2S04SEC0(659587),      --S9300  4-Port 10GBASE-X and 24-Port 100/1000BASE-X and 8-Port 10/100/1000BASE-T Combo Interface Card(EC,RJ45/SFP/SFP+)
                bnameLE1D2S12SEC0(659588),      --S9300  12-Port 10GBASE-X and 36-Port 1000BASE-X Interface Card(EC,SFP+/SFP)
                bnameLE1D2S16SEC0(659589),      --S9300  16-Port 10GBASE-X and 32-Port 1000BASE-X Interface Card(EC,SFP+/SFP)
                bnameLE1D2S24SEC0(659590),      --S9300  24-Port 10GBASE-X and 24-Port 1000BASE-X Interface Card(EC,SFP+/SFP)
                bnameLE1D2S32SEC0(659591),      --S9300  32-Port 10GBASE-X and 16-Port 1000BASE-X Interface Card(EC,SFP+/SFP)
                bnameLX1D2G24SX1C(659592),      --S9300X  24-Port 100/1000BASE-X Interface Card(X1C,SFP)
                bnameLX1D2G48SX1C(659593),      --S9300X  48-Port 100/1000BASE-X Interface Card(X1C,SFP))
                bnameLX1D2G48TX1C(659594),      --S9300X  48-Port 10/100/1000BASE-T Interface Card(X1C,RJ45)
                bnameLX1D2X04SX3E(659595),      --S9300X  4-Port 10GBASE-X Interface Card(X3E,SFP+)
                bnameLX1D2X04SX3D(659596),      --S9300X  4-Port 10GBASE-X Interface Card(X3D,SFP+)
                bnameLX1D2S04SX3E(659597),      --S9300X  4-Port 10GBASE-X and 24-Port 100/1000BASE-X and 8-Port 10/100/1000BASE-T Combo Interface Card(X3E,RJ45/SFP/SFP+)
                bnameLX1D2S04SX3D(659598),      --S9300X  4-Port 10GBASE-X and 24-Port 100/1000BASE-X and 8-Port 10/100/1000BASE-T Combo Interface Card(X3D,RJ45/SFP/SFP+)
                bnameLX1D2S08SX3E(659599),      --S9300X  8-Port 10GBASE-X and 8-Port 100/1000BASE-X and 8-Port 10/100/1000BASE-T Combo Interface Card(X3E,RJ45/SFP/SFP+)
                bnameLX1D2S08SX3D(659600),      --S9300X  8-Port 10GBASE-X and 8-Port 100/1000BASE-X and 8-Port 10/100/1000BASE-T Combo Interface Card(X3D,RJ45/SFP/SFP+)
                bnameLX1D2G24SX3E(659601),      --S9300X  24-Port 100/1000BASE-X Interface Card(X3E,SFP)
                bnameLX1D2G24SX3D(659602),      --S9300X  24-Port 100/1000BASE-X Interface Card(X3D,SFP)
                bnameLX1D2G48SX3E(659603),      --S9300X  48-Port 100/1000BASE-X Interface Card(X3E,SFP)
                bnameLX1D2G48SX3D(659604),      --S9300X  48-Port 100/1000BASE-X Interface Card(X3D,SFP)
                bnameLX1D2G48TX3E(659605),      --S9300X  48-Port 10/100/1000BASE-T Interface Card(X3E,RJ45)
                bnameLX1D2G48TX3D(659606),      --S9300X  48-Port 10/100/1000BASE-T Interface Card(X3D,RJ45)
                bnameLX1D2X08SX2C(659607),      --S9300X  8-Port 10GBASE-X Interface Card(X2C,SFP+)
                bnameLX1D2X16SX2C(659608),      --S9300X  16-Port 10GBASE-X Interface Card(X2C,SFP+)
                bnameLX1D2X32SX2C(659609),      --S9300X  32-Port 10GBASE-X Interface Card(X2C,SFP+)
                bnameLX1D2C02FX2E(659610),      --S9300X  2-Port 100GBASE-X Interface Card(EE,CFP)
                bnameLX1D2MFUAC00(659611),      --S9300X  S9303X Main Control Unit A(Optional Clock)
                bnameLX1D2MFUC000(659612),      --S9300X  S9306X/S9312X Main Control Unit C(Optional Clock)
                bnameLX1D2MFUF000(659613),      --S9300X  S9306X/S9312X,Main Control Unit F
                bnameLE1D2X48SEC1(659614),      --S9300   48-Port 10GBASE-X Interface Card(EC,SFP+)
                bnameLE1D2SRUE000(659615),      --S9300   Main Control Unit E
                bnameLE1D2SRUKC00(659616),      --S9300   Main Processing Unit K(Optional clock)
                bnameLX1D2MFUD000(659617),      --S9300X   Main Processing Unit D
                bnameLX1D2MFUXC00(659618),      --S9300X   Main Processing Unit X(Optional clock)
                bnameLE1D2SFUK000(659619),      --S9300   Switch Fabric Unit K
                bnameLX1D2SFUX000(659620),      --S9300X   Switch Fabric Unit X
                bnameLE1D2L08QX2E(659621),      --S9300   8-Port 40GE QSFP+ Interface Card(X2E,QSFP+)
                bnameLE1D2X32SX2S(659622),      --S9300   32-Port 10GE SFP+ Interface Card(X2S,SFP+)
                bnameLE1D2X32SX2E(659623),      --S9300   32-Port 10GE SFP+ Interface Card(X2E,SFP+)
                bnameLE1D2S24SX2S(659624),      --S9300   24-Port 10GE SFP+ Interface and 8-Port GE SFP Interface Card(X2S,SFP+)
                bnameLE1D2S24SX2E(659625),      --S9300   24-Port 10GE SFP+ Interface and 8-Port GE SFP Interface Card(X2E,SFP+)
                bnameLE1D2S16SX2S(659626),      --S9300   16-Port 10GE SFP+ Interface and 16-Port GE SFP Interface Card(X2S,SFP+)
                bnameLE1D2S16SX2E(659627),      --S9300   16-Port 10GE SFP+ Interface and 16-Port GE SFP Interface Card(X2E,SFP+)
                bnameLE1D2C04HX2S(659628),      --S9300   4-Port 100GE QSFP28 Interface Card(X2S,QSFP28)
                bnameLE1D2C04HX2E(659629),      --S9300   4-Port 100GE QSFP28 Interface Card(X2E,QSFP28)
                bnameLE1D2H02QX2S(659630),      --S9300   2-Port 100GE QSFP28 Interface and 2-Port 40GE QSFP+ Interface Card(X2S,QSFP28)
                bnameLE1D2H02QX2E(659631),      --S9300   2-Port 100GE QSFP28 Interface and 2-Port 40GE QSFP+ Interface Card(X2E,QSFP28)
                bnameLE1D2X48SX2S(659632),      --S9300   48-Port 10GE SFP+ Interface Card(X2S,SFP+)
                bnameLX1D2X48SX2C(659633),      --S9300X  48-Port 10GBASE-X Interface Card(X2C,SFP+)
                bnameLX1D2S24XX1D(659634),      --S9300X  24-Port 100/1000BASE-X and 2-Port 10GBASE-X Interface Card(X1D,SFP/XFP)
                bnameLX1D2L08QX4D(659635),      --S9300X  8-Port 40GE QSFP+ Interface Card(X4D,QSFP+)
                bnameLX1D2X32SX4C(659636),      --S9300X  32-Port 10GE SFP+ Interface Card(X4C,SFP+)
                bnameLX1D2X32SX4D(659637),      --S9300X  32-Port 10GE SFP+ Interface Card(X4D,SFP+)
                bnameLX1D2S24SX4C(659638),      --S9300X  24-Port 10GE SFP+ Interface and 8-Port GE SFP Interface Card(X4C,SFP+)
                bnameLX1D2S24SX4D(659639),      --S9300X  24-Port 10GE SFP+ Interface and 8-Port GE SFP Interface Card(X4D,SFP+)
                bnameLX1D2S16SX4C(659640),      --S9300X  16-Port 10GE SFP+ Interface and 16-Port GE SFP Interface Card(X4C,SFP+)
                bnameLX1D2S16SX4D(659641),      --S9300X  16-Port 10GE SFP+ Interface and 16-Port GE SFP Interface Card(X4D,SFP+)
                bnameLX1D2C04HX4C(659642),      --S9300X  4-Port 100GE QSFP28 Interface Card(X4C,QSFP28)
                bnameLX1D2C04HX4D(659643),      --S9300X  4-Port 100GE QSFP28 Interface Card(X4D,QSFP28)
                bnameLX1D2H02QX4C(659644),      --S9300X  2-Port 100GE QSFP28 Interface and 2-Port 40GE QSFP+ Interface Card(X4C,QSFP28)
                bnameLX1D2H02QX4D(659645),      --S9300X  2-Port 100GE QSFP28 Interface and 2-Port 40GE QSFP+ Interface Card(X4D,QSFP28)
                bnameLX1D2X48SX4C(659646),      --S9300X  48-Port 10GE SFP+ Interface Card(X4C,SFP+)
             -- bnameLE2D2X48SEC0(659647),      S9300   48-Port 10GBASE-X Interface Card(EC,SFP+)  modify:LE2D2X48SEC0 is a old board,already has id,the id is 659573,so this id Abandoned
                bnameLE1D2X32SEC0(659648),      --S9300   32-Port 10GE SFP+ Interface Card(EC,SFP+)
                bnameLE1D2H02QEC0(659649),      --S9300   2-Port 100GE QSFP28 Interface and 2-Port 40GE QSFP+ Interface Card(EC,QSFP28)
                bnameLE1DAS24SX2S(659650),      --S9300   24-Port 10GE SFP+ Interface and 24-Port GE SFP Interface Card(X2E,SFP+)
                bnameLE1D2X32SX2H(659651),      --S9300   32-Port 10GE SFP+ Interface Card(X2H,SFP+)
                bnameLE1D2S08SX2S(659652),      --S9300   8-Port 10GE SFP+ Interface and 24-Port GE SFP Interface Card(X2S,SFP+)
                bnameLE1D2C04HX2H(659653),      --S9300   4-Port 100GE QSFP28 Interface Card(X2H,QSFP28)

                bnameLE3D2C04HX2L(659654),      --S9310X  4-Port 100GE QSFP28 Interface Card(X2L,QSFP28)
                bnameLE3D2X48SX2L(659655),      --S9310X  48-Port 10GE SFP+ Interface Card(X2L,SFP+)
                bnameLE3D2G48SX1L(659659),      --S9310X  48-Port 100/1000BASE-X Interface Card(X1L,SFP)
                bnameLE3D2G48TX1L(659660),      --S9310X  48-Port 100/1000BASE-T Interface Card(X1L,RJ45)

                bnameLE1D2S08SX2E(659661),      --S9300 S9300E S9310X  8-Port 10GE SFP+ Interface and 24-Port GE SFP Interface Card(X2E,SFP+)  for V2R11
                bnameLE1D2S04SX1C(659662),      --4-Port 10GBASE-X and 24-Port 100/1000BASE-X and 8-Port 10/100/1000BASE-T Combo Interface Card(X1C,RJ45/SFP/SFP+) for V2R11
                bnameLE1D2G48TX1C(659663),      --48-Port 10/100/1000BASE-T Interface Card(X1C,RJ45) for V2R11
                bnameLE1D2G48SX1C(659664),      --48-Port 100/1000BASE-X Interface Card(X1C,SFP) for V2R11

                bnameLE1D2L16QX2H(659665),    --16-Port 40GE QSFP+ Interface Card(X2H,QSFP+) for 9310 v2r11
                bnameLE1D2C08HX2H(659666),    --8-Port 100GE QSFP28 Interface Card(X2H,QSFP28)  for 9310 v2r11
                bnameLE1D2SRUKC01(659667),      --S9310,Main Processing Unit K(Support Security Startup) for v2r12
                bnameLE1D2SRUH002(659668),      --S9306/S9312,Main Control Unit H(Support Security Startup) for v2r12
                bnameLE1D2MPUA000(659669),      --S9316 Main Processing Unit A(Optional clock) for v2r12
                bnameLE1D2SFUD000(659670),      --S9316 Switch Fabric Unit D for v2r12
                bnmaeLE1D2G48TX2S(659671),      --S9300 48-Port 100/1000BASE-T Interface Card(X2S,RJ45) for v2r13
                bnameLE3D2G48TX2L(659672),      --S9300X 48-Port 100/1000BASE-T Interface Card(X2L,RJ45) for v2r13
                bnameLE1D2G48TX2E(659673),      --S9300 48-Port 100/1000BASE-T Interface Card(X2E,RJ45) for v2r13
                bnameLE1D2G48TX2H(659674),      --S9300 48-Port 100/1000BASE-T Interface Card(X2H,RJ45) for v2r13
                bnameLE1D2G48SX2S(659675),      --S9300 48-Port 100/1000BASE-X Interface Card(X2S,SFP) for v2r13
                bnameLE1D2G48SX2E(659676),      --S9300 48-Port 100/1000BASE-X Interface Card(X2E,SFP) for v2r13
                bnameLE1D2G48SX2H(659677),      --S9300 48-Port 100/1000BASE-X Interface Card(X2H,SFP) for v2r13
                bnameLE3D2G48SX2L(659678),      --S9300X 48-Port 100/1000BASE-X Interface Card(X2L,SFP) for v2r13
                bnameLE1D2MCUBC00(659679),      --S9303,Main Processing Unit B(Optional clock) for v2r13
                bnameLE3D2X22SX2L(659680),        --S9300X 22-Port 10GE SFP+ Interface Card(X2L,SFP+) for v2r12c00
                bnameLE1D2X24SX2S(659681),      --S9300 24-Port 10GE SFP+ Interface Card(X2S,SFP+) for v2r12c00
                bnameLE1D2X08SX2E(659682),      --S9300 8-Port 10GE SFP+ Interface Card(X2E,SFP+) for v2r13
                bnameLE1D2S04SX2E(659683),      --S9300 4-Port 10GE SFP+ Interface and 44-Port GE SFP Interface Card(X2E,SFP+) for v2r13
                bnameLE1D2G24SX2E(659684),      --S9300 24-Port 100/1000BASE-X Interface Card(X2E,SFP) for v2r13
                bnaemLE1D2X08SX2H(659685),      --S9300 8-Port 10GE SFP+ Interface Card(X2H,SFP+) for v2r13
                bnameES1D2MCUDC00(659686),      --S9303 main control unit D for v2r13c99
                bnameLSS3SRUHX100(659687),      --S9300 main control unit H for v2r13c99
                bnameLE1M2G48TX5S(659688),      --48-port 10/100/1000BASE-T interface card (X5S,RJ45) for v2r13c99
                bnameLE1M2G48TX5E(659689),      --48-port 10/100/1000BASE-T interface card (X5E,RJ45) for v2r13c99
                bnameLST3X48SX6S0(659690),      --48-port 10GE SFP+ interface card (X6S,SFP+) for v2r13c99
                bnameLST3X48SX6E0(659691),       --48-port 10GE SFP+ interface card (X6E,SFP+) for v2r13c99
                bnameLST3G48SX6S0(659692),      --48-port 1000BASE-X interface card (X6S,SFP) for v2r13c99
                bnameLST3G48SX6E0(659693),      --48-port 1000BASE-X interface card (X6E,SFP) for v2r13c99
                bnameLSS3X48SX6S1(659694),      --48-port 10GE SFP+ interface card (X6S,SFP+) S9310/S9310X  for v2r13c99
                bnameLSS3X48SX6E1(659695),      --48-port 10GE SFP+ interface card (X6E,SFP+) S9310/S9310X  for v2r13c99
                bnameLST3X48SX6H1(659696),      --48-port 10GE SFP+ interface card (X6H,SFP+) S9310/S9310X  for v2r13c99
                bnameLSS3SRUHA100(659697),      --S9306/S9312 main control unit H for v2r19c00
                bnameLSS3SFUKA200(659698),      --S9310 switch fabric unit K for v2r19c00
                bnameLSX3SFUXA200(659699),      --S9310X switch fabric unit X for v2r19c00
                bnameLE02CMUA(659700),              --Centralized Monitoring Board for v2r19c00
                bnameLSS3X24BX6S0(659701),      --24-port 10GE SFP+ interface and 24-port GE SFP interface card (X6S,SFP+) for v2r13c99
                bnameLSS3X24BX6E0(659702),      --24-port 10GE SFP+ interface and 24-port GE SFP interface card (X6E,SFP+) for v2r13c99
                bnameLST3C06HX6S0(659703),      --6-port 100GE QSFP28 interface card (X6S,QSFP28) for v2r19c00
                bnameLST3C06HX6E0(659704),      --6-port 100GE QSFP28 interface card (X6E,QSFP28) for v2r19c00
                bnameLSS3C06HX6S1(659705),      --6-port 100GE QSFP28 interface card (X6S,QSFP28) for v2r19c00
                bnameLSS3C06HX6E1(659706),      --6-port 100GE QSFP28 interface card (X6E,QSFP28) for v2r19c00
                bnameLST3C06HX6H1(659707),      --6-port 100GE QSFP28 interface card (X6H,QSFP28) for v2r19c00
                bnameLST3X24BX6S0(659708),       -- 24-port 10GE SFP+ interface and 24-port GE SFP interface card (X6S,SFP+) for v2r19c00
                bnameLST3X24BX6E0(659709),       --24-port 10GE SFP+ interface and 24-port GE SFP interface card (X6E,SFP+) for v2r19c00
                bnameLST3X04BX6S0(659710),       --4-port 10GE SFP+ interface and 44-port GE SFP interface card (X6S,SFP+) for v2r19c00
                bnameLST3X16BX6S0(659711),       --16-port 10GE SFP+ interface and 32-port GE SFP interface card (X6S,SFP+) for v2r19c00
                bnameLST3X08BX6S0(659712),       --8-port 10GE SFP+ interface and 40-port GE SFP interface card (X6S,SFP+)  for v2r19c00
                bnameLST3X02BX6S0(659713),       --2-port 10GE SFP+ interface and 24-port GE SFP interface card (X6E,SFP+) for v2r19c00
                bnameLST3X32SX6E0(659714),       --32-port 10GE SFP+ interface card (X6E,SFP+) for v2r19c00
                bnameLST3X16SX6E0(659715),       --16-port 10GE SFP+ interface card (X6E,SFP+) for v2r19c00
                bnameLST3X08SX6S0(659716),       --8-port 10GE SFP+ interface card (X6S,SFP+) for v2r19c00
                bnameLST3MPUE0000(659717),      --S9300X main control unit E for v2r19c00
                bnameLST3SFUEX100(659718),      --S9300X switch fabric unit E(X1) for v2r19c00
                bnameLST3X04BX6E0(659719),       --4-port 10GE SFP+ interface and 44-port GE SFP interface card (X6E,SFP+) for v2r19c00
                bnameLST3X24SX6E0(659720),       --24-port 10GE SFP+ interface card (X6E,SFP+)  for v2r19c00
                bnameLST3X08BX6E0(659721),       --8-port 10GE SFP+ interface and 24-port GE SFP interface card (X6E,SFP+) for v2r19c00
                bnameLST3X16BX6E0(659722),       --16-port 10GE SFP+ interface and 24-port GE SFP interface card (X6E,SFP+)  for v2r19c00
                bnameLST3X36SX6E0(659723),       --36-port 10GE SFP+ interface card (X6E,SFP+)  for v2r19c00
                bnameLST3C04HX6E0(659724),       --4-port 100GE QSFP28 interface card (X6E,QSFP28)  for v2r19c00
                bnameLST3SFUHX100(659725),      --S12700E switch fabric unit H(X1)  for v2r19c00
                bnameLST3SFUMX100(659726),      --S12700E switch fabric unit M(X1) for v2r19c00
                bnameLST3C24HX6S0(659727),       --24-port 100GE QSFP28 interface card (X6S,QSFP28) for v2r19c00
                bnameLST3G48TX5S1(659728),       --48-port 10/100/1000BASE-T interface card (X5S,RJ45) for v2r19c00 S9300x
                bnameLST3G48TX5E1(659729),       --48-port 10/100/1000BASE-T interface card (X5E,RJ45) for v2r19c99 S9300x
                bnameLE0D0G48SC01(659730),      --48-port 100/1000 SFP+ interface card for v2r19c00 S9300
                bnameLE0D0G48TC01(659731),      --48-port 00/1000BASE-T interface card for v2r19c00 S9300
                bnameLST3Y40SX6H0(659732),       --40-port 25GE SFP28 interface card (X6H,SFP28) for S9300X

                bnameLSS3G48TA1S0(659734), --48-port 10/100/1000BASE-T PoE interface card (EA1, RJ45) for V2R20C00 S9300
                bnameLSS3G48TA1E0(659735), --48-port 10/100/1000BASE-T PoE interface card (EC1, RJ45) for V2R20C00 S9300
                bnameLSS3G48VA1S0(659736), --48-port 10/100/1000BASE-T PoE interface card (EA1, RJ45, PoE++) for V2R20C00 S9300
                bnameLSS3G48SA1S0(659737), --48-Port 100/1000BASE-X Interface Card(EA1,SFP) for V2R20C00 S9300
                bnameLSS3G48SA1E0(659738), --48-Port 100/1000BASE-X Interface Card(EC1,SFP) for V2R20C00 S9300
                bnameLSS3X48SA100(659742), --48-Port 10GBASE-X Interface Card(EC,SFP+) for V2R20C00
                bnameLST3MPUA1000(659739), --S9300XS,Main Processing Unit A(Optional clock) for V2R20C00 S9300
                bnameLSS3SRUH1000(659740), --S9306/S9312,Main Control Unit H for V2R20C00 S9300

                bnameLSS3G48SD1E0(659746), --48-port 100/1000BASE-X interface card (D1E, SFP) for V2R20C00 S9300
                bnameLSS3X24BD1E0(659747), --24-port 10GE SFP+ interface and 24-port GE SFP interface card (D1E,SFP+) for V2R20C00 S9300
                bnameLSS3X16BD1E0(659748), --16-port 10GE SFP+ interface and 16-port GE SFP interface card (D1E,SFP+) for V2R20C00 S9300
                bnameLSS3X32SD1E0(659749), --32-Port 10GBASE-X Interface card(D1E,SFP+) for V2R20C00 S9300

                bnameLSS3SRUHD000(659750), --S9306/S9312 main control unit HD for V2R20C10 S9300
                bnameLST3MPUE0001(659752), --S9300X main control unit E for v2r20c10
                bnameLSS3L12QX6E0(659758), --12-port 40GE QSFP+ inferface card (X6E,QSFP28) for v2r21c00
                bnameLST3L12QX6E0(659759), --12-port 40GE QSFP+ inferface card (X6E,QSFP28) for v2r21c00
                bnameLSS3M24VX6E0(659753), --24-port 100M/1G/2.5G/5G/10G and 24-port 100M/1G interface card (X6S,RJ45,PoE++) for v2r21c00
                bnameLST3M24BX6E0(659754), --24-port 100M/1G/2.5G/5G/10G and 24-port 100M/1G interface card (X6E,RJ45) for v2r21c00
                bnameLSS3G48TX6E0(659755), --48-port 100/1000BASE-T interface card (X6E,RJ45) for v2r21c00
                bnameLST3G48TX6E0(659756), --48-port 100/1000BASE-T interface card (X6E,RJ45) for v2r21c00
                bnameLST3G48TX6S0(659757), --48-port 100/1000BASE-T interface card (X6S,RJ45) for v2r21c00
                bnameLSS3MCUA1000(659743), --S9303 main control unit A1 for v2r21c00
                bnameLSS3MCUD0001(659761), --S9303 main control unit D for v2r21c01
                bnameLSS3SRUHX101(659762), --S9306/S9312 main control unit H(X1) for v2r21c01          
                bnameLST3MPUEC000(659760), --S9300X main control unit EC for v2r21c01    
                bnameLSS3X16SA1E0(659763), --16-port 10GBASE-X interface card(SC,SFP+) for v2r21c01
                bnameLSS3X32SA1E0(659764), --32-port 10GBASE-X interface card(SC,SFP+) for v2r21c01 
                bnameLSG3SRUFX500(659767), --S9300XE-8 main control unit F
                bnameLSG3SRUEX500(659768), --S9300XE-4 main control unit E
                bnameLSG3C16QX1E0(659769), --16-port 40GBASE-X interface card(QSFP+) or 8-port 100GBASE-X interface card(QSFP28)
                bnameLSG3C04HX1E0(659770), --4-port 100GBASE-X interface card(QSFP28)
                bnameLSG3X72SX1E0(659771), --72-port 100M/1G/10GBASE-X interface card (SFP+)
                bnameLSG3X48SX2E0(659772), --48-port 100M/1G/10GBASE-X interface card (SFP+)
                bnameLSG3X24SX1E0(659773), --24-port 100M/1G/10GBASE-X interface card (SFP+)
                bnameLSG3G48SX1E0(659774), --48-port 100/1000BASE-X interface card (SFP)
                bnameLSG3G48TX1E0(659775), --48-port 10/100/1000BASE-T interface card (RJ45)
                bnameLSG3SFUAX100(659776), --S9300XE Switch Fabric Unit A (X1)    
                bnameLSG3X48SX2E1(659777), --48-port 100M/1G/10GBASE-X interface card (SFP+)
                bnameLSG3X32SX2E0(659778), --32-port 100M/1G/10GBASE-X interface card (SFP+)
                bnameLSG3C08HX1E0(659779), --8-port 100GBASE-X interface card(QSFP28) or 16-port 40GBASE-X interface card(QSFP+)

-- S7700:       0x000A2000~0x000A2fff(663552~667647)
                bnameES0D00SRUA00(663552),      --Quidway S7700,ES02SRUA,Switch and Routing Unit(256G Switch Capacity),1*1
                bnameES0D00SRUB00(663553),      --Main Control Unit
                bnameES0D00MCUA00(663554),      --Main Control Unit
                bnameES0D0G24SA00(663555),      --Quidway S7700,ES02G24SA,24-Port 1000BASE-X Interface Card(SI,SFP),32K MAC,1*1
                bnameES0D0G24SC00(663556),      --24-Port 100/1000BASE-X Interface Card(EC,SFP)
                bnameES0D0G48TA00(663557),      --Quidway S7700,ES02G48TA,48-Port 1000BASE-T Interface Card(EA,RJ45),32K MAC,1*1
                bnameES0D0G48TC00(663558),      --Quidway S7700,ES02G48TC,48-Port 1000BASE-T Interface Card(EC,RJ45),128K MAC,1*1
                bnameES0D0G48VA00(663559),
                bnameES0D0G48SA00(663560),      --Quidway S7700,ES02G48SA,48-Port 1000BASE-X Interface Card(EA,SFP),32K MAC,1*1
                bnameES0D0G48SC00(663561),      --Quidway S7700,ES02G48SC,48-Port 1000BASE-X Interface Card(EC,SFP),128K MAC,1*1
                bnameES0D0F48TA00(663562),      --48-Port 100/1000BASE-T Interface Card(EA,RJ45)
                bnameES02F48SA(663563),         --48-Port 100BASE-FX Interface Card(EA,SFP)
                bnameES0D0G24CA00(663564),      --Quidway S7700,ES02G24CA,24-Port 1000BASE-X and 8-Port 1000BASE-T Combo Interface Card(SI,SFP/RJ45),1*1
                bnameES0D0T24XA00(663565),      --24-Port 100/1000BASE-T and 2-Port 10GBASE-X Interface Card(EA,RJ45/XFP)
                bnameES0D0S24XA00(663566),      --24-Port 100/1000BASE-X and 2-Port 10GBASE-X Interface Card(EA,SFP/XFP)
                bnameES0D0X4UXA00(663567),      --4-Port 10GBASE-X Interface Card(EA,XFP)
                bnameES0D0X4UXC00(663568),      --E-product,ES02X4UXC,40G Ethernet XFP Interface Board,1*1
                bnameES0D0X2UXA00(663569),      --2-Port 10GBASE-X Interface Card(EA,XFP)
                bnameES0D0X2UXC00(663570),      --E-product,ES02X2UXC,20G Ethernet XFP Interface Board,1*1
                bnameES0D0E12GA00(663571),      --12-Port EPON Interface and 12-Port 1000BASE-X Interface Card (SFP)
                bnameES0DG48CEAT0(663572),      --12-port 100/1000BASE-X and 36-port 100/1000BASE-T Interface Card (32K MAC)
                bnameLE0DCMUA0000S7700(663573),
                bnameES0D00SRUA00VB(663574),    --ES02SRUA_VB
                bnameES0D00SRUB00VB(663575),    --ES02SRUB_VB
                bnameES03SRUA(663576),          --Main Control Unit(BITS/1588)
                bnameES03MCUA(663577),          --Main Control Unit(BITS/1588)
                bnameES0D0F48TC00(663578),      --48-Port 100/1000BASE-T Interface Card(EC,RJ45)
                bnameES0DF48TFA00(663579),      --48-Port 100BASE-T Interface Card(32K MAC)
                bnameES0DG48TFA00(663580),      --48-Port 1000BASE-T Interface Card(32K MAC)
                bnameES0D0X12SA00(663581),
                bnameES0DG24TFA00(663582),
                bnameES1D2X04XED0(663583),      --4-Port 10GBASE-X Interface Card(ED,XFP)
                bnameES1D2G48SFA0(663584),      --48-Port 100/1000BASE-X Interface Card(FA,SFP)
                bnameES1D2G48SED0(663585),      --48-Port 100/1000BASE-X Interface Card(ED,SFP)
                bnameES1D2X16SFC0(663586),      --16-Port 10GBASE-X Interface Card(FC,SFP+)
                bnameES1D2X40SFC0(663587),      --40-Port 10GBASE-X Interface Card(FC,SFP+)
                bnameES2D2MB86S00(663588),      --X86 Service Process Mother board
                bnameES1D2L02QFC0(663589),      --2-port 40GBASE-X interface card(FC,QSFP+)
                bnameES1D2X08SED4(663590),      --8-Port 10GBASE-X Interface Card(ED,SFP+)
                bnameES1D2X08SED5(663591),      --8-Port 10GBASE-X Interface Card(ED,SFP+) FCC
                bnameES1D2G24SED0(663592),      --24-Port 100/1000BASE-X Interface Card(ED,SFP)
                bnameES1D2G48TED0(663593),      --48-Port 10/100/1000BASE-T Interface Card(ED,RJ45)
                bnameES1D2G48SBC0(663594),      --48-Port 100/1000BASE-X Interface Card(BC,SFP)
                bnameES1D2G48TBC0(663595),      --48-Port 10/100/1000BASE-T Interface Card(BC,RJ45)
                bnameES1D2S24XEC0(663596),      --24-Port 100/1000BASE-X and 2-Port 10GBASE-X Interface Card(EC,SFP/XFP)
                bnameES1D2X12SEE0(663597),      --12-Port 10GBASE-X Interface Card(EE,SFP+)
                bnameES1D2X12SED0(663598),      --12-Port 10GBASE-X Interface Card(ED,SFP+)
                bnameES1D2X02XEC1(663599),      --S7700,ES1D2X02XEC1,2-Port 10GBASE-X Interface Card(EC,XFP),FCC,128K MAC-1*1
                bnameES1D2X04XEC1(663600),      --S7700,ES1D2X04XEC1,4-Port 10GBASE-X Interface Card(EC,XFP),FCC,128K MAC-1*1
                bnameES1D2G48TX1E(663601),      --S7700,48-Port 10/100/1000BASE-T Interface Card(XF,RJ45)
                bnameES1D2G48SX1E(663602),      --S7700,48-Port 100/1000BASE-X Interface Card(XF,SFP)
                bnameES1D2S04SX1E(663603),      --S7700,4-Port 10GBASE-X and 24-Port 100/1000BASE-X and 8-Port 10/100/1000BASE-T Combo Interface Card(XF,RJ45/SFP/SFP+)
                bnameES1D2S08SX1E(663604),      --S7700,8-Port 10GBASE-X and 8-Port 100/1000BASE-X and 8-Port 10/100/1000BASE-T Combo Interface Card(XF,RJ45/SFP/SFP+)
                bnameES1D2ACU2000(663605),      --S7700,ACU2
                bnameES1D2G48VEA2(663606),      --S7700,48-Port 10/100/1000BASE-T POE Interface Card(EA,RJ45,POE,EEE)
                bnameES1D2SRUH000(663607),      --S7706/S7712,Main Control Unit H
                bnameES1D2C02FEE0(663608),      --S7700, 2-Port 100GBASE-X Interface Card(EE,CFP)
                bnameES1D2X32SSC0(663609),      --S7700, 32-Port 10GBASE-X Interface Card(SC,SFP+)
                bnameES1D2X16SSC2(663610),      --S7700, 16-Port 10GBASE-X Interface Card(SC,SFP+)
                bnameES1D2X48SEC0(663611),      --S7700, 48-Port 10GBASE-X Interface Card(EC,SFP+)
                bnameES1D2SRUE000(663612),      --S7700, Main Control Unit E
                bnameES1D2SRUKC00(663613),      --S7700, Main Processing Unit K(Optional clock)
                bnameES1D2SFUK000(663614),      --S7700, Switch Fabric Unit K
                bnameES1D2L08QX2E(663615),      --S7700 8-Port 40GE QSFP+ Interface Card(X2E,QSFP+)
                bnameES1D2X32SX2S(663616),      --S7700 32-Port 10GE SFP+ Interface Card(X2S,SFP+)
                bnameES1D2X32SX2E(663617),      --S7700 32-Port 10GE SFP+ Interface Card(X2E,SFP+)
                bnameES1D2S24SX2S(663618),      --S7700 24-Port 10GE SFP+ Interface and 8-Port GE SFP Interface Card(X2S,SFP+)
                bnameES1D2S24SX2E(663619),      --S7700 24-Port 10GE SFP+ Interface and 8-Port GE SFP Interface Card(X2E,SFP+)
                bnameES1D2S16SX2S(663620),      --S7700 16-Port 10GE SFP+ Interface and 16-Port GE SFP Interface Card(X2S,SFP+)
                bnameES1D2S16SX2E(663621),      --S7700 16-Port 10GE SFP+ Interface and 16-Port GE SFP Interface Card(X2E,SFP+)
                bnameES1D2C04HX2S(663622),      --S7700 4-Port 100GE QSFP28 Interface Card(X2S,QSFP28)
                bnameES1D2C04HX2E(663623),      --S7700 4-Port 100GE QSFP28 Interface Card(X2E,QSFP28)
                bnameES1D2H02QX2S(663624),      --S7700 2-Port 100GE QSFP28 Interface and 2-Port 40GE QSFP+ Interface Card(X2S,QSFP28)
                bnameES1D2H02QX2E(663625),      --S7700 2-Port 100GE QSFP28 Interface and 2-Port 40GE QSFP+ Interface Card(X2E,QSFP28)
                bnameES1D2X48SX2S(663626),      --S7700 48-Port 10GE SFP+ Interface Card(X2S,SFP+)
                bnameES1D2X48SEC4(663627),      --S7700 48-Port 10GBASE-X Interface Card(EC,SFP+)
                bnameES1D2MCUAC00(663628),      --S7703,Main Control Unit A(Optional Clock)
                bnameES1D2SRUAC00(663629),      --S7706/S7712,Main Control Unit A(Optional clock)
                bnameES1DAS24SX2S(663630),      --S7700 24-Port 10GE SFP+ Interface and 24-Port GE SFP Interface Card(X2E,SFP+)

                bnameES1D2L16QX2H(663631),      --16-Port 40GE QSFP+ Interface Card(X2H,QSFP+) for 7700 v2r11
                bnameES1D2C08HX2H(663632),      --8-Port 100GE QSFP28 Interface Card(X2H,QSFP28) for 7700 v2r11
                bnameES1D2SRUKC01(663633),      --S7710,Main Processing Unit K(Support Security Startup) for v2r12
                bnameES1D2SRUH002(663634),      --S7706/S7712,Main Control Unit H(Support Security Startup) for v2r12
                bnameES1D2G48VX2S(663635),      --48-Port 100/1000BASE-T POE Interface Card(X5S,RJ45,POE++) ES1D2G48VX5S for v2r13
                bnameES1D2G48VX2E(663636),      --48-Port 100/1000BASE-T POE Interface Card(X5E,RJ45,POE++) ES1D2G48VX5E for v2r13
                bnameES1D2G48TX2S(663637),      --48-Port 100/1000BASE-T Interface Card(X5S,RJ45) ES1D2G48TX5S for v2r13
                bnameES1D2G48TX2E(663638),      --48-Port 100/1000BASE-T Interface Card(X5E,RJ45) ES1D2G48TX5E for v2r13
                bnameES1D2G48SX2S(663639),      --48-Port 100/1000BASE-X Interface Card(X5S,SFP)  ES1D2G48SX5S for v2r13
                bnameES1D2G48SX2E(663640),      --48-Port 100/1000BASE-X Interface Card(X5E,SFP)  ES1D2G48SX5E for v2r13
                bnameES1D2S04SX2S(663641),      --4-Port 10GE SFP+ Interface and 44-Port GE SFP Interface Card(X5S,SFP+) ES1D2S04SX5S for v2r13
                bnameES1D2S04SX2E(663642),      --4-Port 10GE SFP+ Interface and 44-Port GE SFP Interface Card(X5E,SFP+) ES1D2S04SX5E for v2r13
                bnameES1D2G24SX2S(663643),      --24-Port 100/1000BASE-X Interface Card(X5S,SFP) ES1D2G24SX5S for v2r13
                bnameES1D2G24SX2E(663644),      --24-Port 100/1000BASE-X Interface Card(X5E,SFP) ES1D2G24SX5E for v2r13
                bnameES1D2X08SX2S(663645),      --8-Port 10GE SFP+ Interface Card(X5S,SFP+) ES1D2X08SX5S for v2r13
                bnameES1D2X08SX2E(663646),      --8-Port 10GE SFP+ Interface Card(X5E,SFP+) ES1D2X08SX5E for v2r13
                bnameES1D2MCUBC00(663647),      --S7703,Main Processing Unit B(Optional clock) for v2r13
                bnameES1D2G48TX2H(663648),      --48-Port 100/1000BASE-T Interface Card(X5H,RJ45) ES1D2G48TX5H for v2r13
                bnameES1D2G48SX2H(663649),      --48-Port 100/1000BASE-X Interface Card(X5H,SFP) ES1D2G48SX5H for v2r13
                bnameES1D2X08SX2H(663650),      --8-Port 10GE SFP+ Interface Card(X5H,SFP+) ES1D2X08SX5H for v2r13
                bnameES1D2G48TX5L(663651),      --48-port 100/1000BASE-T interface card (X5L, RJ45) for v2r13
                bnameES1D2G48SX5L(663652),      --48-port 100/1000BASE-X interface card (X5L, SFP) for v2r13
                bnameES1D2G24SX5L(663653),      --24-port 100/1000BASE-X interface card (X5L, SFP) for v2r13
                bnameES1D2X08SX5L(663654),      --8-port 10GE SFP+ interface card (X5L, SFP+) for v2r13
                bnameLE1D2MCUDC00(663655),      --S7703 main control unit D for v2r13c99
                bnameLSS7SRUHX100(663656),       --S7700 main control unit H for v2r19c00
                bnameES1M2G48TX5S(663657),      --48-port 10/100/1000BASE-T interface card (X5S,RJ45) for v2r13c99
                bnameES1M2G48TX5E(663658),      --48-port 10/100/1000BASE-T interface card (X5E,RJ45) for v2r13c99
                bnameEH1D200CMU00V2(663659),    --Centralized Monitoring Board for v2r13c99 for S7700
                bnameLSS7X48SX6S0(663660),       --48-port 10GE SFP+ interface card (X6S,SFP+) for v2r13c99
                bnameLSS7X48SX6E0(663661),       --48-port 10GE SFP+ interface card (X6E,SFP+) for v2r13c99
                bnameLSS7G48SX6S0(663662),      --48-port 1000BASE-X interface card (X6S,SFP) for v2r13c99
                bnameLSS7G48SX6E0(663663),      --48-port 1000BASE-X interface card (X6E,SFP) for v2r13c99
                bnameLSS7X48SX6S1(663664),      --48-port 10GE SFP+ interface card (X6S,SFP+) 7710 for v2r13c99
                bnameLSS7X48SX6E1(663665),      --48-port 10GE SFP+ interface card (X6E,SFP+) 7710 for v2r13c99
                bnameLSS7X48SX6H1(663666),     --48-port 10GE SFP+ interface card (X6H,SFP+) 7710 for v2r13c99
                bnameLSS7SRUHA100(663667),      --S7706/S7712 main control unit H for v2r19c00
                bnameLSS7SFUKA200(663668),      --S7710 switch fabric unit K for v2r19c00
                bnameLSS7M48TX6S1(663669),      --48-port 100BASE-TX/1000/2.5G/5G/10GBASE-T interface card (X6S, RJ45) for v2r19c00
                bnameLSS7M48TX6E1(663670),      --48-port 100BASE-TX/1000/2.5G/5G/10GBASE-T interface card (X6E, RJ45) for v2r19c00
                bnameLSS7X24BX6S0(663673) ,     --24-port 10GE SFP+ interface and 24-port GE SFP interface card (X6S,SFP+) for v2r19c00
                bnameLSS7X24BX6E0(663674) ,     --24-port 10GE SFP+ interface and 24-port GE SFP interface card (X6E,SFP+) for v2r19c00
                bnameLSS7C06HX6S0(663675),      --6-port 100GE QSFP28 interface card (X6S,QSFP28) for v2r19c00
                bnameLSS7C06HX6E0(663676),      --6-port 100GE QSFP28 interface card (X6E,QSFP28) for v2r19c00
                bnameLSS7C06HX6S1(663677),      --6-port 100GE QSFP28 interface card (X6S,QSFP28) for v2r19c00
                bnameLSS7C06HX6E1(663678),      --6-port 100GE QSFP28 interface card (X6E,QSFP28) for v2r19c00
                bnameLSS7C06HX6H1(663679),      --6-port 100GE QSFP28 interface card (X6H,QSFP28) for v2r19c00
                bnameES0D0X12SA01(663680),      --12 port 10GE interface card  for V2R19C00
                bnameES0D0G48SC01(663681),     --48 port 100/1000  SFP+  interface card for V2R19C00
                bnameES0D0G48TC01(663682),     --48 port 10/100/1000BASE-TX  interface card for V2R19C00
                bnameLSS7G48VX5E0(663683),      --48-port 100/1000BASE-T PoE interface card (X5E, RJ45, PoE++) for V2R19C10
                bnameLSS7G48VX5S0(663684),      --48-port 100/1000BASE-T PoE interface card (X5S, RJ45, PoE++) for V2R19C10
                bnameES1D2MCUD00K0(663685),   --S7703 main control unit D(AK)for V2R19C10
                bnameES1M2G48TX5EK(663686),     --48-port 10/100/1000BASE-T interface card (X5E,RJ45)for V2R19C10
                bnameLSS7G48SX6EK0(663687),     --48-port GE SFP interface card (X6E,SFP) for V2R19C10
                bnameLSS7X48SX6EK0(663688),     --48-Port 10GE SFP+ interface card (X6E,SFP+) for V2R19C10
                bnameLSS7X24BX6EK0(663689),     --24-port 10GE SFP+ interface and 24-port GE SFP interface card (X6E,SFP+) for V2R19C10
                bnameLSS7C06HX6EK0(663690),     --6-port 100GE QSFP28 interface card (AK,QSFP28) for V2R20C00
                bnameLSS7G48VX5EK0(663692),     --48-port 10/100/1000BASE-T PoE interface card (AK, RJ45, PoE++) for V2R20C00

                bnameLSS7G48TA1S0(663693), --48-port 10/100/1000BASE-T PoE interface card (EA1, RJ45) for V2R20C00 S7700
                bnameLSS7G48TA1E0(663694), --48-port 10/100/1000BASE-T PoE interface card (EC1, RJ45) for V2R20C00 S7700
                bnameLSS7G48VA1S0(663695), --48-port 10/100/1000BASE-T PoE interface card (EA1, RJ45, PoE++) for V2R20C00 S7700
                bnameLSS7G48SA1S0(663696), --48-Port 100/1000BASE-X Interface Card(EA1,SFP) for V2R20C00 S7700
                bnameLSS7G48SA1E0(663697), --48-Port 100/1000BASE-X Interface Card(EC1,SFP) for V2R20C00 S7700
                bnameLSS7SRUH1000(663698), --S7706/S7712,Main Control Unit H for V2R20C00 S7700
                bnameLSS7SRUE1000(663699), --S7706/S7712,Main Control Unit E for V2R20C00 S7700

                bnameLSS7G48SD1E0(663701), --48-port 100/1000BASE-X interface card (D1E, SFP) for V2R20C00 S7700
                bnameLSS7X48SD1E0(663702), --48-Port 10GBASE-X Interface card(D1E,SFP+) for V2R20C00 S7700
                bnameLSS7X24BD1E0(663703), --24-port 10GE SFP+ interface and 24-port GE SFP interface card (D1E,SFP+) for V2R20C00 S7700
                bnameLSS7X16BD1E0(663704), --16-port 10GE SFP+ interface and 16-port GE SFP interface card (D1E,SFP+) for V2R20C00 S7700
                bnameLSS7X32SD1E0(663705), --32-Port 10GBASE-X Interface card(D1E,SFP+) for V2R20C00 S7700
                bnameLSS7X12BD1E0(663706), --12-port 10GE SFP+ interface and 12-port GE SFP interface card (D1E,SFP+) for V2R20C00 S7700

                bnameLSS7SRUHD000(663707), --S7706/S7712 main control unit HD for V2R20C10 S7700
                bnameLSS7SRUED000(663708), --S7706/S7712 main control unit ED for V2R20C10 S7700
                bnameLSS7L12QX6E0(663717), --12-port 40GE QSFP+ inferface card (X6E,QSFP28) for v2r21c00
                bnameLSS7M24VX6E0(663709), --24-port 100M/1G/2.5G/5G/10G and 24-port 100M/1G interface card (X6E,RJ45,PoE++) for v2r21c00
                bnameLSS7M24VX6S0(663710), --24-port 100M/1G/2.5G/5G/10G and 24-port 100M/1G interface card (X6S,RJ45,PoE++) for v2r21c00
                bnameLSS7G48VX6E00(663711), --48-port 100/1000BASE-T interface card (X6E,RJ45,PoE++) for v2r21c00
                bnameLSS7G48VX6EK0(663712), --48-port 100/1000BASE-T interface card (AK,RJ45,PoE++) for v2r21c00
                bnameLSS7M24BX6E0(663713), --24-port 100M/1G/2.5G/5G/10G and 24-port 100M/1G interface card (X6E,RJ45) for v2r21c00
                bnameLSS7M24BX6EK0(663714), --24-port 100M/1G/2.5G/5G/10G and 24-port 100M/1G interface card (AK,RJ45) for v2r21c00
                bnameLSS7M24BX6S0(663715), --24-port 100M/1G/2.5G/5G/10G and 24-port 100M/1G interface card (X6S,RJ45) for v2r21c00
                bnameLSS7G48TX6E0(663716), --48-port 100/1000BASE-T interface card (X6E,RJ45) for v2r21c00
                bnameLSS7MCUA1000(663700), --S7703 main control unit A1 for v2r21c00
                bnameLSS7MCUD0001(663718), --S7703 main control unit D for v2r21c01
                bnameLSS7SRUHX101(663719), --S7706/S7712 main control unit H(X1) for v2r21c01

                bnameLSS7X16SS100(663720), --16-port 10GBASE-X interface card(SC,SFP+) for v2r21c01
                bnameLSS7X32SS100(663721), --32-port 10GBASE-X interface card(SC,SFP+) for v2r21c01 

-- S9700:       0x000A7000~0x000A7fff(684032~688127)
                bnameEH02MCUA(684032),            --Quidway S9703 Main Control Unit A LE02MCUA
                bnameEH1D2MCUAC00(684033),            --Quidway S9703 Main Control Unit A,Clock LE03MCUA
                bnameEH1D2F48TEA0(684034),           --48-Port 10/100BASE-T Interface Card(EA,RJ45)
                bnameEH1D2F48TEC0(684035),           --48-Port 10/100BASE-T Interface Card(EC,RJ45)
                bnameEH1D2F48TFA0(684036),          --48-Port 10/100BASE-T Interface Card(FA,RJ45)
                bnameEH1D2F48SEA0(684037),           --48-Port 100BASE-FX Interface Card(EA,SFP)
                bnameEH1D2F48SEC0(684038),           --48-Port 100BASE-X Interface Card(EC,SFP)
                bnameEH1D2G24TFA0(684039),          --24-Port 10/100/1000BASE-T Interface Card(FA,RJ45)
                bnameEH1D2G24SSA0(684040),           --24-Port 100/1000BASE-X Interface Card(SA,SFP)
                bnameEH1D2G24SEC0(684041),           --24-Port 100/1000BASE-X Interface Card(EC,SFP)
                bnameEH1D2G24SED0(684042),           --24-Port 100/1000BASE-X Interface Card(ED,SFP)
                bnameEH1D2S24CSA0(684043),           --24-Port 100/1000BASE-X and 8-Port 10/100/1000BASE-T Combo Interface Card(SA,SFP/RJ45)
                bnameEH1D2S24CEA0(684044),         --24-Port 100/1000BASE-X and 8-Port 10/100/1000BASE-T Combo Interface Card(EA,SFP/RJ45,1588)
                bnameEH1D2G48TEA0(684045),           --48-Port 10/100/1000BASE-T Interface Card(EA,RJ45)
                bnameEH1D2G48TEC0(684046),           --48-Port 10/100/1000BASE-T Interface Card(EC,RJ45)
                bnameEH1D2G48TFA0(684047),          --48-Port 10/100/1000BASE-T Interface Card(FA,RJ45)
                bnameEH1D2G48TED0(684048),           --48-Port 10/100/1000BASE-T Interface Card(ED,RJ45)
                bnameEH1D2G48TBC0(684049),          --48-Port 10/100/1000BASE-T Interface Card(BC,RJ45)
                bnameEH1D2G48SEA0(684050),           --48-Port 100/1000BASE-X Interface Card(EA,SFP)
                bnameEH1D2G48SEC0(684051),           --48-Port 100/1000BASE-X Interface Card(EC,SFP)
                bnameEH1D2G48SFA0(684052),          --48-Port 100/1000BASE-X Interface Card(FA,SFP)
                bnameEH1D2G48SED0(684053),           --48-Port 100/1000BASE-X Interface Card(ED,SFP)
                bnameEH1D2G48SBC0(684054),          --48-Port 100/1000BASE-X Interface Card(BC,SFP)
                bnameEH1D2T36SEA0(684055),         --36-Port 10/100/1000BASE-T and 12-Port 100/1000BASE-X Interface Card(EA,RJ45/SFP)
                bnameEH1D2X02XEA0(684056),           --2-Port 10GBASE-X Interface Card(EA,XFP)
                bnameEH1D2X02XEC0(684057),           --2-Port 10GBASE-X Interface Card(EC,XFP)
                bnameEH1D2T24XEA0(684058),           --24-Port 10/100/1000BASE-T and 2-Port 10GBASE-X Interface Card(EA,RJ45/XFP)
                bnameEH1D2S24XEA0(684059),           --24-Port 100/1000BASE-X and 2-Port 10GBASE-X Interface Card(EA,SFP/XFP)
                bnameEH1D2S24XEC0(684060),           --24-Port 100/1000BASE-X and 2-Port 10GBASE-X Interface Card(EC,SFP/XFP)
                bnameEH1D2X04XEA0(684061),           --4-Port 10GBASE-X Interface Card(EA,XFP)
                bnameEH1D2X04XEC0(684062),           --4-Port 10GBASE-X Interface Card(EC,XFP)
                bnameEH1D2X04XED0(684063),           --4-Port 10GBASE-X Interface Card(ED,XFP)
                bnameEH1D2X12SSA0(684064),           --12-Port 10GBASE-X Interface Card(SA,SFP+)
                bnameEH1D2X40SFC0(684065),          --40-Port 10GBASE-X Interface Card(FC,SFP+)
                bnameEH1D2E12GSA0(684066),           -- 12-Port EPON Interface and 12-Port 1000BASE-X Interface Card (SFP)
                bnameEH1D200CMU00(684067),
                bnameEH1D2SRUDC00(684068),           --Quidway S9306E/S9312E,Main Control Unit D,Clock
                bnameEH1D2X08SED0(684069),          --8-Port 10GBASE-X Interface Card(ED,SFP+)
                bnameEH02L8UQFC(684070),          --8-Port 40GBASE-X Interface Card(FC,QSFP+)
                bnameEH1D2WM00000(684071),           --WAN Interface Services Process Card
                bnameEH1D2X16SFC0(684072),          --16-Port 10GBASE-X Interface Card(FC,SFP+)
                bnameEH2D2MB86S00(684073),            --X86 Service Process Mother board
                bnameEH1D2L02QFC0(684074),            --2-port 40GBASE-X interface card(FC,QSFP+)
                bnameEH2d2L08QFC0(684075),            --8-port 40GBASE-X interface card(FC,QSFP+)
                bnameEH1D2X08SED4(684076),            --8-Port 10GBASE-X Interface Card(ED,SFP+)
                bnameEH1D2SRUDC01(684077),            --Quidway S9306E/S9312E,Main Control Unit D,Clock FCC
                bnameEH1D2X16SFC1(684078),            --16-Port 10GBASE-X Interface Card(FC,SFP+) FCC
                bnameEH1D2X40SFC1(684079),           --40-Port 10GBASE-X Interface Card(FC,SFP+) FCC
                bnameEH1D2X08SED1(684080),            --8-Port 10GBASE-X Interface Card(ED,SFP+) FCC
                bnameEH1D2X08SED5(684081),            --8-Port 10GBASE-X Interface Card(ED,SFP+) FCC
                bnameEH1D2X12SEE0(684082),            --12-Port 10GBASE-X Interface Card(EE,SFP+)
                bnameEH1D2X24SEE0(684083),            --24-Port 10GBASE-X Interface Card(EE,SFP+)
                bnameEH1D2X12SED0(684084),            --12-Port 10GBASE-X Interface Card(ED,SFP+)
                bnameEH1D2X24SED0(684085),            --24-Port 10GBASE-X Interface Card(ED,SFP+)
                bnameEH1D2SRUC000(684086),            --S9706/S9712,Main Control Unit C,Option clock
                bnameEH1D2X02XEC1(684087),            --S9700,EH1D2X02XEC1,2-Port 10GBASE-X Interface Card(EC,XFP),FCC,128K MAC-1*1
                bnameEH1D2X04XEC1(684088),            --S9700,EH1D2X04XEC1,4-Port 10GBASE-X Interface Card(EC,XFP),FCC,128K MAC-1*1
                bnameEH1D2G48TX1E(684089),            --S9700,48-Port 10/100/1000BASE-T Interface Card(XF,RJ45)
                bnameEH1D2G48SX1E(684090),            --S9700,48-Port 100/1000BASE-X Interface Card(XF,SFP)
                bnameEH1D2S04SX1E(684091),            --S9700,4-Port 10GBASE-X and 24-Port 100/1000BASE-X and 8-Port 10/100/1000BASE-T Combo Interface Card(XF,RJ45/SFP/SFP+)
                bnameEH1D2S08SX1E(684092),            --S9700,8-Port 10GBASE-X and 8-Port 100/1000BASE-X and 8-Port 10/100/1000BASE-T Combo Interface Card(XF,RJ45/SFP/SFP+)
                bnameEH1D2X48SEC0(684093),            --S9700,48-Port 10GBASE-X Interface Card(ED,SFP+)
                bnameEH1D2ACU2000(684094),            --S9700,ACU2
                bnameEH1D2C02FEE0(684095),            --S9700, 2-Port 100GBASE-X Interface Card(EE,CFP)
                bnameEH1D2X32SSC0(684096),            --S9700, 32-Port 10GBASE-X Interface Card(SC,SFP+)
                bnameEH1D2X16SSC2(684097),            --S9700, 16-Port 10GBASE-X Interface Card(SC,SFP+)
                bnameEH1D2L08QX2E(684098),            --S9700 8-Port 40GE QSFP+ Interface Card(X2E,QSFP+)
                bnameEH1D2X32SX2S(684099),            --S9700 32-Port 10GE SFP+ Interface Card(X2S,SFP+)
                bnameEH1D2X32SX2E(684100),            --S9700 32-Port 10GE SFP+ Interface Card(X2E,SFP+)
                bnameEH1D2S24SX2S(684101),            --S9700 24-Port 10GE SFP+ Interface and 8-Port GE SFP Interface Card(X2S,SFP+)
                bnameEH1D2S24SX2E(684102),            --S9700 24-Port 10GE SFP+ Interface and 8-Port GE SFP Interface Card(X2E,SFP+)
                bnameEH1D2S16SX2S(684103),            --S9700 16-Port 10GE SFP+ Interface and 16-Port GE SFP Interface Card(X2S,SFP+)
                bnameEH1D2S16SX2E(684104),            --S9700 16-Port 10GE SFP+ Interface and 16-Port GE SFP Interface Card(X2E,SFP+)
                bnameEH1D2C04HX2S(684105),            --S9700 4-Port 100GE QSFP28 Interface Card(X2S,QSFP28)
                bnameEH1D2C04HX2E(684106),            --S9700 4-Port 100GE QSFP28 Interface Card(X2E,QSFP28)
                bnameEH1D2H02QX2S(684107),            --S9700 2-Port 100GE QSFP28 Interface and 2-Port 40GE QSFP+ Interface Card(X2S,QSFP28)
                bnameEH1D2H02QX2E(684108),            --S9700 2-Port 100GE QSFP28 Interface and 2-Port 40GE QSFP+ Interface Card(X2E,QSFP28)
                bnameEH1D2X48SX2S(684109),            --S9700 48-Port 10GE SFP+ Interface Card(X2S,SFP+)
                bnameEH1DAS24SX2S(684110),            --S9700 24-Port 10GE SFP+ Interface and 24-Port GE SFP Interface Card(X2E,SFP+)
                bnameEH1D2X32SX2H(684111),            --S9700 32-Port 10GE SFP+ Interface Card(X2H,SFP+)
                bnameEH1D2C04HX2H(684112),            --S9700 4-Port 100GE QSFP28 Interface Card(X2H,QSFP28)

-- S12700:       0x000AB000~0x000ABfff(700416~704511)

                bnameET1D2G48TEA0(700416),            --S12700,48-Port 10/100/1000BASE-T Interface Card(EA,RJ45)
                bnameET1D2G48TEC0(700417),            --S12700,48-Port 10/100/1000BASE-T Interface Card(EC,RJ45)
                bnameET1D2G48TED0(700418),            --S12700,48-Port 10/100/1000BASE-T Interface Card(ED,RJ45)
                bnameET1D2G48TX1E(700419),            --S12700,48-Port 10/100/1000BASE-T Interface Card(XF,RJ45)
                bnameET1D2G24SEC0(700420),            --S12700,24-Port 100/1000BASE-X Interface Card(EC,SFP)
                bnameET1D2G24SED0(700421),            --S12700,24-Port 100/1000BASE-X Interface Card(ED,SFP)
                bnameET1D2G48SEA0(700422),            --S12700,48-Port 100/1000BASE-X Interface Card(FA,SFP)
                bnameET1D2G48SEC0(700423),            --S12700,48-Port 100/1000BASE-X Interface Card(EC,SFP)
                bnameET1D2G48SED0(700424),            --S12700,48-Port 100/1000BASE-X Interface Card(ED,SFP)
                bnameET1D2G48SX1E(700425),            --S12700,48-Port 100/1000BASE-X Interface Card(XF,SFP)
                bnameET1D2X04XEA0(700426),            --S12700,4-Port 10GBASE-X Interface Card(FA,XFP)
                bnameET1D2X04XEC1(700427),            --S12700,4-Port 10GBASE-X Interface Card(EC,XFP)
                bnameET1D2X04XED0(700428),            --S12700,4-Port 10GBASE-X Interface Card(ED,XFP)
                bnameET1D2X08SED5(700429),            --S12700,8-Port 10GBASE-X Interface Card(ED,SFP+)
                bnameET1D2X12SSA0(700430),            --S12700,12-Port 10GBASE-X Interface Card(FA,SFP+)
                bnameET1D2X16SSC0(700431),            --S12700,16-Port 10GBASE-X Interface Card(FC,SFP+)
                bnameET1D2X40SFC0(700432),            --S12700,40-Port 10GBASE-X Interface Card(FC,SFP+)
                bnameET1D2X48SED0(700433),            --S12700,48-Port 10GBASE-X Interface Card(ED,SFP+)
                bnameET1D2L02QSC0(700434),            --S12700,2-port 40GBASE-X interface card(FC,QSFP+)
                bnameET1D2L08QSC0(700435),            --S12700,8-port 40GBASE-X interface card(FC,QSFP+)
                bnameET1D2T24XFA0(700436),            --S12700,24-Port 10/100/1000BASE-T and 2-Port 10GBASE-X Interface Card (FA,RJ45/XFP)
                bnameET1D2S24XFA0(700437),            --S12700,24-Port 100/1000BASE-X and 2-Port 10GBASE-X Interface Card(EA,SFP/XFP)
                bnameET1D2S24XEC0(700438),            --S12700,24-Port 100/1000BASE-X and 2-Port 10GBASE-X Interface Card(EC,SFP/XFP)
                bnameET1D2T36SEA0(700439),            --S12700,36-Port 10/100/1000BASE-T and 12-Port 100/1000BASE-X Interface Card(FA,RJ45/SFP)
                bnameET1D2S04SX1E(700440),            --S12700,4-Port 10GBASE-X and 24-Port 100/1000BASE-X and 8-Port 10/100/1000BASE-T Combo Interface Card(XF,RJ45/SFP/SFP+)
                bnameET1D2S08SX1E(700441),            --S12700,8-Port 10GBASE-X and 8-Port 100/1000BASE-X and 8-Port 10/100/1000BASE-T Combo Interface Card(XF,RJ45/SFP/SFP+)
                bnameEH1D2PS00P00(700442),            --S12700,Open Service Platform Unit
                bnameET1D200CMU00(700443),            --S12700,Centralized Monitoring Board
                bnameET1D2MPUA000(700444),            --S12700,Main Processing Unit A,Optional clock
                bnameET1D2SFUA000(700445),            --S12700,S12708/S12712,Switch Fabric Unit A
                bnameET1D2SFUD000(700446),            --S12700,S12708/S12712,Switch Fabric Unit D
                bnameET1D2ACU2000(700447),            --S12700,ACU2
                bnameET1D2SFUC000(700448),            --S12700,S12708/S12712,Switch Fabric Unit C
                bnameET1D2IPS0S00A(700449),           --S12700,IPS/IDS Unit
                bnameET1D2FW00S00A(700450),           --S12700,10G Firewall Unit
                bnameET1D2FW00S01A(700451),           --S12700,20G Firewall Unit
                bnameET1D2FW00S02A(700452),           --S12700,40G Firewall Unit
                bnameET1D2C02FEE0(700453),            --S12700, 2-Port 100GBASE-X Interface Card(EE,CFP)
                bnameET1D2X32SSC0(700454),            --S12700, 32-Port 10GBASE-X Interface Card(SC,SFP+)
                bnameET1D2X16SSC2(700455),            --S12700, 16-Port 10GBASE-X Interface Card(SC,SFP+)
                bnameET1D2SEC0S00(700456),            --S12700, Service Encryption Unit
                bnameET1D2MPUBC00(700457),            --S12700, Main Processing Unit B(Optional clock)
                bnameET1D2SFUB000(700458),            --S12700, Switch Fabric Unit B
                bnameET1D2L08QX2E(700459),            --S12700 8-Port 40GE QSFP+ Interface Card(X2E,QSFP+)
                bnameET1D2X32SX2H(700460),            --S12700 32-Port 10GE SFP+ Interface Card(X2H,SFP+)
                bnameET1D2X32SX2S(700461),            --S12700 32-Port 10GE SFP+ Interface Card(X2S,SFP+)
                bnameET1D2X32SX2E(700462),            --S12700 32-Port 10GE SFP+ Interface Card(X2E,SFP+)
                bnameET1D2S24SX2S(700463),            --S12700 24-Port 10GE SFP+ Interface and 8-Port GE SFP Interface Card(X2S,SFP+)
                bnameET1D2S24SX2E(700464),            --S12700 24-Port 10GE SFP+ Interface and 8-Port GE SFP Interface Card(X2E,SFP+)
                bnameET1D2S16SX2S(700465),            --S12700 16-Port 10GE SFP+ Interface and 16-Port GE SFP Interface Card(X2S,SFP+)
                bnameET1D2S16SX2E(700466),            --S12700 16-Port 10GE SFP+ Interface and 16-Port GE SFP Interface Card(X2E,SFP+)
                bnameET1D2C04HX2H(700467),            --S12700 4-Port 100GE QSFP28 Interface Card(X2H,QSFP28)
                bnameET1D2C04HX2S(700468),            --S12700 4-Port 100GE QSFP28 Interface Card(X2S,QSFP28)
                bnameET1D2C04HX2E(700469),            --S12700 4-Port 100GE QSFP28 Interface Card(X2E,QSFP28)
                bnameET1D2H02QX2S(700470),            --S12700 2-Port 100GE QSFP28 Interface and 2-Port 40GE QSFP+ Interface Card(X2S,QSFP28)
                bnameET1D2H02QX2E(700471),            --S12700 2-Port 100GE QSFP28 Interface and 2-Port 40GE QSFP+ Interface Card(X2E,QSFP28)
                bnameET1D2X48SX2S(700472),            --S12700 48-Port 10GE SFP+ Interface Card(X2S,SFP+)
                bnameET1D2X48SEC0(700473),            --S12700 48-Port 10GBASE-X Interface Card(EC,SFP+)
                bnameET1DAS24SX2S(700474),            --S12700 24-Port 10GE SFP+ Interface and 24-Port GE SFP Interface Card(X2E,SFP+)

                bnameET1D2MPUDC00(700475),            --S12700,Main Processing Unit D(Optional clock)

                bnameET1D2L16QX2H(700476),             --16-Port 40GE QSFP+ Interface Card(X2H,QSFP+) for 12700 v2r11
                bnameET1D2C08HX2H(700477),             --8-Port 100GE QSFP28 Interface Card(X2H,QSFP28) for 12700 v2r11
                bnameET1D2MPUBC01(700478),             --S12710,Main Processing Unit B(Support Security Startup) for v2r12
                bnameET1D2SFUH000(700479),             --S12708/S12712,Switch Fabric Unit H for v2r13
                bnameET1D2C32HEC0(700480),             --S12708/S12712,32-Port 100GE QSFP28 Interface Card(EC,QSFP28) for v2r13
                bnameET1D2L32QEC0(700481),             --S12708/S12712,32-Port 40GE QSFP+ Interface Card(EC,QSFP+) for v2r13
                bnameET1D2MPUHC00(700482),             --S12704/S12708/S12712,Main Processing Unit H(Optional clock) for v2r13
                bnameET1D2G48TX2E(700483),             --48-Port 100/1000BASE-T Interface Card(X2E,RJ45) for v2r13
                bnameET1D2G48TX2H(700484),             --48-Port 100/1000BASE-T Interface Card(X2H,RJ45) for v2r13
                bnameET1D2G48SX2E(700485),             --48-Port 100/1000BASE-X Interface Card(X2E,SFP) for v2r13
                bnameET1D2G48SX2H(700486),             --48-Port 100/1000BASE-X Interface Card(X2H,SFP) for v2r13
                bnameET1D2X08SX2E(700487),             --8-Port 10GE SFP+ Interface Card(X2E,SFP+) for v2r13
                bnameET1D2X08SX2H(700488),             --8-Port 10GE SFP+ Interface Card(X2H,SFP+) for v2r13
                bnameET1D2S04SX2E(700489),             --4-Port 10GE SFP+ Interface and 44-Port GE SFP Interface Card(X2E,SFP+) for v2r13
                bnameET1D2G24SX2E(700490),             --24-Port 100/1000BASE-X Interface Card(X2E,SFP) for v2r13
                bnameET1D2G48TX2S(700491),             --48-Port 100/1000BASE-T Interface Card(X2S,RJ45) for v2r13
                bnameET1D2G48SX2S(700492),             --48-Port 100/1000BASE-X Interface Card(X2S,SFP) for v2r13
                bnameLST7X48SX6S1(700493),              --48-port 10GE SFP+ interface card (X6S,SFP+) for v2r19c00
                bnameLST7X48SX6E1(700494),              --48-port 10GE SFP+ interface card (X6E,SFP+) for v2r19c00
                bnameLST7X48SX6H1(700495),             --48-port 10GE SFP+ interface card (X6H,SFP+) for v2r19c00
                bnameLSG7SFUBA200(700496),             --S12700 switch fabric unit B for v2r19c00
                bnameLST7M48TX6S1(700497),             --48-port 100BASE-TX/1000/2.5G/5G/10GBASE-T interface card (X6S, RJ45) for v2r19c00
                bnameLST7M48TX6E1(700498),             --48-port 100BASE-TX/1000/2.5G/5G/10GBASE-T interface card (X6E, RJ45) for v2r19c00
                bnameLST7G48SX6S0(700499),             --48-port GE SFP interface card (X6S,SFP) for v2r19c00
                bnameLST7G48SX6E0(700500),             --48-port GE SFP interface card (X6E,SFP) for v2r19c00
                bnameLST7X24BX6S0(700501),             --24-port 10GE SFP+ interface and 24-port GE SFP interface card (X6S,SFP+) for v2r19c00
                bnameLST7X24BX6E0(700502),             --24-port 10GE SFP+ interface and 24-port GE SFP interface card (X6E,SFP+) for v2r19c00
                bnameLST7C06HX6S1(700503),             --6-port 100GE QSFP28 interface card (X6S,QSFP28) for v2r19c00
                bnameLST7C06HX6E1(700504),             --6-port 100GE QSFP28 interface card (X6E,QSFP28) for v2r19c00
                bnameLST7C06HX6H1(700505),             --6-port 100GE QSFP28 interface card (X6H,QSFP28) for v2r19c00
                bnameLST7MPUE0000(700506),             --S12700E main control unit E for v2r19c00 12700E
                bnameLST7SFUEX100(700507),             --S12700E switch fabric unit E(X1) for v2r19c00 12700E
                bnameLST7G48TX5S0(700508),             --48-port 10/100/1000BASE-T interface card (X5S,RJ45) for v2r19c00 12700E
                bnameLST7G48TX5E0(700509),             --48-port 10/100/1000BASE-T interface card (X5E,RJ45) for v2r19c00 12700E
                bnameLST7X48SX6S0(700510),             --48-port 10GE SFP+ interface card (X6S,SFP+) for v2r19c00 12700E
                bnameLST7X48SX6E0(700511),             --48-port 10GE SFP+ interface card (X6E,SFP+) for v2r19c00 12700E
                bnameLST7SFUHX100(700512),            --S12700E switch fabric unit H(X1) for v2r19c00 12700E
                bnameLST7SFUMX100(700513),            --S12700E switch fabric unit M(X1) for v2r19c00 12700E
                bnameLST7C24HX6S0(700514),            --24-port 100GE QSFP28 interface card (X6S,QSFP28) for v2r19c00 12700E
                bnameLST7C06HX6S0(700515),            --6-port 100GE QSFP28 interface card (X6S,QSFP28) for v2r19c00 12700E
                bnameLST7C06HX6E0(700516),            --6-port 100GE QSFP28 interface card (X6E,QSFP28) for v2r19c00 12700E
                bnameLST7G48TX5S1(700517),            --48-port 10/100/1000BASE-T interface card (X5S,RJ45) for v2r19c00 12700E
                bnameLST7G48TX5E1(700518),            --48-port 10/100/1000BASE-T interface card (X5E,RJ45) for v2r19c00 12700E
                bnameLST7Y40SX6H0(700519),       --40-port 25GE SFP28 interface card (X6H,SFP28) for V2R19C10
                bnameLST7MPUE000K0(700520),      --S12700E main control unit E(AK) for V2R19C10
                bnameLST7SFUEX10K0(700521),      --S12700E switch fabric unit E(AK) for V2R19C10
                bnameLST7SFUHX10K0(700522),      --S12700E switch fabric unit H(AK) for V2R19C10
                bnameLST7G48TX5EK0(700523),      --48-port 10/100/1000BASE-T interface card (X5E,RJ45) for V2R19C10
                bnameLST7G48SX6EK0(700524),      --48-port GE SFP interface card (X6E,SFP) for V2R19C10
                bnameLST7X24BX6EK0(700525),      --24-port 10GE SFP+ interface and 24-port GE SFP interface card (X6E,SFP+) for V2R19C10
                bnameLST7X48SX6EK0(700526),      --48-Port 10GE SFP+ interface card (X6E,SFP+) for V2R19C10
                bnameLST7C06HX6EK0(700527),      --6-port 100GE QSFP28 interface card (X6E,QSFP28) for V2R19C10
                bnameLST7C24HX6EK0(700528),      --24-port 100GE QSFP28 interface card (X6E,QSFP28) for V2R19C10

                bnameLST7G48TA1S0(700531), --48-port 10/100/1000BASE-T PoE interface card (EA1, RJ45) for V2R20C00 S12700
                bnameLST7G48TA1E0(700532), --48-port 10/100/1000BASE-T PoE interface card (EC1, RJ45) for V2R20C00 S12700
                bnameLST7G48SA1S0(700533), --48-Port 100/1000BASE-X Interface Card(EA1,SFP) for V2R20C00 S12700
                bnameLST7G48SA1E0(700534), --48-Port 100/1000BASE-X Interface Card(EC1,SFP) for V2R20C00 S12700
                bnameLST7MPUA1000(700535), --S12700,Main Processing Unit A(Optional clock) for V2R20C00 S12700

                bnameLST7G48SD1E0(700538), --48-port 100/1000BASE-X interface card (D1E, SFP) for V2R20C00 S12700
                bnameLST7X48SD1E0(700539), --48-Port 10GBASE-X Interface card(D1E,SFP+) for V2R20C00 S12700
                bnameLST7X24BD1E0(700540), --24-port 10GE SFP+ interface and 24-port GE SFP interface card (D1E,SFP+) for V2R20C00 S12700
                bnameLST7X16BD1E0(700541), --16-port 10GE SFP+ interface and 16-port GE SFP interface card (D1E,SFP+) for V2R20C00 S12700
                bnameLST7X32SD1E0(700542), --32-Port 10GBASE-X Interface card(D1E,SFP+) for V2R20C00 S12700
                bnameLST7X12BD1E0(700543), --12-port 10GE SFP+ interface and 12-port GE SFP interface card (D1E,SFP+) for V2R20C00 S12700

                bnameLST7MPUE0001(700544),   --S12700E main control unit E for v2r20c10 12700E
                bnameLST7MPUE000K1(700545), --S12700E main control unit E(AK) for v2r20c10 12700E
                bnameLST7MPUE000Z0(700546),    		   -- S12700E main control unit E(Z) for V2R22C10
                bnameLST7SFUEX10Z0(700547),    		   -- S12700E switch fabric unit E(Z) for V2R22C10
                bnameLST7SFUHX10Z0(700548),    		   -- S12700E switch fabric unit H(Z) for V2R22C10
                bnameLST7G48SX6EZ0(700549),    		   -- 48-port GE SFP interface card (Z,SFP) for V2R22C10
                bnameLST7X24BX6EZ0(700550),    		   -- 24-port 10GE SFP+ interface and 24-port GE SFP interface card (Z,SFP+) for V2R22C10
                bnameLST7X48SX6EZ0(700551),    		   -- 48-Port 10GE SFP+ interface card (Z,SFP+) for V2R22C10
                bnameLST7G48TX5EZ0(700552),    		   -- 6-port 100GE QSFP28 interface card (Z,QSFP28) for V2R22C10
                bnameLST7C06HX6EZ0(700553),    		   -- 6-port 100GE QSFP28 interface card (Z,QSFP28) for V2R22C10
                bnameLST7C24HX6EZ0(700554),    		   -- 6-port 100GE QSFP28 interface card (Z,QSFP28) for V2R22C10
                bnameLST7G48TX6EZ0(700564),    		   -- 48-port 100/1000BASE-T interface card (Z,RJ45) for V2R22C10                
                bnameLST7L12QX6E0(700561), --12-port 40GE QSFP+ inferface card (X6E,QSFP28) for v2r21c00
                bnameLST7L12QX6EK0(700562), --12-port 40GE QSFP+ inferface card (AK,QSFP28) for v2r21c00
                bnameLST7M24BX6E0(700557), --24-port 100M/1G/2.5G/5G/10G and 24-port 100M/1G interface card (X6E,RJ45) for v2r21c00
                bnameLST7M24BX6EK0(700558), --24-port 100M/1G/2.5G/5G/10G and 24-port 100M/1G interface card (AK,RJ45) for v2r21c00
                bnameLST7G48TX6E0(700559), --48-port 100/1000BASE-T interface card (X6E,RJ45) for v2r21c00
                bnameLST7G48TX6S0(700560), --48-port 100/1000BASE-T interface card (X6S,RJ45) for v2r21c00
                bnameLST7MPUEC000(700563), --S12700E main control unit EC for v2r21c01
                bnameLSX7SFUAX500(700565),
                bnameLSX7SFUGX500(700566),
                bnameLSX7CMUA(700567),
                bnameLSX7MPUAX0T0(700568),
                bnameLSX7G24TX1E0(700569),
                bnameLSX7G48TX1E0(700570),
                bnameLSX7G48SX1E0(700571),
                bnameLSX7X24BX1E0(700572),
                bnameLSX7M48VX1E0(700573),
                bnameLSX7X24SX1E0(700574),
                bnameLSX7X48SX1E0(700575),
                bnameLSX7X72SX1E0(700576),
                bnameLSX7X52BX1E0(700577),
                bnameLSX700VSX1E0(700578),
                bnameLSX704CLX1E0(700579),
                bnameLSX708CLX1E0(700580),
                bnameLSX7Y16SX1E0(700581),
                bnameLSX7Y48SX1E0(700582),
                bnameLSX7C04QX1E0(700583),
                bnameLSX7C16QX1E0(700584),
                bnameLSX7C32QX1E0(700585),
                bnameLSX7C04HX1E0(700586),
                bnameLSX7C16HX1E0(700587),
                bnameLSX7C08HX1E0(700588),
                bnameLSX7C16BX1E0(700589),
                bnameLSX7M48VX1E1(700590),    --48-port 100M/1G interface card (RJ45, PoE++, optional RTU upgrade to 2.5/5/10G)
                bnameLSX7M24VX1E1(700591),    --24-port 100M/1G interface card (RJ45, PoE++, optional RTU upgrade to 2.5/5/10G)



-- S7900:       0x000AE000~0x000AEfff(712704~716799)
               bnameEF1D2S48TE3E(712706),             -- s7900 12-Port 100/1000BASE-X Interface Card and 36-Port 10/100/1000BASE-T(E3E,SFP/RJ45)
               bnameEF1D2G48TE3E(712707),             -- s7900 48-Port 10/100/1000BASE-T Interface Card(E3E,RJ45)
               bnameEF1D2G48TE3S(712708),             -- s7900 48-Port 10/100/1000BASE-T Interface Card(E3S,RJ45)
               bnameEF1D2G48SE3E(712709),             -- s7900 48-Port 100/1000BASE-X Interface Card(E3E,SFP)
               bnameEF1D2G48SE3S(712710),             -- s7900 48-Port 100/1000BASE-X Interface Card(E3S,SFP)
               bnameEF1D2S08SX3S(712711),             -- s7900 8-Port 10GE SFP+ Interface and 24-Port GE SFP Interface Card(X3S,SFP+)
               bnameEF1D2S16SX3S(712712),             -- s7900 16-Port 10GE SFP+ Interface and 16-Port GE SFP Interface Card(X3S,SFP+)
               bnameEF1D2X48SX3S(712713),              -- s7900 48-Port 10GE SFP+ Interface Card(X3S,SFP+)

               bnameEF1D2MCUB000(712704),        -- S7905 Main Control Unit B
               bnameEF1D2SRUF000(712705),        -- S7908 Main Control Unit F

               bnameEF1D2G24SSA0(712714),            -- s7900 24-Port 100/1000BASE-X Interface Card(SA,SFP) for v2r12c10
               bnameEF1D2G24TFA0(712715),            -- s7900 24-Port 100/1000BASE-X Interface Card(SA,RJ45) for v2r12c10
               bnameLSF7X24BX6S0(712716),            --24-port 10GE SFP+ interface and 24-port GE SFP interface card (X6S,SFP+) for v2r19c00

  -- S8700:    0x000AE300~0x000AE4ff(713472~713983)  
               bnameLSG7SRUEX1C0(713472),  --S8700-6 main control unit E, supporting 1*100G QSFP28, 2*40G QSFP+, 4*25G SFP28, or 8*10G SFP+ ports
               bnameLSG7SRUEX1T0(713473),  --S8700-6 main control unit E, supporting 1*100G QSFP28, 2*40G QSFP+, 4*25G SFP28, or 8*10G SFP+ ports (TPM)
               bnameLSG7SRUFX1C0(713474),  --S8700-10 main control unit E, supporting 1*100G QSFP28, 2*40G QSFP+, 4*25G SFP28, or 8*10G SFP+ ports
               bnameLSG7SRUFX1T0(713475),  --S8700-10 main control unit E, supporting 1*100G QSFP28, 2*40G QSFP+, 4*25G SFP28, or 8*10G SFP+ ports (TPM)
               bnameLSG7X48SX1E0(713476),  --48-port 100M/1G/10GBASE-X interface card (SFP+)
               bnameLSG7G48SX1E0(713477),  --48-port 100/1000BASE-X interface card (SFP)
               bnameLSG7X24SX1E0(713478),  --24-port 100M/1G/10GBASE-X interface card (SFP+)
               bnameLSG7X24BX1E0(713479),  --20-port 100/1000BASE-X (SFP), 4-port 100M/1G/10G (SFP/SFP+) interface card
               bnameLSG7M48VX1E0(713480),  --48-port 100M/1G/2.5G/5G/10G multi-GE PoE++ interface card (RJ45, PoE++)
               bnameLSG7M24VX1E0(713481),  --24-port 100M/1G/2.5G/5G/10G multi-GE PoE++ interface card (RJ45, PoE++)
               bnameLSG7G48VX1E0(713482),  --48-port 10/100/1000BASE-T PoE++ interface card (RJ45, PoE++)
               bnameLSG7G48TX1E0(713483),  --48-port 10/100/1000BASE-T interface card (RJ45)
               bnameLSG7G24TX1E0(713484),  --24-port 10/100/1000BASE-T interface card (RJ45)
               bnameLSG7X52BX1E0(713485),  --12-port 100M/1G/10GBASE-X, 16-port 100M/1GBASE-X, and 24-port 10/100/1000BASE-T interface card (SFP+, SFP, RJ45)
               bnameLSG7Y24QX1E0(713486),  --24-port 1G/10G/25GBASE-X interface card (SFP28)
               bnameLSG7X48PX1E0(713487),  --48-port 100M/1G/10GBASE-X  PoE++ interface card (SFP+,PoE++)
               bnamePDC2K2S54-DF(713488),  --2200W DC Power Module(Front to Back, Power panel side intake) for V600R021C10
               bnamePAC3KS54-DF(713489),   --2500W/3000W AC&240VDC Power Module (Front to Back, Power panel side intake) for V600R021C0
               bnameLSG7SRUEX1C1(713490),  --S8700-6 main control unit E, supporting 1*100G QSFP28, 2*40G QSFP+, 4*25G SFP28, or 8*10G SFP+ ports,Enhanced
               bnameLSG7SRUEX1T1(713491),  --S8700-6 main control unit E, supporting 1*100G QSFP28, 2*40G QSFP+, 4*25G SFP28, or 8*10G SFP+ ports (TPM),Enhanced
               bnameLSG7SRUFX1C1(713492),  --S8700-10 main control unit F, supporting 1*100G QSFP28, 2*40G QSFP+, 4*25G SFP28, or 8*10G SFP+ ports,Enhanced
               bnameLSG7SRUFX1T1(713493),  --S8700-10 main control unit F, supporting 1*100G QSFP28, 2*40G QSFP+, 4*25G SFP28, or 8*10G SFP+ ports (TPM),Enhanced
               bnameLSG7M48VX1E1(713494),  --48-port 100M/1G/2.5G/5G/10G multi-GE PoE++ interface card (RJ45, PoE++)
               bnameLSG7M24VX1E1(713495),  --24-port 100M/1G/2.5G/5G/10G multi-GE PoE++ interface card (RJ45, PoE++)
               bnameLSG7Y16SX1E0(713496),  --16-port 25G BASE-X interface card(SFP28)
               bnameLSG7SRUDX000(713497),  --S8700-4 main control unit D, supporting 2*10GE SFP+, 24*GE SFP ports
               bnameLSG7SRUDX0H0(713498),  --S8700-4 main control unit D, supporting 2*10GE SFP+, 24*GE SFP ports(TPM)
               bnamePAC600S56-EB(713499),  --Function Module,AC&240VDC PSU,PAC600S56-EB,600W AC&240V DC Power Module (66mm Width Case,Back to Front,Power panel side exhaust)
               bnamePAC1000S56-EB(713500),  --Function Module,AC&240VDC PSU,PAC1000S56-EB,1000W AC&240V DC Power Module(66mm Width Case,Back to Front, Power panel side exhaust)
               bnamePDC1000S56-EB(713501),  --Function Module,DC PSU,PDC1000S56-EB,POE1000W DC Power Module (66mm Width Case, Back to Front, Power panel side exhaust)
               bnameLSG7C04HX1E0(713502),   --4-port 100G BASE-X interface card(QSFP28,optional RTU upgrade to 100G)  
               bnameLSG700VSX1E0(713503),   --High-quality value-added service board
               bnameLSG7SRUDX100(713504),   --S8700-4 main control unit, supporting 2*25GE+6*10GE+20*GE electrical+4*GE combo, or 4*25GE+8*10GE+12*GE electrical+4*GE combo 4*25GE/10GE+8*10GE, or 4*10GE+8*GE+12*GE electrical+4*GE combo service ports     
               bnameLSG7SRUDX1H0(713505),   --S8700-4 main control unit, supporting 2*25GE+6*10GE+20*GE electrical+4*GE combo, or 4*25GE+8*10GE+12*GE electrical+4*GE combo 4*25GE/10GE+8*10GE, or 4*10GE+8*GE+12*GE electrical+4*GE combo service ports
               bnameLSG7SRUEX100(713506),   --S8700-6 main control unit, supporting 2*25GE+6*10GE+20*GE electrical+4*GE combo, or 4*25GE+8*10GE+12*GE electrical+4*GE combo 4*25GE/10GE+8*10GE, or 4*10GE+8*GE+12*GE electrical+4*GE combo service ports     
               bnameLSG7SRUEX1H0(713507),   --S8700-6 main control unit, supporting 2*25GE+6*10GE+20*GE electrical+4*GE combo, or 4*25GE+8*10GE+12*GE electrical+4*GE combo 4*25GE/10GE+8*10GE, or 4*10GE+8*GE+12*GE electrical+4*GE combo service ports
               bnameLSG7SRUFX500(713508),   --S8700-10 main control unit, supporting 1*100GE+2*40GE+12*10GE, 1*100GE+8*25GE, or 3*100GE service ports                                                                                                        
               bnameLSG7SRUFX5H0(713509),   --S8700-10 main control unit, supporting 1*100GE+2*40GE+12*10GE, 1*100GE+8*25GE, or 3*100GE service ports                                                                                                   
               bnameLSG7SRUEX500(713510),   --S8700-6 main control unit, supporting 1*100GE+2*40GE+12*10GE, 1*100GE+8*25GE, or 3*100GE service ports                                                                                                         
               bnameLSG7SRUEX5H0(713511),   --S8700-6 main control unit, supporting 1*100GE+2*40GE+12*10GE, 1*100GE+8*25GE, or 3*100GE service ports                                                                                                    
               bnameLSG7SFUAX100(713512),   --S8700 SFU A (X1)                                                                                                                                                                                               
               bnameLSG7C04HX1E1(713513),   --4-Port 100G Ethernet Optical Interface Card (QSFP28)                                                                                                                                                           
               bnameLSG7X72SX1E0(713514),   --72-port 100M/1G/10G Ethernet optical interface card (SFP+)                                                                                                                                                     
               bnamePAC1K5S54-PF(713515),   --Function Module,AC&240VDC PSU,PAC1K5S54-PF,1500W AC&240VDC Power Module (Front to Back, Power panel side intake)                                                                                               
               bnameLSG7C08HX1E0(713517),   --8-port 100GBASE-X interface card(QSFP28)
               bnameLSG7C32QX1E0(713518),   --32-port 40GBASE-X interface card(QSFP+)
               bnameLSG7C16HX1E0(713516),   --16-port 100GBASE-X interface card(QSFP28)
               bnameLSG7C16QX1E0(713519),   --16-port 40GBASE-X interface card(QSFP+) or 8-port 100GBASE-X interface card(QSFP28)
               bnameLSG7C16BX1E0(713521),   --8-port 100G/40GBASE-X and 8-port 40GBASE-X interface card(QSFP28/QSFP+)
               bnameLSG7X48SX2E0(713520),   --48-port 100M/1G/10GBASE-X interface card (SFP+)    
               bnameLSG7SRUDX200(713524),   --S8700-4 main control unit D, supporting 24*10GE/GE+24*1000BASE-T ports
               bnameLSG7SRUEX200(713522),   --S8700-6 main control unit E, supporting 24*10GE/GE+24*1000BASE-T ports
               bnameLSG7Y48SX1E0(713523),   --48-port 25G BASE-X interface card(SFP28) 
               bnameLSG704CLX1E0(713526),   --4 CFP2 PEN ports optical interface card (CFP2)                         
               bnameLSG708CLX1E0(713525),   --8 CFP2 PEN ports optical interface card (CFP2)
               bnameLSG7SRUDX201(713527),   --S8700-4 main control unit D, supporting 24*10GE/GE+24*1000BASE-T ports
               bnameLSG7M48VX1E2(713528),   --48-port 100M/1G interface card (RJ45, PoE++, optional RTU upgrade to 2.5/5/10G)
               bnameLSG7M24VX1E2(713529),   --24-port 100M/1G interface card (RJ45, PoE++, optional RTU upgrade to 2.5/5/10G)

-- S16700:   0x00AE400~0x000AE4ff(713728~713983)
               bnameLSH7MPUAX1C0(713728), --S16700 Main Processing Unit A
               bnameLSH7MPUAX1T0(713729), --S16700 Main Processing Unit A (HTM)
               bnameLSH7SFUAX100(713730), --S16700-4 Switch Fabric Unit A (X1)
               bnameLSH7SFUBX100(713731), --S16700-4 Switch Fabric Unit B (X1)
               bnameLSH7SFUGX100(713732), --S16700-8 Switch Fabric Unit G (X1)
               bnameLSH7SFUHX100(713733), --S16700-8 Switch Fabric Unit H (X1)
               bnameLSH7X48SX1E0(713734), --48-Port 10G Optical Interface Card (X1E, SFP+)
               bnameLSH7L24QX1E0(713735), --24-Port 40G Optical Interface Card (X1E, QSFP+)
               bnameLSH7L36QX1E0(713736), --36-Port 40G Optical Interface Card (X1E, QSFP+)
               bnameLSH7C18HX1E0(713737), --18-Port 100G Optical Interface Card (X1E, QSFP28)
               bnameLSH7C36HX1E0(713738), --36-Port 100G Optical Interface Card (X1E, QSFP28)
               bnameLSH7L36QX1E1(713739), --36-Port 40GE Interface Card (X1E, QSFP+)
               bnameLSH7SFUCX200(713740), --S16700-4 Switch Fabric Unit C (X2)
               bnameLSH7SFUJX200(713741), --S16700-8 Switch Fabric Unit C (X2)
               bnameLSH7Y52BX2E0(713742), --40-port 25G/10G/GE Ethernet Optics and 4-port 100G/40GE Ethernet Optics, or 48-port 25G/10G/GE Ethernet (X2E, SFP+/QSFP28)
               bnameLSH7X52BX2E0(713743), --40-port 10GE/GE Ethernet optical and 4-port 40GE Ethernet optical, or 48-port 10GE/GE Ethernet optical (X2E, SFP+/QSFP28)
               bnameLSH7C24HX2E0(713744), --24-Port 100G Optical Interface Card (X2E, QSFP28)
               bnameLSH7C36HX2E0(713745), --36-Port 100G Optical Interface Card (X2E, QSFP28)
               bnameLSH7D18DX2E0(713746), --18-Port 400G Optical Interface Card (X2E, QSFP-DD)
               bnameLSH7X74BX1S0(713747), --48-Port 10G Optical Interface and 2-Port 25G Optical Interface and 24-Port 10/100/1000BASE-T Interface Card (X1S, SFP+/SFP28/RJ45)
               bnameLSH7X48SX1S0(713748), --48-Port 10GE Optical Interface Card (X1S, SFP+)                                                                                   
               bnameLSH7G48SX1S0(713749), --48-Port GE Optical Interface Card (X1S, SFP)                                                                                      
               bnameLSH7X48BX1S0(713750), --24-Port 10G Optical Interface and 24-Port GE Optical Interface Card (X1S, SFP+/SFP)                                               
               bnameLSH7L12QX1S0(713751), --12-Port 40G Optical Interface Card (X1E, QSFP+)/6-Port 100G Optical Interface Card (X1E, QSFP28)                                  

-- lanSwChassis: 0x000AE500~0x000AE5ff(713984~714239)
                bnameSRU750-24T24X(713984),    --S750 main control unit D, supporting 24*10GE/GE+24*1000BASE-T ports           
                bnameSRU750-24S2X(713985),     --S750 main control unit D, supporting 2*10G+24*GE, or 8*10G ports (SFP/SFP+)   
                bnameLPU750-24T(713986),       --24-port 10/100/1000BASE-T interface card (RJ45)                               
                bnameLPU750-48T(713987),       --48-port 10/100/1000BASE-T interface card (RJ45)                               
                bnameLPU750-20S4X(713988),     --20-port 100/1000BASE-X and 4-port 100M/1G/10GBASE-X interface card (SFP, SFP+)

   -- NE0508E:  0x000AC000~0x000ACFFF(704512~708607)
                bnameNEDD000PIU00(704512),            --NE08E, Power
                bnameNEDD000FAN00(704513),            --NE08E, FAN

   -- ETN:      0x000AD000~0x000ADFFF(708608~712703)
                bnameLNDD01FAN(708608),               --Fan board, etn550-A


   -- SSP & NSE:
                bnameSSP302X10GL(571003),              -- SSP30-2x10GE-LAN-XFP
                bnameSSP302X10GW(571004),              -- SSP30-2x10GE-WAN-XFP
                bnameSSP301X10GL(571005),              -- SSP30-1x10GE-LAN-XFP
                bnameSSP301X10GW(571006),              -- SSP30-1x10GE-WAN-XFP
                bnameSSP3020GSF(571007),               -- SSP30-20xGE-SFP
                bnameSSP3010GSF(571008),               -- SSP30-10xGE-SFP
                bnameSSP3024GTX(571009),               -- SSP30-24xGE-TX
                bnameSSP3048GTX(571010),               -- SSP30-48xGE-TX
                bnameSSP302XP64X(571011),              -- SSP30-2xPOS/STM64-XFP
                bnameSSP301XP64X(571012),              -- SSP30-1xPOS/STM64-XFP
                bnameSSP308XP16S(571013),              -- SSP30-8xPOS/STM16-SFP
                bnameSSP304XP16S(571014),              -- SSP30-4xPOS/STM16-SFP
                bnameSSP302XP16S(571015),              -- SSP30-2xPOS/STM16-SFP
                bnameSSP301XP16S(571016),              -- SSP30-1xPOS/STM16-SFP
                bnameSSP308XP4S(571017),               -- SSP30-8xPOS/STM4-SFP
                bnameSSP304XP4S(571018),               -- SSP30-4xPOS/STM4-SFP
                bnameSSP308XP1S(571019),               -- SSP30-8xPOS/STM1-SFP
                bnameSSP201X10GLLPUA(571020),          -- SSP20-1x10GE-LAN-XFP LPUA
                bnameSSP201X10GLLPUG(571021),          -- SSP20-1x10GE-LAN-XFP LPUG
                bnameSSP201X10GWLPUA(571022),          -- SSP20-1x10GE-WAN-XFP LPUA
                bnameSSP201X10GWLPUG(571023),          -- SSP20-1x10GE-WAN-XFP LPUG
                bnameSSP2010GSLPUA(571024),            -- SSP20-10xGE-SFP LPUA
                bnameSSP2010GSLPUG(571025),            -- SSP20-10xGE-SFP LPUG
                bnameSSP205GSLPUA(571026),             -- SSP20-5xGE-SFP  LPUA
                bnameSSP205GSLPUG(571027),             -- SSP20-5xGE-SFP  LPUG
                bnameSSP2024GTLPUA(571028),            -- SSP20-24xGE-TX  LPUA
                bnameSSP2024GTLPUG(571029),            -- SSP20-24xGE-TX  LPUG
                bnameSSP2024GFSLPUG(571030),           -- SSP20-24xGE/FE-SFP  LPUG
                bnameSSP20PS64LPUA(571031),            -- SSP20-POS/STM64-XFP LPUA
                bnameSSP20PS64LPUG(571032),            -- SSP20-POS/STM64-XFP LPUG
                bnameSSP204PS64LPUA(571033),            -- SSP20-4xPOS/STM16-SFP LPUA
                bnameSSP204PS64LPUG(571034),            -- SSP20-4xPOS/STM16-SFP LPUG
                bnameSSP202XPS16LPUA(571035),          -- SSP20-2xPOS/STM16-SFP LPUA
                bnameSSP202XPS16LPUG(571036),          -- SSP20-2xPOS/STM16-SFP LPUG
                bnameSSP201XPS16LPUA(571037),          -- SSP20-POS/STM16-SFP LPUA
                bnameSSP201XPS16LPUG(571038),          -- SSP20-POS/STM16-SFP LPUG
                bnameSSP204XPS4LPUA(571039),           -- SSP20-4xPOS/STM4-SFP LPUA
                bnameSSP204XPS4LPUG(571040),           -- SSP20-4xPOS/STM4-SFP LPUG
                bnameSSP208XPS1LPUA(571041),           -- SSP20-8xPOS/STM1-SFP LPUA
                bnameSSP208XPS1LPUG(571042),           -- SSP20-8xPOS/STM1-SFP LPUG
                bnameSSP204XPS1LPUA(571043),           -- SSP20-4xPOS/STM1-SFP LPUA
                bnameSSP204XPS1LPUG(571044),           -- SSP20-4xPOS/STM1-SFP
                bnameSSPDEVOPM(571045) ,                      -- SSP10-OPM Module
                bnameNSESX11LPUF10(571046),                     -- SX11LPUF1020
                bnameNSESX11LPUF20(571047),                     -- SX11LPUF2020
                virentSSP5000SX1D0MPUB460(696500),     --virentSSP5000SX1D0MPUB460
                virentSSP5000SX1D0SRUA570(696501),     --virentSSP5000SX1D0SRUA570
                virentSSP5000SX1DLPUFA070(696502),     --virentSSP5000SX1DLPUFA070
                virentSSP5000SX1DSFUIE07B(696503),     --virentSSP5000SX1DSFUIE07B
                virentSSP5000SX1DSFUIE07C(696504),     --virentSSP5000SX1DSFUIE07C
                virentSSP5000CR57FRA200A(696505),      --virentSSP5000CR57FRA200A
     -- ATN:
                bnameATNDEVUNKNOWN(225280),           -- Unknown board type
                bnameATNDEVMPUG(225281),              -- Main Processing Unit G(Including 1*1G CF Card)
                bnameATNDEVNPUI20(225282),            -- Network Processing Unit Integrated with 2-Port 10GBase LAN/WAN-XFP
                bnameATNDEVPIUD(225283),              -- Power Supply Unit
   -- ATN 910&950,950B:
                bnameANCD000PIU00(225295),          --Power board, 910 and 910I
                bnameATNANC1FAN(225396),        --Fan board, 910 and 910I
                bnameATNAND2PIU(225397),         --Power board, 950 and 950B
                bnameATNAND1FAN(225398),        --Fan board, 950 and 950B
                bnameANCD00APIU00(225340),             --Power board, 910I-AC
                bnameATNANJ1FAN(225341),         --Fan board, 980B
                bnameANJ0000PIU00(225342),           --DC Power board, 980B
                bnameATNTNF5APIU(225343),         --AC Power board, 980B
                bnameATNGENERAL(229000),        --The general type
                bnameANKD000PIU00(229005),               --ATN950C, Power
                bnameANKD000FAN00(229006),               --ATN950C, FAN
                bnameANGD00APIU00(229007),               --ATN910C-A/B AC Power
                bnameES5M0PSD1700(229008),               --ATN910C-A/B DC Power
                bnameANGD000FAN00(229009),               --ATN910C-A/B FAN
                bnameNEJD002FAN00(229010),               --NE08E-S9, FAN
                bnameANND000FAN00(229011),
                bnameANTD000FAN00(229012),
                bnamePDC260S12-CL(229014),
                bnamePAC300S12-CL(229016),
                bnameCR8MM60FBXC0(229017),
                bnameTNRMM82FBXC1(229022),
                bnameCX67FCBA(229023),
                bnameCX67FCBB(229024),
                bnameCX68FCBC(229025),
                bnameEXTPOWER(229026),
                bnameNECD001FAN00(229027),        --Fan board, 910 and 910I
                bnameCX6X0PWRDC70(229033),        --CX600-X2 DC/DC Power Module
                bnameCX6X0PWRAC70(229034),        --CX600-X2 AC/DC Power Module
                bnameANDD002PIU00(229035),        --Power board, 950 and 950B
                bnameTNF5APIU(229036),            --AC Power board, 980B
    --PTN:
                -- for PTN7900 V100R006C00 2013-8-8 by lishaobin begin
                bnamePTN7900TPA1SCA(229376),    --TPA1SCA,System Control,Communication and Auxiliary Process Unit,1*1
                bnamePTN7900TPA1EX12(229377),   --TPA1EX12,12ch 10 Gigabit Ethernet Switching Processing Board-1*1
                bnamePTN7900TPA1EG24(229378),   --TPA1EG24, 24-Port Gigabit Ethernet Processing Board,1*1
                bnamePTN7900TPA1EXL2(229379),   --TPA1EXL2,2ch 40 Gigabit Ethernet Switching Processing Board,1*1
                bnamePTN7900TPA1EH1(229380),    --TPA1EH1,1 Ports 100GE Ethernet Processing Board
                bnamePTN7900TPA1XCS(229381),    --TPA1XCS,Switch Fabric Unit,1*1
                bnamePTN7900TPA1EX8(229382),    --TPA1EX8,8ch 10 Gigabit Ethernet Switching Processing Board-1*1
                bnamePTN7900TPA1CH1(229383),    --TPA1CH1,16 Channels STM-1 CES Optical Interface board ,1*1
                bnamePTN7900TPA1CQ4(229384),    --TPA1CQ4,4 Channels STM-4 CES Optical Interface board ,1*1
                bnamePTN7900TPA1FAN(229385),    --TPA1FAN, fan board
                bnamePTN7900TPA1PIU(229386),    --TPA1PIU,Power board
                bnamePTN7900TPA1EFI(229387),    --TPA1EFI,EMI Filter Interface Board
                -- FOR package board
                bnamePTN7900TPA1EX4(229388),   --TPA1EX4,12ch 10 Gigabit Ethernet Switching Processing Board-1*1
                bnamePTN7900TPA1EXL1(229389),  --TPA1EXL1,1ch 40 Gigabit Ethernet Switching Processing Board,1*1
                bnamePTN7900TPA1CO1(229390),   --TPA1CO1,8ch Channels STM-1 CES Optical Interface board ,1*1
                bnamePTN7900TPA1EG16(229391),  --TPA1EG16, 16-Port Gigabit Ethernet Processing Board,1*1
                -- FOR PTN7900-24
                bnamePTN7900TPB1CXP(229392),    --TPB1CXP,System Control Communication and Switch Fabric Process Unit,1*1
                bnamePTN7900TPB1XCS(229393),    --TPB1XCS,Switch Fabric Unit,1*1
                bnamePTN7900TPB1FAN(229394),    --TPB1FAN, fan board
                bnamePTN7900TPB1PIU(229395),    --TPB1PIU,Power board
                bnamePTN7900TPB1PSU(229396),    --TPB1PSU,PSU Power board
                -- for PTN7900 V100R006C00 2013-8-8 by lishaobin end
                -- for PTN POTN&100G 80KM begin
                bnamePTN7900TPA1EH1A(229397),   --TPA1EH1A,1-port WAN 80km 100 Gigabit Ethernet Switching Processing Board
                bnamePTN7900TPA1UH1(229398),    --TPA1UH1,1-port 100 Gigabit Ethernet and OTN Hybrid Line Card
                bnamePTN7900TPA1UX10(229399),   --TPA1UX10,10-port 10 Gigabit Ethernet and OTN Hybrid Line Card
                bnamePTN790TPA1UH1A(229400),    --TPA1UH1A,1-port 100 Gigabit Ethernet and OTN PIC Hybrid Line Card
                bnamePTN7900TPA1TG30(229401),   --TPA1TG30,30-port 1 Gigabit Ethernet OTN Tributary Card
                bnamePTN7900TPA1TX10(229402),   --TPA1TX10,10-port 10 Gigabit Ethernet OTN Tributary Card
                -- for PTN POTN&100G 80KM end by zhangyi 2014-3-14
                -- FOR PTN7900-12
                bnamePTN7900TPA2XCS(229403),    --TPA2XCS,Switch Fabric Unit,1*1
                bnamePTN7900TPB2XCS(229404),    --TPB2XCS,Switch Fabric Unit,1*1
                bnamePTN7900TPC1XCS(229405),    --TPC1XCS,Switch Fabric Unit,1*1
                bnamePTN7900TPB2CXP(229406),    --TPB2CXP,System Control Communication and Switch Fabric Process Unit,1*1
                bnamePTN7900TPC1CXP(229407),    --TPC1CXP,System Control Communication and Switch Fabric Process Unit,1*1
               bnamePTN990TPJD000CXP00(229408), --TPJD000CXP00,System Control,Cross-connect and Multi-protocol Process Unit
               bnamePTN990TPJD000PIU00(229409), --TPJD000PIU00,Power Interface Board
               bnamePTN990TPJM000FAN00(229410), --TPJM000FAN00,Fan box
               bnamePTN990TPJD000CXP01(229411), --TPJD000CXP01,System Control,Cross-connect and Multi-protocol Process Unit
               --for PTN7900 V1R7C10 20160617
               bnamePTN7900TPA2EH1(229412), --TPA2EH1,1-port 100 Gigabit Ethernet Switching Processing Board
               bnamePTN7900TPA1EH2(229413), --TPA1EH2,2-port 100 Gigabit Ethernet Switching Processing Board
               bnamePTN7900TPA2EXL2(229414), --TPA2EXL2,2-port 40 Gigabit Ethernet Switching Processing Board
               bnamePTN7900TPA1EX16S(229415), --TPA1EX16S,16-port 10 Gigabit Ethernet Switching Processing Board
               bnamePTN7900TPA2EX12(229416), --TPA2EX12,12-port 10 Gigabit Ethernet Switching Processing Board
               bnamePTN7900TPA1EX8S(229417), --TPA1EX8S,8-port 10 Gigabit Ethernet Switching Processing Board
               --for PTN7900 V1R7C10 20160617

               --for PTN7900 V1R8C00 20160617
               bnamePTN7900TPA1MQ1(229418),   --TPA1MQ1,63 Channels E1 Interface Processing Board
               bnamePTN7900TPA2EG24(229419),  --TPA2EG24,24-port Gigabit Ethernet Switching Processing Board
               bnamePTN7900TPA1MPA(229420),   --TPA1MPA,Multi-port GE/STM-1/E1 Processing Board
               bnamePTN990TPJA000PIU00(229421),   --TPJA000PIU00,AC Power Interface Board
               --for PTN7900 V1R8C00 20160617

               --for PTN970  V1R8C10 2016-07-12 by j00278821 begin
               bnameTPKD00CXPA00(229422),           --TPK1CXPA, System Control,Cross-connect and Multi-protocol Process Unit
               bnameTPKD00CXPB00(229423),           --TPK1CXPB, System Control,Cross-connect and Multi-protocol Process Unit
               bnameTPKD000PIU00(229424),             --TPK1PIU, Power Interface Board
               bnameTPKM000FAN00(229425),           --TPK1FAN, Fan box

               --for PTN7900 V1R8C10 20160805
               bnamePTN7900TPA1EHD1(229426), --TPA1EHD1,1-port 200 Gigabit Ethernet Switching Processing Board
               bnamePTN7900TPA2EH2(229427), --TPA2EH2,2-port 100 Gigabit Ethernet Switching Processing Board
               bnamePTN7900TPA3EH1(229428), --TPA3EH1,1-port 100 Gigabit Ethernet Switching Processing Board
               bnamePTN7900TPA2EX8S(229429), --TPA2EX8S,8-port 10 Gigabit Ethernet Switching Processing Board
               --for PTN7900 V1R8C10 20160805

               bnamePTN990TPJD002CXP00(229430), --TPJD002CXP00,System Control,Cross-connect and Multi-protocol Process Unit

               bnameTPLD00CXP000(229431),          --TPL1CXP, System Control,Cross-connect and Multi-protocol Process Unit
               bnameTPMD00CXPN00(229432),         --TPM1CXPN, System Control,Cross-connect and Multi-protocol Process Unit
               bnameTPMD00CXPL00(229433),          --TPM1CXPL, System Control,Cross-connect and Multi-protocol Process Unit
               bnameTPMD00CXPB00(229434),         --TPM1CXPB, System Control,Cross-connect and Multi-protocol Process Unit
               bnameTPMD00CXPM00(229435),         --TPM1CXPM, System Control,Cross-connect and Multi-protocol Process Unit
               bnameTPMD000PIU00(229436),           -- DC Power Module
               bnameTPMD00APIU00(229437),          -- AC Power Module

               --for PTN7900 V1R8C10 20170220
               bnamePTN7900TPA1EV4(229438), --TPA1EV4,4-port 50 Gigabit Ethernet Switching Processing Board
               --for PTN7900 V1R8C10 20170220

               --for PTN7900 V1R9C10 20170502
               bnamePTN7900TPB3CXP(229439), --TPB3CXP,System Control, Cross-Connect and Timing Unit,1*1
               bnamePTN7900TPC2CXP(229440), --TPC2CXP,System Control, Cross-Connect and Timing Unit,1*1
               bnamePTN7900TPA2SCA(229441), --TPA2SCA,System Control, Communication and Auxiliary Processing Unit,1*1
               bnamePTN7900TPD1SCA(229442), --TPD1SCA,System Control, Communication and Auxiliary Processing Unit,1*1
               bnamePTN7900TPB3XCS(229443), --TPB3XCS,Switch Fabric Unit,1*1
               bnamePTN7900TPC2XCS(229444), --TPC2XCS,Switch Fabric Unit,1*1
               bnamePTN7900TPD1XCS(229445), --TPD1XCS,Switch Fabric Unit,1*1
               bnamePTN7900TPA4EH1(229446), --TPA4EH1,1-Port 100GE Switching Processing Board
               bnamePTN7900TPA1EH4(229447), --TPA1EH4,4-Port 100GE Switching Processing Board
               bnamePTN7900TPD1EHL2(229448), --TPD1EHL2,2-Port 400GE Switching Processing Board
               bnamePTN7900TPD1PIU(229449), --TPD1PIU,Power Interface Unit
               bnamePTN7900TPD1FAN(229450), --TPD1FAN,Fan Board
               bnamePTN7900TPD1EFI(229451), --TPD1EFI,EMI Filter Interface Board
               bnamePTN7900TPA1EV2(229452), --TPA1EV2,2-Port 50GE Switching Processing Board
               --for PTN7900 V1R9C10 20170502

               --for PTN7900 V1R9C10 20170807
               bnamePTN7900TPD1EHD1(229453), --TPD1EHD1,1-port 200 Gigabit Ethernet Switching Processing Board
               bnamePTN7900TPD1EXL2(229454), --TPD1EXL2,2-port 40 Gigabit Ethernet Switching Processing Board
               bnamePTN7900TPD1EX8S(229455), --TPD1EX8S,8-port 10 Gigabit Ethernet Switching Processing Board
               bnamePTN7900TPD1EX16S(229456), --TPD1EX16S,16-port 10 Gigabit Ethernet Switching Processing Board
               bnamePTN7900TPD1EG24(229457), --TPD1EG24,24-port Gigabit Ethernet Switching Processing Board
               bnamePTN7900TPD1MQ1(229458), --TPD1MQ1,63 Channels E1 Interface Processing Board
               bnamePTN7900TPD1EV4(229459), --TPD1EV4,4-port 50 Gigabit Ethernet Switching Processing Board
               bnamePTN7900TPD1EH4(229460), --TPD1EH4,4-Port 100 Gigabit Ethernet Switching Processing Board
               bnamePTN7900TPD1EH2A(229461), --TPD1EH2A,2-port 100 Gigabit Ethernet Switching Processing Board
               bnamePTN7900TPA1EH2A(229462), --TPA1EH2A,2-Port 100 Gigabit Ethernet Switching Processing Board
               bnamePTN7900TPA1EX20A(229463), --TPA1EX20A,20-port 10 Gigabit Ethernet Switching Processing Board
               --for PTN7900 V1R9C10 20170807

               --for PTN7900 V1R10C00 20171220
               bnamePTN7900TPA1FHD1(229464), --TPA1FHD1,1-port 200 Gigabit Ethernet Switching Processing Board
               bnamePTN7900TPD1FHD1(229465), --TPD1FHD1,1-port 200 Gigabit Ethernet Switching Processing Board
               bnamePTN7900TPA1FH2(229466), --TPA1FH2,2-port 100 Gigabit Ethernet Switching Processing Board
               bnamePTN7900TPD1FH2(229467), --TPD1FH2,2-port 100 Gigabit Ethernet Switching Processing Board
               bnamePTN7900TPA1FH1(229468), --TPA1FH1,1-port 100 Gigabit Ethernet Switching Processing Board
               bnamePTN7900TPD1FH1(229469), --TPD1FH1,1-port 100 Gigabit Ethernet Switching Processing Board
               bnamePTN7900TPA1FV2(229470), --TPA1FV2,2-port 50 Gigabit Ethernet Switching Processing Board
               bnamePTN7900TPD1FV2(229471), --TPD1FV2,2-port 50 Gigabit Ethernet Switching Processing Board
               bnamePTN7900TPE1CXP(229472), --TPE1CXP,System Control Communication and Switch Fabric Process Unit,1*1
               bnamePTN7900TPF1CXP(229473), --TPF1CXP,System Control Communication and Switch Fabric Process Unit,1*1
               bnamePTN7900TPE1XCS(229474), --TPE1XCS,Switch Fabric Unit,1*1
               --for PTN7900 V1R10C00 20171220

               --for PTN7900 V1R10C00 20180103
               bnamePTN7900TPE1PSU(229475), --PTN7900E-24 power board
               bnamePTN7900TPE1FAN(229476), --PTN7900E-24 fan board
               --for PTN7900 V1R10C00 20180103

               --for PTN9X0  V1R10C00 2018-01-15 by j00278821 begin
               bnameTPLD000PIU00(229477),           --TPL1PIU, Power Interface Board
               bnameTPLM000FAN00(229478),           --TPL1FAN, Fan box
               bnameTNDM000PIU00(229479),           --TND1PIU, Power Interface Board
               bnameTNDM0FAN0300(229480),           --TND1FAN03, Fan box
               --for PTN9X0  V1R10C00 2018-01-15 by j00278821 end

               bnameTPLD00CXPB00(229481),
               bnameTNDD00CXPA00(229482),

               --for PTN7900E V1R10C10 20180409 add by libaicheng begin
               bnamePTN7900TPD1CQ1(229486), --TPD1CQ1,1 Channels STM-4 CES Optical Interface board ,1*1
               bnamePTN7900TPD1CO1(229487), --TPD1CO1,1 Channels STM-4 CES Optical Interface board ,1*1
               fnamePTN7900TPE1CHASSIS(229488),   --PTN 7900E-24 Integrated Chassis Components
               fnamePTN7900TPF1CHASSIS(229489),   --PTN 7900E-12 Integrated Chassis Components
               bnamePTN7900TPD1PSU(229490), --TPD1PSU,Power Subboard
			   bnamePTN7900TPD2PSU(229707), --TPD2PSU,Power Subboard
			   bnamePTN7900TPD1SCAD(229708), --TPD1SCAD, System Control, Communication and Auxiliary Processing Unit,1*1
			   bnamePTN7900TPF1CXPD(229709), --TPF1CXPD, System Control, Communication and Switch Fabric Process Unit,1*1
			   virentPTN7900TPF1VXCSD(229710), --TPF1VXCSD,Switch Fabric Unit,1*1
			   bnamePTN7900TPA1GY16(229711), --TPA1GY16, Fine Granularity Unit Functional Board, 16-Port-10GE/25GE/10G-FG Interface Card(SFP28/SFP+)
              bnamePTN7900TPF1XCS(229491), --TPF1XCS,Switch Fabric Unit,1*1
              virentPTN7900TPE1VXCS(229492), --TPE1VXCS,Switch Fabric Unit,1*1
              virentPTN7900TPF1VXCS(229493), --TPF1VXCS,Switch Fabric Unit,1*1
              bnameTPJD003CXP00(229494), --PTN 990TPJ3CXPA
              bnameTPPMHOSTA000(225440), --PTN 910E-FTPP1CXPA
              bnameTPPMHOSTB000(225441), --PTN 910E-F TPP1CXPA
              --for PTN7900E V1R10C10 20180409 add by libaicheng end
                bnamePTN7900TPA1EY8(229510), --TPA1EY8,8-port 25 Gigabit Ethernet Switching Processing Board
                bnamePTN7900TPD1EY8(229495), --TPD1EY8,8-port 25 Gigabit Ethernet Switching Processing Board
                bnamePTN7900TPA1EY16(229496), --TPA1EY16,16-port 25 Gigabit Ethernet Switching Processing Board
                bnamePTN7900TPD1EY16(229497), --TPD1EY16,16-port 25 Gigabit Ethernet Switching Processing Board
                bnamePTN7900TPA1FV4(229498), --TPA1FV4,4-port 50 Gigabit Ethernet Switching Processing Board
                bnamePTN7900TPD1FV4(229499), --TPD1FV4,4-port 50 Gigabit Ethernet Switching Processing Board
                bnamePTN7900TPA1FV8(229500), --TPA1FV8,8-port 50 Gigabit Ethernet Switching Processing Board
                bnamePTN7900TPD1FV8(229501), --TPD1FV8,8-port 50 Gigabit Ethernet Switching Processing Board
                bnamePTN7900TPA2FH2(229502), --TPA2FH2,2-port 100 Gigabit Ethernet Switching Processing Board
                bnamePTN7900TPD2FH2(229503), --TPD2FH2,2-port 100 Gigabit Ethernet Switching Processing Board
                bnamePTN7900TPA1FH4(229504), --TPA1FH4,4-port 100 Gigabit Ethernet Switching Processing Board
                bnamePTN7900TPD1FH4(229505), --TPD1FH4,4-port 100 Gigabit Ethernet Switching Processing Board
                bnamePTN7900TPA1FHD2(229506), --TPA1FHD2,2-port 200 Gigabit Ethernet Switching Processing Board
                bnamePTN7900TPD1FHD2(229507), --TPD1FHD2,2-port 200 Gigabit Ethernet Switching Processing Board
                bnamePTN7900TPD1FHD4(229508), --TPD1FHD4,4-port 200 Gigabit Ethernet Switching Processing Board
                bnamePTN7900TPD1FHL2(229509), --TPD1FHL2,2-port 400 Gigabit Ethernet Switching Processing Board
                bnamePTN7900TPD2FHD1(229514), --TPD2FHD1,1-port 200 Gigabit Ethernet Switching Processing Board
                bnamePTN7900TPA2FHD1(229515), --TPA2FHD1,1-port 200 Gigabit Ethernet Switching Processing Board
                bnamePTN7900TPA2EX24S(229516), --TPA2EX24S, 24-port 10 Gigabit Ethernet Switching Processing Board
                bnamePTN7900TPA1EX24S(229552), --TPA1EX24S, 24-port 10 Gigabit Ethernet Switching Processing Board
                bnamePTN7900TPD2EX24S(229517), --TPD2EX24S, 24-port 10 Gigabit Ethernet Switching Processing Board
                bnamePTN7900TPA2EX16S(229518), --TPA2EX16S, 16-port 10 Gigabit Ethernet Switching Processing Board
                bnamePTN7900TPD2EX16S(229519), --TPD2EX16S, 16-port 10 Gigabit Ethernet Switching Processing Board
                bnamePTN7900TPD1FH12(229520), --TPD1FH12, 12-port 100 Gigabit Ethernet Switching Processing Board
                bnamePTN7900TPD1FH8(229521), --TPD1FH8, 8-port 100 Gigabit Ethernet Switching Processing Board
                bnamePTN7900TPA2FH4(229522), --TPA2FH4, 4-port 100 Gigabit Ethernet Switching Processing Board
                bnamePTN7900TPD2FH4(229523), --TPD2FH4, 4-port 100 Gigabit Ethernet Switching Processing Board
                bnamePTN7900TPA3FH2(229524), --TPA3FH2, 2-port 100 Gigabit Ethernet Switching Processing Board
                bnamePTN7900TPD3FH2(229525), --TPA3FH2, 2-port 100 Gigabit Ethernet Switching Processing Board
                bnamePTN7900TPA2FH1(229526), --TPA2FH1, 1-port 100 Gigabit Ethernet Switching Processing Board
                bnamePTN7900TPD2FH1(229527), --TPD2FH1, 1-port 100 Gigabit Ethernet Switching Processing Board
                bnamePTN7900TPA2FHD2(229528), --TPA2FHD2, 2-port 200 Gigabit Ethernet Switching Processing Board
                bnamePTN7900TPD2FHD2(229529), --TPD2FHD2, 2-port 200 Gigabit Ethernet Switching Processing Board
                bnamePTN7900TPA1FHL1(229530), --TPA1FHL1, 1-port 400 Gigabit Ethernet Switching Processing Board
                bnamePTN7900TPD1SCAB(229531), --TPD1SCAB, System Control, Communication and Auxiliary Processing Unit,1*1
                bnamePTN7900TPD1XCSB(229532), --TPD1XCSB, Switch Fabric Unit,1*1
                bnamePTN7900TPA2FV4(229533), --TPA2FV4, 4-port 50 Gigabit Ethernet Switching Processing Board
                bnamePTN7900TPA3EG24(229534), --TPA3EG24, 24-port Gigabit Ethernet Switching Processing Board
                bnamePTN7900TPF1CXPB(229535), --TPF1CXPB, System Control, Communication and Switch Fabric Process Unit,1*1
                bnamePTN7900TPF1XCSB(229536), --TPF1XCSB, Switch Fabric Unit,1*1
				bnamePTN7900TPE1CXPB(229549), --TPE1CXPB, System Control, Communication and Switch Fabric Process Unit,1*1
                bnamePTN7900TPE1XCSB(229550), --TPE1XCSB, Switch Fabric Unit,1*1
                virentPTN7900TPE1VXCSB(229547), --TPE1VXCSB, Switch Fabric Unit,1*1
                virentPTN7900TPF1VXCSB(229548), --TPF1VXCSB, Switch Fabric Unit,1*1
                bnamePTN7900TPA5FHD1(229556), --TPA5FHD1, 1-port 200 Gigabit Ethernet Switching Processing Board
                bnamePTN7900TPA2EY16(229557), --TPA2EY16, 16-port 25 Gigabit Ethernet Switching Processing Board
                bnamePTN7900TPA2EY8(229558), --TPA2EY8, 8-port 25 Gigabit Ethernet Switching Processing Board
                bnamePTN7900TPA2FV8(229559),  --TPA2FV8, 8-port 50 Gigabit Ethernet Switching Processing Board
                bnamePTN7900TPA3FHD2(229560),  --TPA3FHD2, 2-port 200 Gigabit Ethernet Switching Processing Board
                bnamePTN7900TPA3FHD1(229561),  --TPA3FHD1, 1-port 200 Gigabit Ethernet Switching Processing Board
                bnamePTN7900TPA5FH2(229562), --TPA5FH2, 2-port 100 Gigabit Ethernet Switching Processing Board
                bnamePTN7900TPD3FHD4(229563), --TPD3FHD4,4-port 200 Gigabit Ethernet Switching Processing Board
                bnamePTN7900TPA2EG16(229564), --TPA2EG16,16-port Gigabit Ethernet Switching Processing Board
           
				bnamePTN7900TPH1FH8(229803), --TPH1FH8, 8-port 100 Gigabit Ethernet Switching Processing Board
				bnamePTN7900TPH1EX24S(229804), --TPH1EX24S, 24-port 10 Gigabit Ethernet Switching Processing Board
				bnamePTN7900TPH1FH2(229805), --TPH1FH2, 2-port 100 Gigabit Ethernet Switching Processing Board
				bnamePTN7900TPH1FH4(229806), --TPH1FH4, 4-port 100 Gigabit Ethernet Switching Processing Board
				bnamePTN7900TPH1FGU(229807), --TPH1FGU, Fine Granularity Unit Functional Board
				bnamePTN7900TPH1XCS(229808), --TPH1XCS, Switch Fabric Unit,1*1
				bnamePTN7900TPH1SCA(229809), --TPH1SCA,System Control, Communication and Auxiliary Processing Unit,1*1
				bnamePTN7900TPF1XCSD(229810),   --TPF1XCSD, Switch Fabric Unit,1*1
				bnamePTN7900TPH1EG24(229811), --TPH1EG24, 24-Port GE/FE adaptive ethernet service processing board
				
                
                bnamePTN7900TPE2CXP(229605),  --TPE2CXP, System Control, Communication and Switch Fabric Process Unit,1*1
                bnamePTN7900TPE2XCS(229606),  --TPE2XCS, Switch Fabric Unit,1*1
                bnamePTN7900TPE2VXCS(229607), --TPE2VXCS, Switch Fabric Unit,1*1
                bnamePTN7900TPF2CXP(229608),  --TPF2CXP, System Control, Communication and Switch Fabric Process Unit,1*1
                bnamePTN7900TPF2XCS(229609),  --TPF2XCS, Switch Fabric Unit,1*1
                bnamePTN7900TPF2VXCS(229610), --TPF2VXCS, Switch Fabric Unit,1*1
                bnamePTN7900TPD2XCS(229611),  --TPD2XCS, Switch Fabric Unit,1*1
                bnamePTN7900TPA6FH2(229612),  --TPA6FH2, 2-port 100 Gigabit Ethernet Switching Processing Board
                bnamePTN7900TPA6FV4(229613),  --TPA6FV4, 4-port 50 Gigabit Ethernet Switching Processing Board
                bnamePTN7900TPA6EX16S(229614), --TPA6EX16S, 16-port 10 Gigabit Ethernet Switching Processing Board
                bnamePTN7900TPA6EY8(229615),  --TPA6EY8, 8-port 25 Gigabit Ethernet Switching Processing Board

                --for PTN7900E V1R12C10 20201218 add by lihaoxiang end
                bnamePTN7900TPD1SCAC(229620),   --TPD1SCAC, System Control, Communication and Switch Fabric Process Unit,1*1
                bnamePTN7900TPD1XCSC(229621),   --TPD1XCSC, Switch Fabric Unit,1*1
                bnamePTN7900TPF1CXPC(229622),   --TPF1CXPC, System Control, Communication and Switch Fabric Process Unit,1*1
                bnamePTN7900TPF1VXCSC(229623), --TPF1VXCSC, Switch Fabric Unit,1*1
                bnamePTN7900TPA5FH4(229624),       --TPA5FH4,  4-port 100 Gigabit Ethernet Switching Processing Board
                bnamePTN7900TPA5FV8(229625),       --TPA5FV8, 8-port 50 Gigabit Ethernet Switching Processing Board
                bnamePTN7900TPA6FHD1(229626),    --TPA6FHD1, 1-port 200 Gigabit Ethernet Switching Processing Board

                --for PTN7900E V1R21C00 20201222 add by y00406927 begin
                bnamePTN7900TPD1FGUB(229627),    --TPD1FGUB, Fine Granularity Unit Functional Board
                --for PTN7900E V1R21C00 20201222 add by y00406927 end

                --for PTN7900E V1R21C10 20200601 add by z00580539 begin
                bnamePTN7900TPD1FH8R(229628),   --TPD1FH8R, 8*100GE Packet Flexible Ethernet Service Processing Board
                bnamePTN7900TPD7FH8(229629),    --TPD7FH8, 8*100GE Flexible Ethernet Service Processing Board
                bnamePTN7900TPA7FV8(229630),    --TPA7FV8, 8*50GE Flexible Ethernet Service Processing Board
                bnamePTN7900TPA7FH4(229631),    --TPA7FH4, 4*100GE Flexible Ethernet Service Processing Board
                bnamePTN7900TPA7FV4(229632),    --TPA7FV4, 4*50GE  Flexible Ethernet Service Processing Board
                bnamePTN7900TPA7FH2(229633),    --TPA7FH2, 2*100GE Flexible Ethernet Service Processing Board
                bnamePTN7900TPD1FHD4R(229634),  --TPD1FHD4R, 4*200GE Flexible Ethernet Service Processing Board
                bnamePTN7900TPD7FHD4(229635),   --TPD7FHD4, 4*200GE Flexible Ethernet Service Processing Board
                bnamePTN7900TPA7FHD2(229636),   --TPA7FHD2, 2*200GE Flexible Ethernet Service Processing Board
                bnamePTN7900TPA7FHD1(229637),   --TPA7FHD1, 1*200GE Packet Service Processing Board
                bnamePTN7900TPA7EY16(229638),   --TPA7EY16, 16*25GE Ethernet Service Processing Board
                bnamePTN7900TPA7EX16S(229639),  --TPA7EX16S, 16*10GE Ethernet Service Processing Board
                bnamePTN7900TPA7EY8(229640),    --TPA7EY8, 8*25GE Ethernet Service Processing Board
                --for PTN7900E V1R21C10 20200601 add by z00580539 end

                --for PTN7900E V1R21C00 20200706 add by z00576107 begin
                bnamePTN7900TPD3FHD4R(229641),   --TPD3FHD4R, 4*200GE Packet Flexible Ethernet Service Processing Board
                bnamePTN7900TPA7FHD2B(229642),    --TPA7FHD2B, 2*200GE Flexible Ethernet Service Processing Board
                bnamePTN7900TPA7FHD1B(229643),    --TPA7FHD1B, 1*200GE Packet Service Processing Board
                bnamePTN7900TPA7FH2B(229644),    --TPA7FH2B, 2*100GE Flexible Ethernet Service Processing Board
                --for PTN7900E V1R21C00 20200706 add by z00576107end
				
				--for PTN7900E V1R21C00 20200728 add by z30000103 begin
                bnamePTN7900TPD2FH8R(229645),   --TPD2FH8R, 8*100GE Packet Flexible Ethernet Service Processing Board
                bnamePTN7900TPD2FHD4R(229646),    --TPD2FHD4R, 4*200GE Flexible Ethernet Service Processing Board
                --for PTN7900E V1R21C00 20200728 add by z30000103 end

				--for PTN7900E V1R21C10 20211015 add by l00572726 begin
                bnamePTN7900TPA5EY8(229647),    --TPA5EY8, 8*25GE Ethernet Service Processing Board
                --for PTN7900E V1R21C00 20211015 add by l00572726 end

				--for PTN7900E V1R22C00 20220112 add by l00503784 begin
                bnamePTN7900TPA1FGU(229648),    --TPA1FGU, Fine Granularity Unit Functional Board
                --for PTN7900E V1R22C00 20220112 add by l00503784 end
				
				--for PTN7900E V8R22C10 20220721 add by g30022025 begin
                bnamePTN7900TPA2MQ1(229649),    --TPA2MQ1, 63 Channels E1 Interface Processing Board
				bnamePTN7900TPA2MQ1A(229658),    --TPA2MQ1A, 63 Channels E1 Interface Processing Board
				bnamePTN7900TPA2MQ1B(229659),    --PA2MQ1B, 63 Channels E1 Interface Processing Board
				bnamePTN7900TPA2CH1(229660),    --TPA2CH1, 16 channelized STM-1 processing board
				bnamePTN7900TPA7EX8S(229676),   --TPA7EX8S, 8-Port GE/GE adaptive ethernet processing board
				bnamePTN7900TPA7EG24(229677),   --TPA7EG24, 24-Port GE/FE adaptive ethernet service processing board
                --for PTN7900E V8R22C10 20220721 add by g30022025 end
				
				--for PTN7900E V8R22C10 20220809 add by g30022025 begin
                bnamePTN7900TPA2CH1G(229678),    --TPA2CH1G, 16 channelized STM-1 processing board
				bnamePTN7900TPA2MQ1G(229679),    --TPA2MQ1G, 63 Channels E1 Interface Processing Board
                --for PTN7900E V8R22C10 20220809 add by g30022025 end

                                --for PTN7900E V8R23C10 20230717 add by x00803952 begin
                               bnamePTN7900TPD1XCSD(229692),     --TPD1XCSD, Switch Fabric Unit,1*1
               --for PTN7900E V8R23C10 20230717 add by x0080395 end
	
		--for PTN7900E V8R23C10 20230731 add by x00803952 begin
                               bnamePTN7900TPD3XCS(229693),     --TPD3XCS, Switch Fabric Unit,1*1
	        --for PTN7900E V8R23C10 20230731 add by x0080395 end

               --for PTN7900E V8R23C10 20230823 add by l00795584 begin
                               bnamePTN7900TPE1CXPD(229694),     --TPE1CXPD,  System Control, Communication and Switch Fabric Unit,1*1
                               virentPTN7900TPE1VXCSD(229695),   --TPE1VXCSD,Switch Fabric Unit,1*1
                               bnamePTN7900TPA2FGU(229696),    --TPA2FGU, Fine Granularity Unit Functional Board
               --for PTN7900E V8R23C10 20230823 add by l00795584 end

               --for PTN7900E V8R24C10 20240713 add by f00852289 begin
                               bnamePTN7900TPD1FHL4(229697),   --TPD1FHL4,4-Port 400 Gigabit ethernet switching flexe service processing board,1*1,
               --for PTN7900E V8R24C10 20240713 add by f00852289 end
               --for PTN7900E V8R24C10 20241108 add by f00852289 begin
                               virentPTN7900VPICTPD1FHL4(229720),   --VPICTPD1FHL4,4-Port 400 Gigabit ethernet switching flexe service processing board,1*1,
               --for PTN7900E V8R24C10 20241108 add by f00852289 end
               --for PTN7900E V8R25C00 20250108 add by l00921167 begin
                               bnamePTN7900TPA2EX16P(229712),   --TPA2EX16P,16-Port 10 Gigabit Adaptive Ethernet Switching Processing Board(physical board, with 8 port enabled by default)
                               bnamePTN7900TPA1EX24P(229713),   --TPA1EX24P,24-Port 10 Gigabit Ethernet Switching Processing Board(physical board, with 16 port enabled by default)
                               bnamePTN7900TPA3FH2P(229714),   --TPA3FH2P,2-port 100Gigabit Ethernet FlexE Service Processing Board(physical board, with 1 port enabled by default) (QSFP28)
                               bnamePTN7900TPA5FH4P(229715),   --TPA5FH4P,4-port 100Gigabit Ethernet FlexE Service Processing Board(physical board, with 1 port enabled by default) (QSFP28)
                               bnamePTN7900TPD1FH8P(229716),   --TPD1FH8P,8-port 100Gigabit Ethernet FlexE Service Processing Board(physical board, with 4 port enabled by default)(QSFP28)
                               bnamePTN7900TPA5FV8P(229717),   --TPA5FV8P,8-port 50Gigabit Ethernet FlexE Service Processing Board(physical board, with 4 port enabled by default)
			   --for PTN7900E V8R25C00 20250108 add by l00921167 end

               --for PTN980  V1R11C00 2018-12-01 by j00278821 begin
               bnameTPNM001FAN00(229511),         --TPN1FAN, Fan box
               bnameTPND001PIU00(229512),           --TPN1PIU, Power Interface Board
               bnameTPND01APIU00(229513),           --TPN1APIU, Power Interface Board
               --for PTN980  V1R11C00 2018-12-01 by j00278821 end
               bnamePTN980TPN1CXPA00(229537),           --PTN980 800G TPN1CXPA
               bnamePTN980TPN1CXPB00(229538),           --PTN980 320G TPN1CXPB
               bnamePTN980TPN1CXPC00(229539),           --PTN980 320G TPN1CXPC
               bnamePTN990ETPN1CXPA00(229540),          --PTN990E
               bnameTPQD02CXPA00(229565),               --OptiX PTN 990E,TPQ2CXPA0,System Control,Cross-connect and Multi-protocol Process Unit
               bnameTPQD02CXPA02(229566),               --OptiX PTN 990E,TPQ2CXPA3,System Control,Cross-connect and Multi-protocol Process Unit
               bnameANND00CXPA00(229483),               --ATN 980C,ANN1CXPA00,System Control,Cross-connect and Multi-protocol Process Unit with 800G
               bnameANND00CXPA01(229484),               --ATN 980C,ANN1CXPA10,System Control,Cross-connect and Multi-protocol Process Unit with 320G
               bnameANND00CXPA02(229485),               --ATN 980C,ANN1CXPA20,System Control,Cross-connect and Multi-protocol Process Unit with 480G
               bnameANND00CXPA03(229541),               --ATN 980C,ANN1CXPA30
              bnameANND01CXPA00(229573),               --ATN 980C,ANN2CXPA00,System Control,Cross-connect and Multi-protocol Process Unit with 800G
              bnameANND01CXPA03(229576),               --ATN 980C,ANN2CXPA20,System Control,Cross-connect and Multi-protocol Process Unit with 360G
              bnameANRD00CXPA02(229577),               --ATN 950D,ANR1CXPA01,System Control,Cross-connect and Multi-protocol Process Unit with 160G
             bnameANRD00CXPA03(229578),               --ATN 950D,ANR1CXPA11,System Control,Cross-connect and Multi-protocol Process Unit with 160G
             bnameANKD00CXPB03(229579),               --ATN 950C,ANK3CXPA0,System Control,Cross-connect and Multi-protocol Process Unit with 160G
             bnameTPND01CXPA00(229599),               --OptiX PTN 980,TPN1CXPA0,System Control,Cross-connect and Multi-protocol Process Unit
             bnameTPND01CXPB00(229601),               --OptiX PTN 980,TPN1CXPB0,System Control,Cross-connect and Multi-protocol Process Unit
             bnameTPND01CXPC00(229603),               --OptiX PTN 980,TPN1CXPC0,System Control,Cross-connect and Multi-protocol Process Unit
             bnameTPND02CXPA02(229604),               --OptiX PTN 980,TPN2CXPA1,System Control,Cross-connect and Multi-protocol Process Unit
             bnameTPTD01CXPA01(229616),               --OptiX PTN 980B,TPT1CXPA01,System Control,Cross-connect and Multi-protocol Process Unit
             bnameTPTD01CXPA02(229617),               --OptiX PTN 980B,TPT1CXPA02,System Control,Cross-connect and Multi-protocol Process Unit
             bnameTPUD01CXPA01(229618),               --OptiX PTN 990B,TPU1CXPA01,System Control,Cross-connect and Multi-protocol Process Unit
             bnameTPUD01CXPA02(229619),               --OptiX PTN 990B,TPU1CXPA02,System Control,Cross-connect and Multi-protocol Process Unit
             bnameTPID01CXPA01(226709),               --OptiX SPN 985,TPI1CXPA0,System Control,Cross-connect and Multi-protocol Process Unit
             bnameTPP1FAN(226711),                    -- PTN 910E-F,TPP1FAN
             bnameTPP1APIU(226712),                   -- PTN 910E-F,TPP1APIU
             bnameTPP1PIU(226713),                    -- PTN 910E-F, TPP1PIU
             bnameTPQ1FAN01(226714),                  -- OptiX PTN 990E,TPQ1FAN
             bnameTPR1FAN01(229021),                  -- PTN970C,TPR1FAN01,Fan Box
             bnamePOWER(226715),                      -- powerSupply
             bnameDEVFAN(226716),                     -- PTN 916-F,FAN01,Fan Box
             bnameTPT1FAN01(226717),                  -- OptiX PTN 980B,TPT1FAN
             bnameTPI1FAN01(226718),                  -- OptiX SPN 985,TPI1FAN01
             bnameTPU1FAN01(226719),                  -- OptiX PTN 990B,TPU1FAN
             bnameTPK1PIU(226720),                    -- ANK1PIU powerSupply
             bnameTND1PIU(226721),                    -- AND2PIU powerSupply

-- AR:          0x000A3000~0x000A3fff(667648~671743)
                bnameAR1220(667648),                   -- AR1220 Main Control Unit
                bnameAR1220W(667649),                  -- AR1220W Main Control Unit
                bnameAR1240(667650),                   -- AR1240 Main Control Unit
                bnameAR1240W(667651),                  -- AR1240W Main Control Unit
                bnameAR2220(667652),                   -- AR2220 Main Control Unit
                bnameAR2240(667653),                   -- AR2240 Main Control Unit
                bnameAR3260(667654),                   -- AR3260 Main Control Unit
                bnameAR01WMF9TTA(667655),              -- 8 Port 100BASE-RJ45 and 1 Port 1000BASE- RJ45  L2/L3 Ethernet Interface Card
                bnameAR01XEGFTA(667656),               -- 24 Port 1000BASE-RJ45-L2/L3  Ethernet Interface Card
                bnameAR01XEGFVA(667657),               -- 24 Port  1000BASE-RJ45-L2/L3 with POE Ethernet Interface Card
                bnameAR01SEG1CA(667658),               -- 1 Port GE Combo WAN Interface Card
                bnameAR01SEF2TA(667659),               -- 2 Port FE WAN Interface Card
                bnameAR01SDE11A(667660),               -- 1 Port Unchannelized E1/Unstructure E1/Fractional E1, WAN Interface Card
                bnameAR01SDME1A(667661),               -- 1 Port Channelized E1/PRI/VE1 ;MFT:Multiflex Trunk
                bnameAR01SDT11A(667662),               -- 1 Port Unchannelized T1/Unstructure T1/Fractional T1,  WAN Interface Card
                bnameAR01SDMT1A(667663),               -- 1 Port Channelized T1/PRI/VT1 ;MFT:Multiflex Trunk
                bnameAR01SDE12A(667664),               -- 2 Port Unchannelized E1/Unstructure E1/Fractional E1,1WAN Interface Card
                bnameAR01SDME2A(667665),               -- 2 Port Channelized E1/PRI/VE1 ;MFT:Multiflex Trunk
                bnameAR01SDT12A(667666),               -- 2 Port Unchannelized T1/Unstructure T1/Fractional T1,  WAN Interface Card
                bnameAR01SDMT2A(667667),               -- 2 Port Channelized T1/PRI/VT1 ;MFT:Multiflex Trunk
                bnameAR01SDSA1A(667668),               -- 1 Port Sync Serial WAN Interface Card
                bnameAR01WDAS8A(667669),               -- 8 Port Async Serial  WAN Interface Card
                bnameAR01SDS1XA(667670),               -- 1 Port ISDN S/T WAN Interface Card
                bnameAR01SVS2XA(667671),               -- 2 Port ISDN S/T Voice Interface Card
                bnameAR01SVA4B1A(667672),              -- 4 Port FXS and 1-Port FXO voice  Interface Card
                bnameAR01SVB4XA(667673),               -- 4 Port FXO voice  Interface Card
                bnameAR01WVAHXA(667674),               -- 32 Port FXS voice  Interface Card
                bnameAR01SLA1XA(667675),               -- 1-Port ADSL2+ annex A/M WAN Interface Card
                bnameAR01SLB1XA(667676),               -- 1-Port ADSL2+ annex B WAN Interface Card
                bnameAR01SLS1XA(667677),               -- 1-Port-4 pair G.SHDSL WAN Interface Card
                bnameAR01SOPP2A(667678),               -- 1-Port GPON/EPON dual-mode interface Card
                bnameAR01FAN(667679),                  -- Fan Card
                bnameAR01PWR(667680),                  -- Power Card, 150W AC
                bnameAR1220V(667681),                  -- AR1220V Main Control Unit
                bnameAR201(667682),                    -- AR201 Main Control Unit
                bnameAR206(667683),                    -- AR206 Main Control Unit
                bnameAR207(667684),                    -- AR207 Main Control Unit
                bnameAR207V(667685),                   -- AR207V Main Control Unit
                bnameAR208E(667686),                   -- AR208 Main Control Unit
                bnameAR01SDSA2A(667687),               -- 2 Port Sync Serial WAN Interface Card
                bnameAR01CPOS(667688),                 -- 155M CPOS Card
                bnameAR01VDSL2(667689),                -- 2 Port VDSL2 Card
                bnameAR1220VW(667690),                 -- AR1220VW Main Control Unit
                bnameAR207VP(667693),                  -- AR207V-P Main Control Unit
                bnameAR201S(667694),                   -- AR201-S Main Control Unit
                bnameAR207S(667695),                   -- AR207-S Main Control Unit
                bnameAR151(667696),                    -- AR151 Main Control Unit
                bnameAR157(667697),                    -- AR157 Main Control Unit
                bnameAR01WDME2A(667698),               -- 2-Port Channelized E1/T1/PRI/VE1 Multiflex Trunk Interface Card (WSIC),1*2
                bnameAR01WVS2XA(667699),               -- 2-Port ISDN S/T Voice Interface Card (WSIC),1*2
                bnameAR2220S(667700),                 -- AR2220-S Main Control Unit
                bnameAR1220L(667701),                 -- AR1220L Main Control Unit
                bnameAR207GHSPA7(667702),             -- AR207G-HSPA+7 Main Control Unit
                bnameAR01WEG4SA(667703),              -- 4-Port GE SFP WAN Interface Card
                bnameAR01WEG4TA(667704),              -- 4-Port GE Copper WAN Interface Card
                bnameAR01SLV1XA(667705),              -- 1-Port VDSL2 WAN Interface Card
                bnameAR01SDGW1A(667706),              -- WCDMA Data Card
                bnameAR01WSX220A(667708),             -- SAE220 WSIC Card
                bnameAR01XSX550A(667709),             -- SAE550 XSIC Card
                bnameSRG1320V(667710),                -- SRG1320V Main Control Unit
                bnameSRG1320VW(667711),               -- SRG1320VW Main Control Unit
                bnameSRG2320(667712),                 -- SRG2320 Main Control Unit
                bnameSRG3340(667713),                 -- SRG3340 Main Control Unit
                bnameSRG3360(667714),                 -- SRG3360 Main Control Unit
                bname16FXS(667715),                   -- 16FXS Card
                bnameAR156(667716),                   -- AR156 Main Control Unit
                bnameAR158E(667717),                  -- AR158E Main Control Unit
                bnameAR151GHSPA(667718),              -- AR151G-HSPA+7 Main Control Unit
                bnameAR157GHSPA(667719),              -- AR157G-HSPA+7 Main Control Unit
                bnameAR151WP(667720),                 -- AR151W-P Main Control Unit
                bnameAR157W(667721),                  -- AR157W Main Control Unit
                bnameAR158EGVWHSPA(667722),           -- AR158EGVW-HSPA+7-P Main Control Unit
                bnameAR157VW(667723),                 -- AR157VW Main Control Unit
                bnameAR158EVW(667724),                -- AR158EVW Main Control Unit
                bnameAR2201(667725),                  -- AR2201 Main Control Unit
                bnameAR2202(667726),                  -- AR2202 Main Control Unit
                bnameAR2220L(667727),                 -- AR2220L Main Control Unit
                bnameAR201VWP(667728),                -- AR201VWP Main Control Unit
                bnameAR207VW(667729),                 -- AR207VW Main Control Unit
                bnameAR2230(667730),                  -- AR2230 Main Control Unit
                bnameAR2220D(667731),                 -- AR2220D Main Control Unit
                bnameAR2204(667732),                  -- AR2204 Main Control Unit
                bnameSRU60(667733),                   -- SRU60 Main Control Unit
                bnameUSR206(667734),                  -- USR20-6 Main Control Unit
                bnameUSR208(667735),                  -- USR20-8 Main Control Unit
                bnameHSE5(667736),                    -- HSE5 Main Control Unit
                bnameAR8CE1T1(667737),                -- 8E1/T1-M Control Unit
                bnameAR4CE1T1(667738),                -- 4E1/T1-M Control Unit
                bnameAR1POS(667739),                  -- 1POS-155M Control Unit (1STM1)
                bnameARIMA(667740),                   -- 4E1-IMA Control Unit
                bnameAR4FE1(667741),                  -- 4E1/T1-F Control Unit
                bnameAR8FE1(667742),                  -- 8E1/T1-F Control Unit
                bnameAR4GEL2 (667743),                -- 4GE-L2 Control Unit
                bnameSRG303W(667744),                 -- SRG303W Main Control Unit
                bnameSRG303VW(667745),                -- SRG303VW Main Control Unit
                bnameSRG2320D(667746),                -- SRG2320D Main Control Unit
                bnameSRG2304(667747),                 -- SRG2304 Main Control Unit
                bnameSRG2330(667748),                 -- SRG2330 Main Control Unit
                bnameSRG1320(667749),                 -- SRG1320 Main Control Unit
                bnameSRG1320W(667750),                -- SRG1320W Main Control Unit
                bnameAR1CE3(667751),                  -- 1CE3 Control Unit
                bnameAR1STM4(667752),                 -- 1POS-622M Control Unit
                bnameAR3CE3(667753),                  -- 3CE3 Control Unit
                bnameAR1CPOS155MW(667754),            -- 1CPOS-155M-W Control Unit
                bnameAR1220S(667755),                 -- AR1220-S Main Control Unit
                bnameAR1220WS(667756),                -- AR1220W-S Main Control Unit
                bnameAR1220D(667757),                 -- AR1220-D Main Control Unit
                bnameAR3GEVDOA(667758),               -- 3G-EVDOA Control Unit
                bnameAR151GEVDO(667759),              -- AR151G-EVDO Main Control Unit
                bnameAR156I(667760),                  -- AR156I Main Control Unit
                bnameAR156IW(667761),                 -- AR156IW Main Control Unit
                bnameAR157I(667762),                  -- AR157I Main Control Unit
                bnameAR157IW(667763),                 -- AR157IW Main Control Unit
                bnameAR168F(667764),                  -- AR168F Main Control Unit
                bnameAR168FW(667765),                 -- AR168FW Main Control Unit
                bnameAR169F(667766),                  -- AR169F Main Control Unit
                bnameAR169W(667767),                  -- AR169W Main Control Unit
                bnameAR169FW(667768),                 -- AR169FW Main Control Unit
                bnameAR169BF(667769),                 -- AR169BF Main Control Unit
                bnameAR169BFW(667770),                -- AR169BFW Main Control Unit
                bnameAR1220F(667771),                 -- AR1220F Main Control Unit
                bnameAR1220FW(667772),                -- AR1220FW Main Control Unit
                bnameAR151S(667773),                  -- AR151-S Main Control Unit
                bnameAR151WPS(667774),                -- AR151W-P-S Main Control Unit
                bnameAR151GUS(667775),                -- AR151G-U-S Main Control Unit
                bnameAR1220LS(667776),                -- AR1220L-S Main Control Unit
                bnameAR220148FES(667777),             -- AR2201-48FE-S Main Control Unit
                bnameAR2204S(667778),                 -- AR2204-S Main Control Unit
                bnameAR159(667779),                   -- AR159 Main Control Unit
                bname3G1EVDO(667780),                 -- 3G-EVDOA Control Unit
                bname24GEV(667781),                   -- 24GEV Control Unit
                bname4ES2GS(667782),                  -- 4ES2G-S Control Unit
                bname4ES2GPS(667783),                 -- 4ES2GP-S Control Unit
                bname9ES2(667784),                    -- 9ES2 Control Unit
                bname1CE3T3M(667785),                 -- 1CE3T3M Control Unit
                bnameLTEH(667786),                    -- LTE-H Control Unit
                bname1VE1T1(667787),                  -- 1VE1/T1 Control Unit
                bname1ADSLBJ(667788),                 -- 1ADSL-BJ Control Unit
                bname1NDE(667789),                    -- 1NDE Control Unit
                bnameAR531GPH(667790),                -- AR531GP-H Main Control Unit
                bnameAR531GBPDH(667791),              -- AR531GBP-D-H Main Control Unit
                bnameAR5312CH(667792),                -- AR531-2C-H Main Control Unit
                bnameAR531F2CH(667793),               -- AR531-F2C-H Main Control Unit
                bnameAR2540H(667794),                 -- AR2540-H Main Control Unit
                bnameAR3560H(667795),                 -- AR3560-H Main Control Unit
                bnameSRU400(667796),                  -- SRU400 Main Control Unit
                bnameSRU200(667797),                  -- SRU200 Main Control Unit
                bnameSRU100(667798),                  -- SRU100 Main Control Unit
                bnameAR4STM1(667799),                 -- 4STM-1 Control Unit
                bnameARALARM(667800),                 -- Alarm Control Unit
                bnameAR8SA(667801),                   -- 8SA/AS Control Unit
                bnameAR6EM(667802),                   -- 6E&M Control Unit
                bnameAR4GECOMBO(667803),              -- 4GE COMBO Control Unit
                bnameAR2240S(667804),                 -- AR2240-S Main Control Unit
                bnameMSP40(667805),                   -- NE16EX-8 Main Control Unit
                bnameAR9ES3P(667806),                 -- 9ES3P Control Unit
                bnameAR01PWR150D(667807),             -- Power Card, 150W DC
                bnameAR01PWR350A(667808),             -- Power Card, 350W AC
                bnameAR01PWR350D(667809),             -- Power Card, 350W DC
                bnameAR121S(667810),                  -- AR121-S Main Control Unit
                bnameAR161FS(667811),                 -- AR161F-S Main Control Unit
                bnameAR156W(667812),                  -- AR156W Main Control Unit
                bnameAR8FE1GE8POE(667813),            -- WSIC-8FE1GE (8POE) Control Unit
                bnameAR4FXS1FXO(667814),              -- SIC-4FXS1FXO Control Unit
                bnameAR159FW(667815),                 -- AR159FW Main Control Unit
                bnameAR161FGWL(667816),               -- AR161FGW-L Main Control Unit
                bnameAR161FGL(667817),                -- AR161FG-L Main Control Unit
                bnameMSP20(667818),                   -- NE16EX-6 Main Control Unit
                bnameSRG2320E(667819),                -- SRG2320E Main Control Unit
                bnameAR162F(667820),                  -- AR162F Main Control Unit
                bnameAR169FVW(667821),                -- AR169FVW Main Control Unit
                bnameAR161FW-P-M5(667822),            -- AR161FW-P-M5 Main Control Unit
                bnameAR511GW-UAV2M5(667823),          -- AR511GW-UAV2M5 Main Control Unit
                bnameAR169GFVW-L(667824),             -- AR169GFVW-L Main Control Unit
                bnameAR531GBP-U-H(667825),            -- AR531GBP-U-H Main Control Unit
                bnameAR161FW(667826),                 -- AR161FW Main Control Unit
                bnameAR1220F-S(667827),               -- AR1220F-S Main Control Unit
                bnameARTDDLTE(667829),                -- TDD-LTE SIC Card
                bnameAR511GW-LAV2M3(667830),          -- AR511GW-LAV2M3 Main Control Unit
                bnameAR161A(667831),                  -- AR161A Main Control Unit
                bnameAR169A(667832),                  -- AR169A Main Control Unit
                bnameAR161AG-L(667833),               -- AR161AG-L Main Control Unit
                bnameAR169AGW-I(667834),              -- AR169AGW-I Main Control Unit
                bnameAR1220EVW(667835),               -- AR1220EVW Main Control Unit
                bnameAR2220E(667836),                 -- AR2220E Main Control Unit
                bnameAR3670-SRUx5(667837),            -- AR3670 (SRUx5) Main Control Unit
                bnameAR3650(667838),                  -- AR3650 Main Control Unit
                bnameAR2630(667839),                  -- AR2630 Main Control Unit
                bnameAR2204E(667840),                 -- AR2204E Main Control Unit
                bnameAR2220E-L(667841),               -- AR2220E-L Main Control Unit
                bnameAR511GW-L-B3(667842),            -- AR511GW-L-B3 Main Control Unit
                bnameAR511GW-LM7(667843),             -- AR511GW-LM7 Main Control Unit
                bnameAR513W-V3M8(667844),             -- AR513W-V3M8 Main Control Unit
                bnameAR1220E-S(667845),               -- AR1220E-S Main Control Unit
                bnameAR3260-S(667846),                -- AR3260-S Main Control Unit
                bnameAR531G-U-D-H(667847),            -- AR531G-U-D-H Main Control Unit
                bnameAR531GPe-U-H(667848),            -- AR531GPe-U-H Main Control Unit
                bnameAR531GR-U-H(667849),             -- AR531GR-U-H Main Control Unit
                bnameAR550-8FE-D-H(667850),           -- AR550-8FE-D-H Main Control Unit
                bnameAR550-24FE-D-H(667851),          -- AR550-24FE-D-H Main Control Unit
                bnameAR502G(667852),                  -- AR502G Main Control Unit
                bnameAR531GP-H(667853),               -- AR531GP-H Main Control Unit
                bnameAR531GB-U-D-H(667854),           -- AR531GB-U-D-H Main Control Unit
                bnameAR161(667855),                   -- AR161 Main Control Unit
                bnameAR161G-LE(667856),               -- AR161G-LE Main Control Unit
                bnameAR161G-HSPA7(667857),            -- AR161G-HSPA+7 Main Control Unit
                bnameAR161GW-L(667858),               -- AR161GW-L Main Control Unit
                bnameAR169(667859),                   -- AR169 Main Control Unit
                bnameAR169G-LE(667860),               -- AR169G-LE Main Control Unit
                bnameAR169G-HSPA7(667861),            -- AR169G-HSPA+7 Main Control Unit
                bnameAR121(667862),                   -- AR121 Main Control Unit
                bnameAR129(667863),                   -- AR129 Main Control Unit
                bnameAR503GW-LM6(667864),             -- AR503GW-LM6 Main Control Unit
                bnameAR169-P-M9(667865),              -- AR169-P-M9 Main Control Unit
                bnameAR1220E(667866),                 -- AR1220E Main Control Unit
                bnameAR1220EV(667867),                -- AR1220EV Main Control Unit
                bnameARWSIC-1NDE(667868),             -- WSIC-1NDE Control Unit
                bnameARSIC-LTEC(667869),              -- SIC-LTEC Control Unit
                bnameARWSIC-GSHDSL(667870),           -- WSIC-G.SHDSL Control Unit
                bnameAR4GE-POE(667871),               -- 4GE POE Control Unit
                bnameAR24GE-L2-POE(667872),           -- 24GE-L2-POE Control Unit
                bnameAR151-S2(667873),                -- AR151-S2 Main Control Unit
                bnameAR01PWR850W-PoE(667874),         -- Power Card, 850W POE
                bnameAR161F(667875),                  -- AR161F Main Control Unit
                bnameAR169FGW-L(667876),              -- AR169FGW-L Main Control Unit
                bnameAR1STM-4POS(667877),             -- 4port STM-1/1port STM-4 POS Control Unit
                bnameAR509G-L-D-H(667878),            -- AR509G-L-D-H Main Control Unit
                bnamePWR700A(667879),                 -- Power Card of AR3670
                bnameAR169FV-8S(667880),              -- AR169FV-8S Main Control Unit
                bnameAR169FVW-8S(667881),             -- AR169FVW-8S Main Control Unit
                bnameAR121W(667882),                  -- AR121W Main Control Unit
                bnameAR121W-S(667883),                -- AR121W-S Main Control Unit
                bnameAR161W(667884),                  -- AR161W Main Control Unit
                bnameAR129W(667885),                  -- AR129W Main Control Unit
                bnameAR2204-27GE(667886),             -- AR2204-27GE Main Control Unit
                bnameAR2204-27GE-P(667887),           -- AR2204-27GE-P Main Control Unit
                bnameAR2204-51GE-P(667888),           -- AR2204-51GE-P Main Control Unit
                bnameAR1220C(667889),                 -- AR1220C Main Control Unit
                bnameAR1220-S2(667890),               -- AR1220-S2 Main Control Unit
                bnameSRU40C(667891),                  -- SRU40C Main Control Unit
                bnameSRU100E(667893),                 -- SRU100E Main Control Unit
                bnameSRU200E(667894),                 -- SRU200E Main Control Unit
                bnameAR2504-H(667895),                -- AR2504-H Main Control Unit
                bnameAR8ES2GS(667896),                -- 8ES2GS Control Unit
                bnameAR8ES2G(667897),                 -- 8ES2G Control Unit
                bnameAR1LTE-LV(667898),               -- 1LTE-LV Control Unit
                bnameAR24ES2GP(667899),               -- 24ES2GP Control Unit
                bnameAR2X10GL(667900),                -- 2X10GL Control Unit
                bnameAR161FV-1P(667901),              -- AR161FV-1P Main Control Unit
                bnameAR169W-P-M9(667902),             -- AR169W-P-M9 Main Control Unit
                bnameAR169RW-P-M9(667903),            -- AR169RW-P-M9 Main Control Unit
                bnameAR531GZ-U-D(667904),             -- AR531GZ-U-D Main Control Unit
                bnameAR161FGW-LA(667905),             -- AR161FGW-LA Main Control Unit
                bnameAR515GW-LM9-D(667906),           -- AR515GW-LM9-D Main Control Unit
                bnameAR161G-U(667907),                -- AR161G-U Main Control Unit
                bnameAR121GW-L(667908),               -- AR121GW-L Main Control Unit
                bnameAR129GW-L(667909),               -- AR129GW-L Main Control Unit
                bnameAR502G-L-D-H(667910),            -- AR502G-L-D-H Main Control Unit
                bnameAR502GR-L-D-H(667911),           -- AR502GR-L-D-H Main Control Unit
                bnameAR531G-F(667912),                -- AR531G-F Main Control Unit
                bnameAR511CGW-LAV2M3(667913),         -- AR511CGW-LAV2M3 Main Control Unit
                bnameAR111-S(667914),                 -- AR111-S Main Control Unit
                bnameAR503GW-LcM7(667915),            -- AR503GW-LcM7 Main Control Unit
                bnameAR511GW-LcAV2M3(667916),         -- AR511GW-LcAV2M3 Main Control Unit
                bnameAR1000V(667917),                 -- AR1000V Main Control Unit
                bnameAR511DcGW-LcAV2(667918),         -- AR511DcGW-LcAV2 Main Control Unit
                bnameAR2204-51GE(667919),             -- AR2204-51GE Main Control Unit
                bnameAR2204E-D(667920),               -- AR2204E-D Main Control Unit
                bname2VDSL2(667921),                  -- 2VDSL2 Control Unit
                bnameAR2504E-H(667922),               -- AR2504E-H Main Control Unit
                bnameAR509G-Lc(667923),               -- AR509G-Lc Main Control Unit
                bnameAR129CGVW-L(667924),             -- AR129CGVW-L Main Control Unit
                bnameAR101-S(667925),                 -- AR101-S Main Control Unit
                bnameAR101W-S(667926),                -- AR101W-S Main Control Unit
                bnameAR550C-4GE(667927),              -- AR550C-4GE Main Control Unit
                bnameAR550C-2C6GE(667928),            -- AR550C-2C6GE Main Control Unit
                bnameAR509CG-Lt(667929),              -- AR509CG-Lt Main Control Unit
                bnameAR509CG-Lt-N(667930),            -- AR509CG-Lt-N Main Control Unit
                bnameAR503EQGW-L(667931),             -- AR503EQGW-L Main Control Unit
                bnameAR503EW(667932),                 -- AR503EW Main Control Unit
                bnameAR503EDGW-Lc(667933),            -- AR503EDGW-Lc Main Control Unit
                bnameAR509CG-L(667934),               -- AR509CG-L Main Control Unit
                bnameAR168FVW(667935),                -- AR168FVW Main Control Unit
                bnameAR532(667936),                   -- AR532 Main Control Unit
                bnameAR502ERc(667937),                -- AR502ERc Main Control Unit
                bnameAR502EGR-L(667938),              -- AR502EGR-L Main Control Unit
                bnameAR502EG-L(667939),               -- AR502EG-L Main Control Unit
                bnameAR502EGW-L(667940),              -- AR502EGW-L Main Control Unit
                bnameAR550E(667941),                  -- AR550E Main Control Unit
                bname1LTE-L(667942),                  -- 1LTE-L Control Unit
                bname1LTE-Lt(667943),                 -- 1LTE-Lt Control Unit
                bname1LTE-Lo(667944),                 -- 1LTE-Lo Control Unit
                bnameHDDSATA(667945),                 -- HDDSATA Control Unit
                bname3G-HSPA7-H(667946),              -- 3G-HSPA+7-H Control Unit
                bnameARPAC-60WC(667947),              -- PAC-60WC Power Card Unit
                bnameAR509CG-Lc(667948),              -- AR509CG-Lc Main Control Unit
                bnameAR2204-51GE-R(667949),           -- AR2204-51GE-R Main Control Unit
                bname1LTE-Lc(667950),                 -- 1LTE-Lc Control Unit
                bnameAR161-S(667951),                 -- AR161-S Main Control Unit
                bnameAR161W-S(667952),                -- AR161W-S Main Control Unit
                bnameAR161GW-Lc-S(667953),            -- AR161GW-Lc-S Main Control Unit
                bnameAR509GW-L-D-H(667954),           -- AR509GW-L-D-H Main Control Unit
                bnameSRG2340E(667955),                -- SRG2340E Main Control Unit
                bnameSRG2320EI(667956),               -- SRG2320EI Main Control Unit
                bnameSRG1320E(667957),                -- SRG1320E Main Control Unit
                bnameAR1200EW-T1(667958),             -- AR1200EW-T1 Main Control Unit
                bname1LTE-L-H(667959),                -- 1LTE-L-H Control Unit
                bnameAR509EG-U-A(667960),             -- AR509EG-U-A Main Unit
                bnameAR169G-Lo(667961),               -- AR169G-Lo Main Unit
                bnameAR161FG-Lc(667962),              -- AR161FG-Lc Main Unit
                bnameAR161FGW-Lc(667963),             -- AR161FGW-Lc Main Unit
                bnameAR161G-Lc(667964),               -- AR161G-Lc Main Unit
                bnameAR101GW-Lc-S(667965),            -- AR101GW-Lc-S Main Unit
                bnameAR201V(667966),                  -- AR201V Main Unit
                bnameAR503EDGW-Lc3(667967),           -- AR503EDGW-Lc3 Main Unit
                bnameAR109(667968),                   -- AR109 Main Unit
                bnameAR109W(667969),                  -- AR109W Main Unit
                bnameAR109GW-L(667970),               -- AR109GW-L Main Unit
                bnameAR502CG-L(667971),               -- AR502CG-L Main Unit
                bnameAR2220E-S(667972),               -- AR2220E-S Main Unit
                bnameAR129CVW(667973),                -- AR129CVW Main Unit
                bnameAR1220-8GE(667974),              -- AR1220-8GE Main Unit
                bnameAR2204-24GE(667975),             -- AR2204-24GE Main Unit
                bnameAR2204-48GE-P(667976),           -- AR2204-48GE-P Main Unit
                bnameAR505Kc-L-RM(667977),            -- AR505Kc-L-RM Main Unit
                bnameAR505Ke-L(667978),               -- AR505Ke-L Main Unit
                bnameAR2504-D-H(667979),              -- AR2504-D-H Main Unit
                bnameAR502EGRb-L(667980),             -- AR502EGRb-L Main Unit
                bnameAR169CVW-4B4S(667981),           -- AR169CVW-4B4S Main Unit
                bnameAR169CVW(667982),                -- AR169CVW Main Unit
                bnameAR169EGW-L(667983),              -- AR169EGW-L Main Unit
                bnameAR169EW(667984),                 -- AR169EW Main Unit
                bnameAR161EW(667985),                 -- AR161EW Main Unit
                bnameAR161EW-M1(667986),              -- AR161EW-M1 Main Unit
                bnameAR509CGW-L(667987),              -- AR509CGW-L Main Unit
                bnameAR509CG-Lt-7(667988),            -- AR509CG-Lt-7 Main Unit
                bnameAR-Sc-Lc(667989),                -- AR-Sc-Lc Main Unit
                bnameAR-Sc-Le(667990),                -- AR-Sc-Le Main Unit
                bnameAR-Sc-La(667991),                -- AR-Sc-La Main Unit
                bnameAR502ER(667992),                 -- AR502ER Main Unit
                bnameAR169FGVW-L-8S(667993),          -- AR169FGVW-L-8S Main Unit
                bname1LTE-Lt-7(667994),               -- 1LTE-Lt-7 Control Unit
                bnameAR502ERb(667995),                -- AR502ERb Main Control Unit
                bnameAR502EGRc-Lc(667996),            -- AR502EGRc-Lc Main Control Unit
				bnameAR111p-S(667997),                -- AR111P-S Main Control Unit
                bnameAR513GW-LcV1(667998),            -- AR513GW-LcV1 Main Control Unit
                bnameAR513W-V1(667999),               -- AR513W-V1 Main Control Unit
                bnameAR1610(668000),                  -- ARAR1610 Main Control Unit
                bnameAR161EGW-L(668001),              -- AR161EGW-L Main Control Unit
                bnameAR2204XE(668002),                -- AR2204XE Main Control Unit
                bnameAR169JFVW-4B4S(668003),          -- AR169JFVW-4B4S Main Control Unit
                bnameAR511EGW-LcAV2(668004),          -- AR511EGW-LcAV2 Main Control Unit
                bnameAR503HGW-L(668005),              -- AR503HGW-L Main Control Unit
                bnameAR503HGW-Lc(668006),             -- AR503HGW-Lc Main Control Unit
                bnameAR502EGRz-Lc(668007),            -- AR502EGRz-Lc Main Control Unit
                bnameAR515CGW-L(668008),              -- AR515CGW-L Main Control Unit
                bnameAR1504-24S(668009),              -- AR1504-24S Main Control Unit
                bnameAR1504-24T(668010),              -- AR1504-24T Main Control Unit
                bnameAR1504-16S8T(668011),            -- AR1504-16S8T Main Control Unit
                bnameAR1504-8S16T(668012),            -- AR1504-8S16T Main Control Unit
                bnameAR168F-4P(668013),               -- AR168F-4P Main Control Unit
                bnameAR550C-2C6GE-2D(668014),         -- AR550C-2C6GE-2D Main Control Unit
                bnameAR-DGP-S(668015),                -- AR-DGP-S Main Control Unit
                bnameAR129CV(668016),                 -- AR129CV Main Control Unit
                bnameAR-Sc-U-BC(668017),              -- AR-Sc-U-BC Main Control Unit
                bnameAR-Se-U-BC(668018),              -- AR-Se-U-BC Main Control Unit
                bnameAR-Sa-U-BC(668019),              -- AR-Sa-U-BC Main Control Unit
                bnameAR-Sc-Lc-BC(668020),             -- AR-Sc-Lc-BC Main Control Unit
                bnameAR-Se-L-BC(668021),              -- AR-Se-L-BC Main Control Unit
                bnameAR-Sa-La-BC(668022),             -- AR-Sa-La-BC Main Control Unit
                bnameAR-Sc-Lc-MC(668023),             -- AR-Sc-Lc-MC Main Control Unit
                bnameAR-Se-L-MC(668024),              -- AR-Se-L-MC Main Control Unit
                bnameAR-Sa-La-MC(668025),             -- AR-Sa-La-MC Main Control Unit
                bnameAR-Sc-MC(668026),                -- AR-Sc-MC Main Control Unit
                bnameAR-Se-MC(668027),                -- AR-Se-MC Main Control Unit
                bnameSRG550C-4GE(668028),             -- SRG550C-4GE Main Control Unit
                bnameSRG550C-2C6GE(668029),           -- SRG550C-2C6GE Main Control Unit
                bnameSRG509CG-Lc(668030),             -- SRG509CG-Lc Main Control Unit
                bnameSRG550-24FE(668031),             -- SRG550-24FE Main Control Unit
                bnameAR503EDGW-Lo(668032),            -- AR503EDGW-Lo Main Control Unit
                bnameAR161FW-DGP(668033),             -- AR161FW-DGP Main Control Unit
                bnameAR161F-DGP(668034),              -- AR161F-DGP Main Control Unit
                bnameAR-So-Lo-BC(668035),             -- AR-So-Lo-BC Main Control Unit
                bnameAR-So-Lo-MC(668036),             -- AR-So-Lo-MC Main Control Unit
                bnameAR-So-U-BC(668037),              -- AR-So-U-BC Main Control Unit
                bnameAR505Ka-L(668038),               -- AR505Ka-L Main Control Unit
                bnameAR502EGW-Lc(668039),             -- AR502EGW-Lc Main Control Unit
                bnameAR502EGRz-L(668040),             -- AR502EGRz-L Main Control Unit
                bnameAR502EG-L-PD(668041),            -- AR502EG-L-PD Main Control Unit
                bnameARPAC-350WB-L(668042),           -- Power Card, 350WB-L AC
                bnameAR503GW-Lo(668043),	      -- AR503GW-Lo Main Control Unit
                bnameAR502EG-La(668044),              --AR502EG-La Main Control Unit
                bnameAR651W-X4(668045),               --AR651W-X4 Main Control Unit
                bnameAR651-X8(668046),                --AR651-X8 Main Control Unit
                bnameAR651U-A4(668047),               --AR651U-A4 Main Control Unit
                bnameAR651-L(668048),                 --AR651-L Main Control Unit
                bnameAR651-L6(668049),                --AR651-L6 Main Control Unit
                bnameAR111EC(668050),                 --AR111EC Main Control Unit
                bnameAR111EC-S(668051),               --AR111EC-S Main Control Unit
                bnameAR161EC(668052),                 --AR161EC Main Control Unit
                bnameAR1220EC(668053),                --AR1220EC Main Control Unit
                bnameAR1220C-S(668054),               --AR1220C-S Main Control Unit
                bnameAR2204-27GE-S(668055),           --AR2204-27GE-S Main Control Unit
                bnameAR502EG-Lj(668056),              --AR502EG-Lj Main Control Unit
                bnameAR651F-Lite(668057),             --AR651F-Lite Main Control Unit
                bnameAR631-Lite(668058),              --AR631-Lite Main Control Unit
                bnameAR651W(668059),                  --AR651W Main Control Unit
                bnameAR169JFVW-2S(668060),            --AR169JFVW-2S Main Control Unit
                bnameAR6120(668061),                  --AR6120 Main Control Unit
                bnameAR6120V(668062),                 --AR6120V Main Control Unit
                bnameAR6120VW(668063),                --AR6120VW Main Control Unit
                bnameAR1660(668064),                  --AR1660 Main Control Unit
                bnameAR1660C(668065),                 --AR1660C Main Control Unit
                bnameSRU100H(668066),                 --SRU100H Main Control Unit
                bnameAR336VW(668067),                 --AR336VW Main Control Unit
                bnameSRU200H(668068),                 --SRU200H Main Control Unit
                bnameAR1600U-X14(668069),             --AR1600U-X14 Main Control Unit
                bnameAR2204XE-DC(668070),             --AR2204XE-DC Main Control Unit
                bnameAR651(668071),                   --AR651 Main Control Unit
                bnameAR651-L4EA(668072),              --AR651-L4EA Main Control Unit
                bnameAR651-L6EA(668073),              --AR651-L6EA Main Control Unit
                bnameAR6120-S(668074),                --AR6120-S Main Control Unit
                bnameAR1660-S(668075),                --AR1660-S Main Control Unit
                bnameAR657-35B(668076),               --AR657-35B Main Control Unit
                bnameAR657W-35B(668077),              --ARAR657W-35B Main Control Unit
                bnameAR6140-16G4XG(668078),           --AR6140-16G4XG Main Control Unit
                bnameSRU400H(668079),                 --SRU400H Main Control Unit
                bnameSRU600H(668080),                 --SRU600H Main Control Unit
                bnameAR2204E-D-27GE(668081),          --AR2204E-D-27GE Main Control Unit
                bnameARPWRPAC150S12-R(668082),        --Power Card, PAC150S12-R
                bnameAR1V35B-AM(668083),              --1V35B-AM LPU Control Unit
                bnameAR6140L-9G-2AC(668084),          --AR6140L-9G-2AC Main Control Unit
                bnameAR651-Lite(668085),              --AR651-Lite Main Control Unit
                bnameAR6140L-S(668086),               --AR6140L-S Main Control Unit
                bnameAR611W(668087),                 --AR611W Main Control Unit
                bnameAR611W-LTE4CN(668088),           --AR611W-LTE4CN Main Control Unit
                bnameAR617VW(668089),                 --AR617VW Main Control Unit
                bnameAR617VW-LTE4EA(668090),          --AR617VW-LTE4EA Main Control Unit
                bnameAR6121(668091),                  --AR6121 Main Control Unit
                bnameSRG1340-9G(668093),              --SRG1340-9G Main Control Unit
                bnameAR651-C(668094),                 --AR651-C Main Control Unit
                bnameAR651W-C(668095),                --AR651W-C Main Control Unit
                bnameAR651U-A4-C(668096),             --AR651U-A4-C Main Control Unit
                bnameAR657W-C(668097),                --AR657W-C Main Control Unit
                bnameAR6121C-S(668098),               --AR6121C-S Main Control Unit
                bnameAR6121-S(668099),                --AR6121-S Main Control Unit
                bnameAR6140H-S(668100),               --AR6140H-S Main Control Unit
                bnameSRG1301(668101),                 --SRG1301 Main Control Unit
                bnameSRU100HH(668102),                --SRU100HH Main Control Unit
                bname1ELTE-L-S(668103),               --1ELTE-L-S Main Control Unit
				bnameAR8140-12G10XG(668104),          --AR8140-12G10XG Main Control Unit
				bnameAR8140-T-12G10XG(668105),        --AR8140-T-12G10XG Main Control Unit
				bnameAR502H(668106),        		  --AR502H Main Control Unit
				bnameAR502H-CN(668107),        		  --AR502H-CN Main Control Unit
				bnameAR502H-5G(668108),        		  --AR502H-5G Main Control Unit
				bnameAR651W-8P(668109),               --AR651W-8P Main Control Unit
				bnameAR6140E-9G-2AC(668110),          --AR6140E-9G-2AC Main Control Unit
				bnameAR6121E(668111),                 --AR6121E Main Control Unit
				bnameAR10(668112),                    --AR10 Main Control Unit
				bnameAR651K(668113),                  --AR651K Main Control Unit
				bnameAR6140K-9G-2AC(668114),          --AR6140K-9G-2AC Main Control Unit
				bnameAR6121K(668115),        		  --AR6121K Main Control Unit
				bnameSRU-600HK(668116),        		  --SRU-600HK Main Control Unit
				bnameSRU-400HK(668117),        	      --SRU-400HK Main Control Unit
				bnameSRG1340-16G4XG(668119),          --SRG1340-16G4XG Main Control Unit
				bnameSRG1321(668120),                 --SRG1321 Main Control Unit
				bnameAR720(668121),                   --AR720 Main Control Unit
				bnameAR730(668122),                   --AR730 Main Control Unit
				bnameSRU-60H(668123),                 --SRU-60H Main Control Unit
				bnameSRU-80H(668124),                 --SRU-80H Main Control Unit
				bnameAR611-S(668125),                 --AR611-S Main Control Unit
				bnameAR611W-S(668126),                --AR611W-S Main Control Unit
				bnameAR303(668127),                   --AR303 Main Control Unit
				bnameAR303W(668128),                  --AR303W Main Control Unit
				bnameAR6121EC-S(668129),              --AR6121EC-S Main Control Unit
				bnameAR6121E-S(668130),               --AR6121E-S Main Control Unit
				bnameAR6140E-S(668131),               --AR6140E-S Main Control Unit
				bnameSRG1311(668132),                 --SRG1311 Main Control Unit
				bnameSRG1340E(668133),                --SRG1340E Main Control Unit
				bnameAR611(668134),                   --AR611 Main Control Unit
				bnameAR6710-L50T2X4(668135),          --AR6710-L50T2X4 Main Control Unit
				bnameAR6710-L50T2X4-T(668136),        --AR6710-L50T2X4-T Main Control Unit
				bnameAR6710-L26T2X4(668137),          --AR6710-L26T2X4 Main Control Unit
				bnameAR6710-L26T2X4-T(668138),        --AR6710-L26T2X4-T Main Control Unit
				bnameAR502H-5G-CN(668139),            --AR502H-5G-CN Main Control Unit
				bnameWSIC-8GE-T-V2(668140),           --WSIC-8GE-T-V2 Lpu Control Unit
				bnameWSIC-4GE-C-V2(668141),           --WSIC-4GE-C-V2 Lpu Control Unit
				bnameSIC-NR-102-V2(668142),           --SIC-NR-102-V2 Lpu Control Unit
                bnameSIC-1LTE4-CN(668143),            --SIC-1LTE4-CN Lpu Control Unit
                bnameSIC-1LTE4-EA(668144),            --SIC-1LTE4-EA Lpu Control Unit
				bnameAR5710-H8T2TS1(668145),          --AR5710-H8T2TS1 Main Control Unit
				bnameAR5710-H8T2TS1-T(668146),        --AR5710-H8T2TS1-T Main Control Unit
				bnameAR6710-L8T3TS1X2(668147),        --AR6710-L8T3TS1X2 Main Control Unit
				bnameAR6710-L8T3TS1X2-T(668148),      --AR6710-L8T3TS1X2-T Main Control Unit
				bnameRU-5G-101(668149),               --RU-5G-101 Main Control Unit
                bnameAR611E-S(668150),                --AR611E-S Main Control Unit
                bnameAR611-LTE4EA(668151),        --AR611-LTE4EA Main Control Unit
                bnameSRU400L(668152),        --SRU400L Main Control Unit
                bnameAR611W-LTE6EA(668153),        --AR611W-LTE6EA Main Control Unit
                bnameAR631I-LTE4CN(668154),        --AR631I-LTE4CN Main Control Unit
                bnameAR631I-LTE4EA(668155),        --AR631I-LTE4EA Main Control Unit
                bnameMPU-100(668156),              --MPU-100 Main Control Unit
                bnameMPU-100-T(668157),            --MPU-100-T Main Control Unit
                bnameSPU-700H(668158),             --SPU-700H SPU Control Unit
                bnameMIC-LTE4-CN-V2(668159),            --MIC-LTE4-CN-V2 Lpu Control Unit
                bnameMIC-LTE4-EA-V2(668160),            --MIC-LTE4-EA-V2 Lpu Control Unit
                bnameMIC-LTE4-AU-V2(668161),            --MIC-LTE4-AU-V2 Lpu Control Unit
                bnameSIC-4E1-V2(668162),                     --SIC-4E1-V2 Lpu Control Unit
                bnameAR6510-L11T1X2(668163),         --AR6510-L11T1X2 Main Control Unit
                bnameAR6510-L5T4S4(668164),          --AR6510-L5T4S4 Main Control Unit
                bnameAR5510-H8P2TW1(668165),      --AR5510-H8P2TW1 Main Control Unit
                bnameAR5510-H10T1(668166),            --AR5510-H10T1 Main Control Unit
                bnameAR5510-L5T-LTE4EA(668167),   --AR5510-L5T-LTE4EA Main Control Unit
                bnameAR5510-L5T(668168),                 --AR5510-L5T Main Control Unit
                bnameAR5710-S10T1X2(668169),             --AR5710-S10T1X2 Main Control Unit
                bnameAR5710-S8P2X(668170),               --AR5710-S8P2X Main Control Unit
                bnameAR5710-S8P2X-LTE4CN(668171),        --AR5710-S8P2X-LTE4CN Main Control Unit
                bnameAR5710-S8T2X(668172),               --AR5710-S8T2X Main Control Unit
                bnameAR5710-S8T2X-LTE4EA(668173),        --AR5710-S8T2X-LTE4EA Main Control Unit
                bnameAR5710-S8T2XE(668174),              --AR5710-S8T2XE Main Control Unit
                bnameAR5710-S8T2XE-LTE4EA-T(668175),     --AR5710-S8T2XE-LTE4EA-T Main Control Unit
                bnameAR5710-S8T2XE-NRCN(668176),         --AR5710-S8T2XE-NRCN Main Control Unit
                bnameAR6710-L14T2X4(668177),             --AR6710-L14T2X4 Main Control Unit
                bnameAR5510-S10T1X2(668178),             --AR5510-S10T1X2 Main Control Unit
                bnameAR5510-S8P2X(668179),               --AR5510-S8P2X Main Control Unit
                bnameAR5510-S8P2X-LTE4CN(668180),        --AR5510-S8P2X-LTE4CN Main Control Unit
                bnameAR5510-S8T2X(668181),               --AR5510-S8T2X Main Control Unit
                bnameAR5510-S8T2X-LTE4EA(668182),        --AR5510-S8T2X-LTE4EA Main Control Unit
                bnameAR5510-S8T2XE-NRCN(668183),         --AR5510-S8T2XE-NRCN Main Control Unit
                bnameSIC-4GET-V2(668184),                --SIC-4GET-V2 Lpu Control Unit
                bnameAR617VW-LTE4(668185),               --AR617VW-LTE4 Main Control Unit
                bnameAR5710S-S8T2X(668186),              --AR5710S-S8T2X Main Control Unit
                bnameAR5710S-S10T1X2(668187),            --AR5710S-S10T1X2 Main Control Unit
				bnameAR5710-S8T2XE-LTE4CN(668188),       --AR5710-S8T2XE-LTE4CN Main Control Unit
				bnameAR5510-H10T2XW1(668189),            --AR5510-H10T2XW1 Main Control Unit
				bnameAR5510-L5TW(668190),                --AR5510-L5TW Main Control Unit
				bnameAR5510-L5TWDS-LTE4EA(668191),       --AR5510-L5TWDS-LTE4EA Main Control Unit
				bnameAR5510-L5TWDS(668192),              --AR5510-L5TWDS Main Control Unit
				bnameAR5510-L5TW-LTE6EA(668193),         --AR5510-L5TW-LTE6EA Main Control Unit
				bnameSIC-4STM1-V2(668194),               --SIC-4STM1-V2 Lpu Control Unit
				bnameSRU-700S(668195),                   --SRU-700S SRU Control Unit
				bnameAR651EW(668196),                    --AR651EW Main Control Unit
				bnameVIRTUAL-SRU-700S(668197),           --VIRTUAL SRU-700S SRU Control Unit
				bnameARPAC300S12-CL(668198),             --Power Card, 300W AC
				bnameARPDC260S12-CL(668199),             --Power Card, 260W DC
				bnameAR5710-S28T2S2XE4(668200),          --AR5710-S28T2S2XE4 Main Control Unit
				bnameAR5710-S52T2XE4(668201),            --AR5710-S52T2XE4 Main Control Unit
				bnameARPDC240S12-CN(668202),             --Power Card, 240W DC
				bnameSIC-NREA-V2(668203),                --SIC-NREA-V2 Lpu Control Unit
                bnameAR617(668204),                      --AR617 Main Control Unit
                bnameAR617-LTE4EA(668205),               --AR617-LTE4EA Main Control Unit
                bnameAR6140E-L14T2X4-V2(668206),         --AR6140E-L14T2X4-V2 Main Control Unit
                bnameAR502H-LTE4AU-V2(668207),           --AR502H-LTE4AU-V2 Main Control Unit
                bnameAR502H-LTE4CN-V2(668208),           --AR502H-LTE4CN-V2 Main Control Unit
                bnameAR502H-LTE4EA-V2(668209),           --AR502H-LTE4EA-V2 Main Control Unit
                bnameAR5710-S8T1XWE(668210),             --AR5710-S8T1XWE Main Control Unit
                bnameAR5710-S8T1XWE-NRGL(668211),        --AR5710-S8T1XWE-NRGL Main Control Unit
                bnameAR5710-S8P2XE-NRGL(668212),         --AR5710-S8P2XE-NRGL Main Control Unit
                bnameAR5710-S8T2XE-NRGL(668213),         --AR5710-S8T2XE-NRGL Main Control Unit
                bnameAR5710-S8T2S(668214),               --AR5710-S8T2S Main Control Unit
                bnameSIC-NRGL-V2(668215),                --SIC-NRGL-V2 Lpu Control Unit
                bnameAR502H-NRGL-V2(668216),             --AR502H-NRGL-V2 Main Control Unit
                bnameAR5710-H4T4N2X(668217),             --AR5710-H4T4N2X Main Control Unit
                bnameAR5710-H4T4N2X-LTE4EA(668218),      --AR5710-H4T4N2X-LTE4EA Main Control Unit
                bnameAR5710-H2T4N2X-NRGL(668219),        --AR5710-H2T4N2X-NRGL Main Control Unit
                bnameAR5710-H2T4PN2X-NRGL(668220),       --AR5710-H2T4PN2X-NRGL Main Control Unit
                bnameAR5710-S8P1XDSE-2LTE4EA(668221),    --AR5710-S8P1XDSE-2LTE4EA Main Control Unit
                bnameAR5710-S8TWDSE-LTE4EA(668222),      --AR5710-S8TWDSE-LTE4EA Main Control Unit
                bnameAR5710-S8T1XWE-LTE4CN(668223),      --AR5710-S8T1XWE-LTE4CN Main Control Unit
                bnameAR5510-S8T2XE-NRGL(668224),         --AR5510-S8T2XE-NRGL Main Control Unit
                bnameSIC-1V35B-V2(668225),               --SIC-1V35B-V2 Lpu Control Unit
                bnameAR180(668226),                      --AR180 Main Control Unit
                bnameAR180PLUS(668227),                  --AR180PLUS Main Control Unit
                bnameAR180PRO(668228),                   --AR180PRO Main Control Unit
                bnameE3(668229),                         --E3 Main Control Unit
                bnameAR280(668230),                      --AR280 Main Control Unit
                bnameAR5510-S8T2S(668231),               --AR5510-S8T2S Main Control Unit
                bnameARPDC260S12-DL(668232),             --Power Card, 260W DC
                bnameRU-301(668233),                     --RU-301 Main Control Unit
                bnameSIC-2X2S-V2(668234),                --SIC-2X2S-V2 Lpu Control Unit
                bnameSIC-4CSTM1-V2(668235),              --SIC-4CSTM1-V2 Lpu Control Unit
                bnameSIC-NRGL-V2-2025(668236),           --SIC-NRGL-V2-2025 Lpu Control Unit
                bnameAR580(668237),                      --AR580 Main Control Unit
                bnameAR580Plus(668238),                  --AR580Plus Main Control Unit
                bnameAR580Pro(668239),                   --AR580Pro Main Control Unit
                bnameAR502H-ELTE-V2(668240),             --AR502H-ELTE-V2 Main Control Unit
                bnameAR5710-S52T2XE4-2025(668241),       --AR5710-S52T2XE4-2025 Main Control Unit
                bnameAR5710-S28T2S2XE4-2025(668242),     --AR5710-S28T2S2XE4-2025 Main Control Unit
                bnameAR5710-S52T2XE(668243),             --AR5710-S52T2XE Main Control Unit
                bnameAR5710-S28T2S2XE(668244),           --AR5710-S28T2S2XE Main Control Unit
                bnameAR6700V-L-16vCPU(668245),           --AR6700V-L-16vCPU Main Control Unit
                bnameAR6700V-L-8vCPU(668246),            --AR6700V-L-8vCPU Main Control Unit
                bnameAR6700V-L-4vCPU(668247),            --AR6700V-L-4vCPU Main Control Unit
                bnameAR6700V-L-2vCPU(668248),            --AR6700V-L-2vCPU Main Control Unit
				bnameEG600-W-5G(668249),                 --EG600-W-5G Main Control Unit
				bnameEG700-P-5G(668250),                 --EG700-P-5G Main Control Unit
				bnameEG800-4C(668251),                   --EG800-4C Main Control Unit

-- vRGW:        0x000A6000~0x000A6fff(679936~684031)
                bnameVRGWDEVUNKNOWN(679936),           -- Unknown board type
                bnameVRGWMPU(679937),                  -- vRGW MPU board
                bnameVRGWLPU(679938),                  -- vRGW LPU board
                bnameVRGWGENERAL(684031),               -- The general type

-- CloudEngine: 0x000A8000~0x000A8fff(688128~692223)
                bnameDE01MPUA(688128),                   -- CloudEngine 12800-CE-MPUA-Main Processing Unit -1*1
                bnameDE01SFU04C(688129),                 -- CloudEngine CE12804 CE-SFU04C,12804 Switch Fabric Unit-1*1
                bnameDE01SFU08C(688130),                 -- CloudEngine CE12808 CE-SFU08C,S12808 Switch Fabric Unit-1*1
                bnameDE01SFU12C(688131),                 -- CloudEngine CE12812 CE-SFU12C,12812 Switch Fabric Unit-1*1
                bnameDE01X48SAAEA(688132),               -- CloudEngine CE12800 CE-L48XS-EA,48-Port 10GBASE-X Interface Card(SFP+)-1*1
                bnameDE01X24SAA(688133),                 -- CloudEngine CE12800 CE-L24XS-EA,24-Port 10GBASE-X Interface Card(SFP+)-1*1
                bnameDE01L24QAA(688134),                 -- CloudEngine CE12800 CE-L24LQ-EA,24-Port-40G Interface Card(QSFP+)-1*1
                bnameDE01BAK04A(688135),                 -- CloudEngine CE12800 CE-BAK04A,12804 Backplane-1*1
                bnameDE01BAK08A(688136),                 -- CloudEngine CE12800 CE-BAK08A,12808 Backplane-1*1
                bnameDE01BAK12A(688137),                 -- CloudEngine CE12800 CE-BAK12A,12812 Backplane-1*1
                bnameDE51SRU1B(688138),                  -- CloudEngine CE5850 CE5850-48T4S2Q-EI 48-Port GE  RJ45 and 4-Port SFP+ Optical and 2-Port 40GE QSFP+ Optical Switch Control Unit
                bnameDE51SRU1A(688139),                  -- CloudEngine CE6850 CE6850-48S4Q-EI 48-Port SFP+ Optical and 4-Port 40GE QSFP+ Optical Switch Control Unit
                bnameDE51SRU1C(688140),                  -- CloudEngine CE6850 CE6850-48T4Q-EI 48-Port 10GBASE-T RJ45 and 4-Port 40GE QSFP+ Optical Switch Control Unit
                bnameDE01CMUA(688141),                   -- CloudEngine CE12800 CE-CMUA,Centralized MoniToRing Board-1*1
                bnamePWRAC(688142),                      -- CloudEngine CE5800 CE6800 AC Power Module
                bnameDE51DFCMA(688143),                  -- CloudEngine CE5800 CE6800 FAN Control Card
                bnameDE01X48SAASA(688144),               -- CloudEngine CE12800 CE-L48XS-SA,48-Port 10GBASE-X Interface Constringency Card(SFP+)-1*1
                bnameDE01X48SAAGSEA(688145),             -- CloudEngine CE12800 CE-L48GS-EA,48-Port 1000BASE-X  Interface Card(SFP)-1*1
                bnameDE01FCMA(688146),                   -- CloudEngine CE12800 FAN-P02,Fan MoniToR and Control Board-1*1
                bnameDE01POWACA(688147),                 -- CloudEngine CE12800 PAC-2700W-P01,Power Board-1*1
                bnameDE01SFU04B(688148),                 -- CloudEngine12804,CE-SFU04B,CE12804 Switch Fabric Unit B,1*1
                bnameDE01SFU08B(688149),                 -- CE12808,CE-SFU08B,CE12808 Switch Fabric Unit B,1*1
                bnameDE01SFU12B(688150),                 -- CE12812,CE-SFU12B,CE12812 Switch Fabric Unit B,1*1
                bnameDE01SFU04A(688151),                 -- CloudEngine12804,CE-SFU04A,CE12804 Switch Fabric Unit A,1*1
                bnameDE01SFU08A(688152),                 -- CE12808,CE-SFU08A,CE12808 Switch Fabric Unit A,1*1
                bnameDE01SFU12A(688153),                 -- CE12812,CE-SFU12A,CE12812 Switch Fabric Unit A,1*1
                bnameCEL48GTEA(688154),                  -- CloudEngine 12800,CE-L48GT-EA,48-Port 10/100/1000BASE-T Interface Card(EA,RJ45),1*1
                bnameCEL48GSEA(688155),                  -- CloudEngine 12800,CE-L48GS-EA,48-Port 100/1000BASE-X Interface Card(EA,SFP),1*1
                bnameCEL48GTED(688156),                  -- CloudEngine 12800,CE-L48GT-ED,48-Port 10/100/1000BASE-T Interface Card(ED,RJ45)-1*1
                bnameCEL48GSED(688157),                  -- CloudEngine 12800,CE-L48GS-ED,48-Port 100/1000BASE-X Interface Card(ED,SFP),1*1
                bnameCEL48XSED(688158),                  -- CloudEngine 12800,CE-L48XS-ED,48-Port-10GE Interface Card(ED,SFP+),1*1
                bnameCEL48XSEF(688159),                  -- CloudEngine 12800,CE-L48XS-EF,48-Port-10GE Interface Card(EF,SFP+),1*1
                bnameCEL24XSED(688160),                  -- CloudEngine 12800,CE-L24XS-ED,24-Port-10GE Interface Card(ED,SFP+),1*1
                bnameCEL24XSEF(688161),                  -- CloudEngine 12800,CE-L24XS-EF,24-Port-10GE Interface Card(EF,SFP+),1*1
                bnameCEL12LQEA(688162),                  -- CloudEngine 12800,CE-L12LQ-EA,12-Port-40G Interface Card(EA,QSFP+),1*1
                bnameCEL12LQEF(688163),                  -- CloudEngine 12800,CE-L12LQ-EF,12-Port-40G Interface Card(EF,QSFP+),1*1
                bnameCEM24T4SP01(688164),                -- CloudEngine CE5810 CE5810-24T4S-EI Switch(24-Port GE RJ45,4-Port 10GE SFP+,Without Fan and Power Module)
                bnameCEM48T4SP01(688165),                -- CloudEngine CE5810 CE5810-48T4S-EI Switch(48-Port GE RJ45,4-Port 10GE SFP+,Without Fan and Power Module)
                bnameCEM48T4S2QP02(688166),              -- CloudEngine 5800,CEM48T4S2QP02,48-Port GE RJ45,4-Port SFP+ Optical,2-Port 40GE QSFP+ Optical Switch Control Unit,1*1
                bnameCEL06LQEA(688167),                  -- CloudEngine 12800,CE-L06LQ-EA,6-Port-40G Interface Card(EA,QSFP+),1*1
                bnameCEL06LQEF(688168),                  -- CloudEngine 12800,CE-L06LQ-EF,6-Port-40G Interface Card(EF,QSFP+),1*1
                bnameCESFU16A(688169),                   -- CloudEngine 12800,CE-SFU16A CE12816 Switch Fabric Unit A 1*1
                bnameCEL12XSED(688171),                  -- CloudEngine 12800,CE-L12XS-ED,12-Port-10GE Interface Card(ED,SFP+),1*1
                bnameCECMUB(688172),                     -- CloudEngine 12800,CE-CMUB,Centralized Monitoring Board B,1*1
                bnameCEL48GTEC(688173),                  -- CloudEngine 12800,CE-L48GT-EC,48-Port 10/100/1000BASE-T Interface Card(EC,RJ45),1*1
                bnameCEL48GSEC(688174),                  -- CloudEngine 12800,CE-L48GS-EC,48-Port 100/1000BASE-X Interface Card(EC,SFP),1*1
                bnameCEL24XSBA(688175),                  -- CloudEngine 12800,CE-L24XS-BA,24-Port 10GBASE-X Interface Card(BA,SFP+),1*1
                bnameCEL48XSBA(688176),                  -- CloudEngine 12800,CE-L48XS-BA,48-Port 10GBASE-X Interface Card(BA,SFP+),1*1
                bnameCESFU16B(688177),                   -- CloudEngine 12800,CE-SFU16B,CE12816 Switch Fabric Unit B,1*1
                bnameCESFU16C(688178),                   -- CloudEngine 12800,CE-SFU16C,CE12816 Switch Fabric Unit C,1*1
                bnameCEL04CFEF(688179),                  -- CloudEngine 12800,CE-L04CF-EF,4-Port-100GE Interface Card(EF,CFP),1*1
                bnameCEL24XSEC(688180),                  -- CloudEngine 12800,CE-L24XS-EC,24-Port-10GE Interface Card(EC,SFP+),1*1
                bnameCEL48XSEC(688181),                  -- CloudEngine 12800,CE-L48XS-EC,48-Port-10GE Interface Card(EC,SFP+),1*1
                bnameCEL24LQEC(688182),                  -- CloudEngine 12800,CE-L24LQ-EC,24-Port 40G Interface Card(EC,QSFP+),1*1
                bnameCEL04CFEA(688183),                  -- CloudEngine 12800,CE-L04CF-EA,4-Port-100GE Interface Card(EA,CFP),1*1
                bnameCE785032QEI(688184),                -- CloudEngine 7800,CEM32QP01,32-Port 40GE QSFP+ Optical Switch Control Unit,1*1
                bnameCE681048S4QEI(688185),              -- CloudEngine 6800,CEM48S4QP02,48-Port SFP+ Optical,4-Port 40GE QSFP+ Optical Switch Control Unit,1*1
                bnameCE681048S4QLI(688186),              -- CloudEngine 6800,CEM48S4QP04,48-Port SFP+ Optical,4-Port 40GE QSFP+ Optical Switch Control Unit,1*1
                bnameCEL48GTEF(688187),                  -- Manufactured Board,iCE,CE-L48GT-EF,48-Port 10/100/1000BASE-T Interface Card(EF,RJ45)-1*1
                bnameCE681048SLI(688188),                -- CloudEngine 6800,CEM48SP01,48-Port SFP+ Optical Switch Control Unit,1*1
                bnameCE685048S6QHI(688189),              -- CloudEngine 6800,CE6850-48S6Q-HI Switch(48-Port 10GE SFP+,6-Port 40GE QSFP+)
                bnameCEMPUAS(688190),                    -- Manufactured Board,CloudEngine 12800S,CE-MPUA-S
                bnameCEL48XTEC(688191),                  -- Manufactured Board,CloudEngine 12800,CE-L48XT-EC,1*1
                bnameCEL12CFEG(688192),                  -- Manufactured Board,CloudEngine 12800,CE-L12CF-EG,12-Port-100GE Interface Card(EG,CFP2),1*1
                bnameCEFWA(688193),                      -- Manufactured Board,CloudEngine 12800,CE-FWA,Fire Wall Card A,1*1
                bnameCEL08CCEC(688194),                  -- Manufactured Board,CloudEngine 12800,CE-L08CC-EC,1*1
                bnameCEL24LQEC1(688195),                 -- Manufactured Board,CE-L24LQ-EC1
                bnameCESFUBS(688196),                    -- Manufactured Board,CloudEngine 12800S,CE-SFUB-S
                bnameCESFUCS(688197),                    -- Manufactured Board,CloudEngine 12800S,CE-SFUC-S,CE-SFUC-S,1*1
                bnameCE6850U48S6QHI(688198),             -- CloudEngine 6800-CEM48S6QP02,48-Port 10GE SFP+,support 2/4/8G FC,6-Port 40GE QSFP+ Optical Switch Control Unit,1*1
                bnameCE685048T6QHI(688199),              -- CloudEngine 6800-CEM48T6QP01,48-Port 10GE RJ45,6-Port 40GE QSFP+ Optical Switch Control Unit,1*1
                bnameCE681032T16S4QLI(688200),           -- CloudEngine 6800-CEM32T16S4QP01,32-Port 10GE RJ45,16-Port 10GE SFP+ Optical,4-Port 40GE QSFP+ Optical Switch Control Unit,1*1
                bnameCE585548T4S2QEI(688202),            -- CloudEngine 5800-CEM48T4S2QP03,48-Port GE RJ45,4-Port SFP+ Optical,2-Port 40GE QSFP+ Optical Switch Control Unit,1*1
                bnameCE585524T4S2QEI(688203),            -- CloudEngine 5800-CEM24T4S2QP03,24-Port GE RJ45,4-Port SFP+ Optical,2-Port 40GE QSFP+ Optical Switch Control Unit,1*1
                bnameCE6850U24S2QHI(688204),             -- CloudEngine 6800-CEM24S2QP02,24-Port 10GE SFP+,support 2/4/8G FC,2-Port 40GE QSFP+ Optical Switch Control Unit,1*1
                bnameCE681024S2QLI(688205),              -- CloudEngine 6800-CEM24S2QP01,24-Port 10GE SFP+,2-Port 40GE QSFP+ Optical Switch Control Unit,1*1
                bnameCE685148S6QHI(688206),              -- CloudEngine 6800-CEM48S6QP04,48-Port 10GE SFP+,6-Port 40GE QSFP+ Optical Switch Control Unit,1*1
                bnameCEL36LQEG(688207),                  -- Manufactured Board,CloudEngine 12800-CE-L36LQ-EG,36-Port 40GE Interface Card(EG,QSFP+)-1*1
                bnameCE88604CEI(688208),                 -- CloudEngine CE8860-4C-EI Switch(with 4 interface slots)
                bnameCEL02LQEC(688209),                  -- Manufactured Board,CloudEngine 12800,CE-L02LQ-EC,2-Port-40G Interface Card(EC,QSFP+)
                bnameCEL04CFMD(688210),                  -- Manufactured Board,CloudEngine 12800,CE-L04CF-MD,4-Port-100GE Interface Card(MD,CFP),1*1
                bnameCEL24LQMC1(688211),                 -- Manufactured Board,CloudEngine 12800,CE-L24LQ-EC1,24-Port-40G Interface Card(MC1,QSFP+),1*1
                bnameCEL12LQMD(688212),                  -- Manufactured Board,CloudEngine 12800,CE-L12LQ-MD,12-Port-40G Interface Card(MD,QSFP+),1*1
                bnameCEL48XSMD(688213),                  -- Manufactured Board,CloudEngine 12800,CE-L48XS-MD,48-Port-10GE Interface Card(MD,QSFP+),1*1
                bnameCEL48XSMC(688214),                  -- Manufactured Board,CloudEngine 12800,CE-L48XS-MC,48-Port-10GE Interface Card(MC,QSFP+),1*1
                bnameCE685548T6QHI(688215),              -- Manufactured Board,CloudEngine 6800,CEM48T6QP02,48 Port 10GE RJ45, 6 Port 40GE QSFP+ Optical Switch Control Unit,1*1
                bnameCE685548S6QHI(688216),              -- Manufactured Board,CloudEngine 6800,CEM48S6QP05,48-Port SFP+ Optical,6-Port 40GE QSFP+ Optical Switch Control Unit,1*1
                bnameCEL36CQFD(688217),                  -- Manufactured Board,CloudEngine 12800,CE-L36CQ-FD,36-Port-100GE Interface Card(FD,QSFP28)
                bnameCEL36LQFD(688218),                  -- Manufactured Board,CloudEngine 12800,CE-L36LQ-FD,36-Port-40GE Interface Card(FD,QSFP+)
                bnameCEL48XSFDA(688219),                 -- Manufactured Board,CE-L48XS-FDA,48-Port-10GE,2-Port-40GE,2-Port-100GE Interface Card(FDA,SFP+,QSFP+,QSFP28)
                bnameCESFU08F(688220),                   -- Manufactured Board,CloudEngine 12800,CE-SFU08F,CE12808 Switch Fabric Unit F,1*1
                bnameCESFU16F(688221),                   -- Manufactured Board,CloudEngine 12800,CE-SFU16F,CE12816 Switch Fabric Unit F,1*1
                bnameCESFUFS(688222),                    -- Manufactured Board,CloudEngine 12800S,CE01SFUFS,CE12800S Switch Fabric Unit F,1*1
                bnameCESFU16G(688223),                   -- Manufactured Board,CloudEngine 12800,CE-SFU16G,CE12816 Switch Fabric Unit G,1*1
                bnameCESFU12G(688224),                   -- Manufactured Board,CloudEngine 12800,CE-SFU12G,CE12812 Switch Fabric Unit G,1*1
                bnameCEL04CFEC(688225),                  -- Manufactured Board,CloudEngine 12800,CE-L04CF-EC,4-Port-100GE Interface Card(EC,CFP)
                bnameCE686048S18CQEI(688226),            -- Manufactured Board,CloudEngine 6800,CEM48S18CQP01,48-Port 25GE SFP28 Optical,18-Port 100GE QSFP28 Optical Switch Control Unit,1*1
                bnameCE686048S8CQEI(688227),             -- Manufactured Board,CloudEngine 6800,CEM48S8CQP01,48-Port 25GE SFP28 Optical,8-Port 100GE QSFP28 Optical Switch Control Unit,1*1
                bnameCE687048S6CQEI(688228),             -- Manufactured Board,CloudEngine 6800,CEM48S6CQP01,48-Port SFP+ Optical,6-Port 100GE QSFP28 Optical Switch Control Unit,1*1
                bnameCE687024S6CQEI(688229),             -- Manufactured Board,CloudEngine 6800,CEM24S6CQP01,24-Port SFP+ Optical,6-Port 100GE QSFP28 Optical Switch Control Unit,1*1
                bnameCE785532QEI(688230),                -- Manufactured Board,CloudEngine 7800,CEM32QP02,32-Port 40GE QSFP+ Optical Switch Control Unit,1*1
                bnameCEL24LQFD(688231),                  -- Manufactured Board,CloudEngine 12800,CE-L24LQ-FD,24-Port-40GE Interface Card(FD,QSFP+)
                bnameCEL12CQFD(688232),                  -- Manufactured Board,CloudEngine 12800,CE-L12CQ-FD,12-Port-100GE Interface Card(FD,QSFP28)
                bnameCEL48XSFD(688233),                  -- Manufactured Board,CloudEngine 12800,CE-L48XS-FD,48-Port-10GE Interface Card(FD,SFP+)
                bnameCESFUAS(688234),                    -- CloudEngine 12800S,CE-SFUA-S,CE12800S Switch Fabric Unit A
                bnameCE688048S4Q2CQEI(688235),           -- Manufactured Board,CloudEngine 6800,CEM48S4Q2CQP01,48-Port SFP+ Optical,4-Port 40GE QSFP+ Optical,2-Port 100GE QSFP28 Optical Switch Control Unit,1*1
                bnameCE688024S4Q2CQEI(688236),           -- Manufactured Board,CloudEngine 6800,CEM24S4Q2CQP01,24-Port SFP+ Optical,4-Port 40GE QSFP+ Optical,2-Port 100GE QSFP28 Optical Switch Control Unit,1*1
                bnameCE688048T4Q2CQEI(688237),           -- Manufactured Board,CloudEngine 6800,CEM48T4Q2CQP01,48-Port 10GE RJ45,4-Port 40GE QSFP+ Optical,2-Port 100GE QSFP28 Optical Switch Control Unit,1*1
                bnameCESFU16GM(688238),                  -- Manufactured Board,CloudEngine 12800,CE-SFU16G-M,CE12816M Switch Fabric Unit G
                bnameCEL36CQFDM(688239),                 -- Manufactured Board,CloudEngine 12800,CEL36CQFD-M,36-Port-100GE Interface Card(FD-M,QSFP28)
                bnameCEL36LQFDM(688240),                 -- Manufactured Board,CloudEngine 12800,CEL36LQFD-M,36-Port-40GE Interface Card(FD-M,QSFP+)
                bnameCEL24LQFDM(688241),                 -- Manufactured Board,CloudEngine 12800,CEL24LQFD-M,24-Port-40GE Interface Card(FD-M,QSFP+)
                bnameCEL12CQFDM(688242),                 -- Manufactured Board,CloudEngine 12800,CEL12CQFD-M,12-Port-100GE Interface Card(FD-M,QSFP28)
                bnameCEL48XSFDAM(688243),                -- Manufactured Board,CloudEngine 12800,CEL48XSFDA-M,48-Port-10GE,2-Port-40GE,2-Port-100GE Interface Card(FDA-M,SFP+,QSFP+,QSFP28)
                bnameCEL48XSFDM(688244),                 -- Manufactured Board,CloudEngine 12800,CEL48XSFD-M,48-Port-10GE Interface Card(FD-M,SFP+)
                bnameCE885032CQEI(688245),               -- Manufactured Board,CloudEngine 8800,CEM32CQP01,32-Port 100GE QSFP28,2-Port 10GE SFP+ Optical Switch Control Unit,1*1
                bnameCESFU08G(688246),                   -- Manufactured Board,CloudEngine 12800,CE-SFU08G,CE12808 Switch Fabric Unit G,1*1
                bnameCESFU04G(688247),                   -- Manufactured Board,CloudEngine 12800,CE-SFU04G,CE12804 Switch Fabric Unit G,1*1
                bnameCESFU16CE(688248),                  -- Manufactured Board,CloudEngine 12800,CESFU16CE,CE12816E Switch Fabric Unit C,1*1
                bnameCESFU12CE(688249),                  -- Manufactured Board,CloudEngine 12800,CESFU12CE,CE12812E Switch Fabric Unit C,1*1
                bnameCESFU08CE(688250),                  -- Manufactured Board,CloudEngine 12800,CESFU08CE,CE12808E Switch Fabric Unit C,1*1
                bnameCESFU04CE(688251),                  -- Manufactured Board,CloudEngine 12800,CESFU04CE,CE12804E Switch Fabric Unit C,1*1
                bnameCEL16CQEGE(688252),                 -- Manufactured Board,CloudEngine 12800E,CEL16CQEG-E,16-Port-100GE Interface ENP Card(EG,QSFP28)
                bnameCEL36LQEDE(688253),                 -- Manufactured Board,CloudEngine 12800E,CEL36LQED-E,36-Port-40GE Interface ENP Card(ED,QSFP+)
                bnameCEL36LQEGE(688254),                 -- Manufactured Board,CloudEngine 12800E,CEL36LQEG-E,36-Port-40GE Interface ENP Card(EG,QSFP+)
                bnameCEL48XSEGAE(688255),                -- Manufactured Board,CloudEngine 12800,CEL48XSEGA-E,48-Port-10GE,4-Port-100GE Interface Card(NGA,SFP+,QSFP28)
                bnameCEL24XSEGAE(688256),                -- Manufactured Board,CloudEngine 12800E,CEL24XSEGA-E,24-Port-10GE,2-Port-100GE Interface ENP Card(EGA,SFP+,QSFP28)
                bnameCEL48XSEDE(688257),                 -- Manufactured Board,CloudEngine 12800E,CEL48XSED-E,48-Port 10GBASE-X Interface ENP Card(ED,SFP+)
                bnameCEL24XSEDE(688258),                 -- Manufactured Board,CloudEngine 12800E,CEL24XSED-E,24-Port 10GBASE-X Interface ENP Card(ED,SFP+)
                bnameCEMPUAE(688259),                    -- Manufactured Board,CloudEngine 12800E,CE-MPUA-E,CE12800E Main Processing Unit A,1*1
                bnameCEL24XSEC1(688260),                 -- (DXJC)Manufactured Board,CloudEngine 12800,CE-L24XS-EC1
                bnameCEL04CFEC1(688261),                 -- (DXJC)Manufactured Board,CloudEngine 12800,CE-L04CF-EC1,4-Port-100GE Interface Card(EC1,CFP)
                bnameSIAMESEDFAN(688262),                -- CloudEngine 12800E,Siamesedfan
                bnameVERTICALPOW(688263),                -- CloudEngine 12800E,Power Module for CE12808E,CE12812E and CE12816E
                bnameCEL04CFEC1B(688264),                -- Manufactured Board,CloudEngine 12800,CE-L04CF-EC1,4-Port-100GE Interface Card(EC1,CFP)
                bnameCE687048T6CQEI(688265),             -- Manufactured Board,CloudEngine 6800,CEM48T6CQP01,48-Port 10GE RJ45,6-Port 100GE QSFP28 Optical Switch Control Unit,1*1
                bnameCEL06CQFD(688266),                  -- (YDJC)Manufactured Board,CloudEngine 12800,CEL06CQFD,6-Port-100GE Interface Card(FD,QSFP28)
                bnameCEL06CQFDM(688267),                 -- (YDJC)Manufactured Board,CloudEngine 12800,CEL06CQFD-M,6-Port-100GE Interface Card(FD-M,QSFP28)
                bnameNSEL32XSEGA(688268),                -- Board for wangan
                bnameCEL36CQFG(688269),                  -- Manufactured Board,CloudEngine 12800,CE-L36CQ-FG,36-Port-100GE Interface Card(FG,QSFP28)
                bnameCEL48XSFG(688270),                  -- Manufactured Board,CloudEngine 12800,CE-L48XS-FG,48-Port-10GE Interface Card(FG,SFP+)
                bnameCEL48GTEGAE(688271),                -- Manufactured Board,CloudEngine 12800E,CEL48GTEGA-E,48-Port-GE,4-Port-10GE Interface ENP Card(EGA,RJ45,SFP+)
                bnameCE685648S6QHI(688273),              -- Manufactured Board,CloudEngine 6800,CEM48S6QP05,48-Port SFP+ Optical,6-Port 40GE QSFP+ Optical Switch Control Unit,1*1
                bnameCE685648T6QHI(688274),              -- Manufactured Board,CloudEngine 6800,CEM48T6QP02,48 Port 10GE RJ45, 6 Port 40GE QSFP+ Optical Switch Control Unit,1*1
                bnameCX916(688275),                      -- CX916
                bnameCEL08CFFG1(688276),                 -- Manufactured Board,CloudEngine 12800,CE-L08CF-FG1,8-Port-100GE Interface Card(FG1,CFP2)
                bnameCEL16CQFD(688277),                  -- Manufactured Board,CloudEngine 12800,CE-L16CQ-FD,16-Port-100GE Interface Card(FD,QSFP28)
                bnameCEL48XSFD1(688279),                 -- Manufactured Board,CloudEngine 12800,CE-L48XS-FD1,48-Port-10GE Interface Card(FD1,SFP+)
                bnameCE687548S4CQEI(688280),             -- Manufactured Board,CloudEngine 6800,CEM48S4CQP01,48-Port 10GE SFP+,4-Port 100GE QSFP28 Optical Switch Control Unit,1*1
                bnameCEMPUBS(688283),                    -- Manufactured Board,CloudEngine 12800S,CE-MPUB-S
                bnameCESFUGS(688284),                    -- Manufactured Board,CloudEngine 12800S,CE-SFUG-S,CE12800S Switch Fabric Unit G,1*1
                bnameCEL18CQFDA(688285),                 -- Manufactured Board,CloudEngine 12800,CE-L18CQ-FDA,18-Port-40GE,18-Port-100GE Interface Card(FDA,QSFP+,QSFP28)
                bnameCEL18CQFDAM(688286),                -- (YDJC)Manufactured Board,CloudEngine 12800,CEL18CQFDA-M,18-Port-40GE,18-Port-100GE Interface Card(FDA-M,QSFP+,QSFP28)
                bnameCE686548S8CQEI(688287),             -- Manufactured Board,CloudEngine 6800,CEM48S8CQP04,48-Port 25GE SFP28 Optical,8-Port 100GE QSFP28 Optical Switch Control Unit,1*1
                bnameCE885064CQEI(688288),               -- Manufactured Board,CloudEngine 8800,CEM64CQP01,64-Port 100GE QSFP28 Optical,2-Port 10GE SFP+ Optical Switch Control Unit,1*1
                bnameCEL36CQFDX(688290),                 -- Manufactured Board,CloudEngine 12800E,CEL36CQFD-X,36-Port-100GE Interface XGS Card(FD,QSFP28),1*1
                bnameCESFU08GX(688291),                  -- Manufactured Board,CloudEngine 12800E,CESFU08GX,CE12808E Switch Fabric Unit G,1*1
                bnameCESFU16GX(688292),                  -- Manufactured Board,CloudEngine 12800E,CESFU16GX,CE12816E Switch Fabric Unit G,1*1
                bnameCE88614CEI(688294),                 -- Manufactured Board,CloudEngine 8800,CEM884CP02,General Switch Control Unit,1*1
                bnameCEL36CQFD1(688296),                 -- Manufactured Board,CloudEngine 12800,CE-L36CQ-FD1,36-Port-100GE Interface Card(FD1,QSFP28)
                bnameCEL36CQSD(688297),                  -- Manufactured Board,CloudEngine 12800,CE-L36CQ-SD,36-Port-100GE Interface Card(SD,QSFP28)
                bnameCE588048T6QEI(688308),              -- Manufactured Board,CloudEngine 6800,CEM48T4Q2CQP01,48-Port 10GE RJ45,4-Port 40GE QSFP+ Optical,2-Port 100GE QSFP28 Optical Switch Control Unit,1*1
                bnameCEL24LQEDE(688309),                 -- Manufactured Board,CloudEngine 12800E,CEL24LQED-E,24-Port-40GE Interface ENP Card(ED,QSFP+)
                bnameCE88684CEI(688310),                 -- Manufactured Board,CloudEngine 8800,CEM884CP02,General Switch Control Unit,1*1
                bnameCEMPUB(688311),                     -- Manufactured Board,CloudEngine 12800,CE-MPUB,Main Processing Unit B,1*1
                bnameCX930(688313),                      -- CX930
                bnameCE685748S6CQEI(688314),             -- Manufactured Board,CloudEngine 6800,CEM48S6CQP03,48-Port 10GE SFP+ Optical,6-Port 100GE QSFP28 Optical Switch Control Unit,1*1
                bnameCX930BASE(688315),                  -- CX930BASE
                bnameCEMPUDHALF(688318),                 -- Finished Board Unit,CE16800,CE-MPUD-HALF,CE16800 Main Processing Unit D (half-width)
                bnameCESFUF1S(688319),                   -- Manufactured Board,CloudEngine 12800S,CE-SFUF1-S,CE12800S Switch Fabric Unit F1,1*1
                bnameCESFU08F1(688320),                  -- Manufactured Board,CloudEngine 12800,CE-SFU08F1,CE12808 Switch Fabric Unit F1,1*1
                bnameCESFU08G1(688321),                  -- Manufactured Board,CloudEngine 12800,CE-SFU08G1,CE12808 Switch Fabric Unit G1,1*1
                bnameCEL36LQFDG(688322),                 -- Finished Board Unit,CloudEngine 16800,CEL36LQFD-G,36-port 40GE interface card (FD-G, QSFP+)
                bnameCESFU08GG(688323),                  -- Finished Board Unit,CE16800,CE-SFU08G-G,CE16808 Switch Fabric Unit G
                bnameCEMPUCS(688325),                    -- Manufactured Board,CloudEngine 12800S,CE-MPUC-S
                bnameCECMUC(688326),                     -- CloudEngine 12800,CE-CMUC,Centralized Monitoring Board B,1*1
                bnameCE98604CEI(688327),                 -- Manufactured Board,CloudEngine 9800,128x100G QSFP28 Tomahawk3 x86
                bnameCESFU16F1(688328),                  -- Manufactured Board,CloudEngine 12816,CE-SFU16F1,CE12816 Switch Fabric Unit F,1*1
                bnameCESFU16G1(688329),                  -- Manufactured Board,CloudEngine 12816,CE-SFU16G1,CE12816 Switch Fabric Unit G,1*1
                bnameCESFU04G1(688330),                  -- Manufactured Board,CloudEngine 12804,CE-SFU04G1,CE12804 Switch Fabric Unit G,1*1
                bnameCEL18CQFDG(688331),                 -- Finished Board Unit,CloudEngine 16800,CEL18CQFD-G,18-port 100GE interface card (FD-G, QSFP28)
                bnameCEL36CQFDG(688332),                 -- Finished Board Unit,CloudEngine 16800,CEL36CQFD-G,36-port 100GE interface card (FD-G, QSFP28)
                bnameCESFU08FG(688333),                  -- Finished Board Unit,CE16800,CE-SFU08F-G,CE16808 Switch Fabric Unit F
                bnameCESFU04GG(688337),                  -- Finished Board Unit,CE16800,CE-SFU04G-G,CE16804 Switch Fabric Unit G
                bnameCEL48XSFDG(688338),                 -- Finished Board Unit,CloudEngine 16800,CEL48XSFD-G,48-port 10GE interface card (FD-G, SFP+)
                bnameCE686348S6CQ(688339),               -- CloudEngine 6800,CE6863-48S6CQ-F,CE6863-48S6CQ-F switch
                bnameCE688148S6CQ(688340),               -- CloudEngine 6800,CE6881-48S6CQ-F,CE6881-48S6CQ-F switch
                bnameCESFU16GG(688341),                  -- Finished Board Unit,CE16800,CE-SFU16G-G,CE16816 Switch Fabric Unit G
                bnameCESFU16FG(688342),                  -- Finished Board Unit,CE16800,CE-SFU16F-G,CE16816 Switch Fabric Unit F
                bnameCEL24LQFDG(688343),                 -- Finished Board Unit,CloudEngine 16800,CEL24LQFD-G,24-port 40GE interface card (FD-G, QSFP+)
                bnameCEMPUDFULL(688344),                 -- Finished Board Unit,CE16800,CE-MPUD-FULL,CE16800 Main Processing Unit D (full-width)
                bnameCESFU04FG(688345),                  -- Finished Board Unit,CE16800,CE-SFU04F-G,CE16804 Switch Fabric Unit F
                bnameCE682048S6CQ(688347),               -- CloudEngine 6800, CE6820-48S6CQ, CE6820-48S6CQ switch
                bnameCE686548S8CQSI(688348),             -- CloudEngine 6800, CE6865-48S8CQ-SI, CE6865-48S8CQ-SI switch
                bnameCEMPUEHALF(688349),                 -- Finished Board Unit,CE16800,CE-MPUE-HALF,CE16800 Main Processing Unit E (half-width)
                bnameCEL24LQFDAG(688350),                -- Finished Board Unit,CloudEngine 16800,CEL24LQFDA-G,24-port 40GE, 6-port 100GE interface card (FDA-G, QSFP+,QSFP28)
                bnameCEMPUEFULL(688351),                 -- Finished Board Unit,CE16800,CE-MPUE-FULL,CE16800 Main Processing Unit E (full-width)
                bnameCEL48GSFDG(688352),                 -- Finished Board Unit,CloudEngine 16800,CEL48GSFD-G,48-port 100M/GE interface card (FD-G, SFP)
                bnameCEL18CQFDAG(688353),                -- Finished Board Unit,CloudEngine 16800,CEL18CQFDA-G,18-port 40GE, 18-port 100GE interface card (FDA-G, QSFP+,QSFP28)
                bnameCE686348S6CQK(688354),              -- CloudEngine 6800,CE6863-48S6CQ-KF,CE6863-48S6CQ-KF switch 
				bnameCE688148S6CQK(688355),              -- CloudEngine 6800,CE6881-48S6CQ-KF,CE6881-48S6CQ-KF switch 
				bnameCE6881E48S6CQ(688356),              -- CloudEngine 6800,CE6881E-48S6CQ-B,CE6881E-48S6CQ-B switch 
				bnameCEMPUDHK(688357),                   -- Finished Board Unit,CE16800,CE-MPUD-HK,CE16800 Main Processing Unit D-HK (half-width)
				bnameCEMPUDFK(688358),                   -- Finished Board Unit,CE16800,CE-MPUD-FK,CE16800 Main Processing Unit D-FK (full-width)
				bnameCEL36CQFDGK(688359),                -- Finished Board Unit,CloudEngine 16800,CEL36CQFD-GK,36-port 100GE interface card (FD-GK, QSFP28)
				bnameCEL18CQFDGK(688360),                -- Finished Board Unit,CloudEngine 16800,CEL18CQFD-GK,18-port 100GE interface card (FD-GK, QSFP28)
				bnameCEL36LQFDGK(688361),                -- Finished Board Unit,CloudEngine 16800,CEL36LQFD-GK,36-port 40GE interface card (FD-GK, QSFP+)
				bnameCEL24LQFDGK(688362),                -- Finished Board Unit,CloudEngine 16800,CEL24LQFD-GK,24-port 40GE interface card (FD-GK, QSFP+)
				bnameCEL48XSFDGK(688363),                -- Finished Board Unit,CloudEngine 16800,CEL48XSFD-GK,48-port 10GE interface card (FD-GK, SFP+)
				bnameCESFU04GGK(688364),                 -- Finished Board Unit,CE16800,CE-SFU04G-GK,CE16804 Switch Fabric Unit GK
				bnameCESFU08GGK(688365),                 -- Finished Board Unit,CE16800,CE-SFU08G-GK,CE16808 Switch Fabric Unit GK
				bnameCESFU16GGK(688366),                 -- Finished Board Unit,CE16800,CE-SFU16G-GK,CE16816 Switch Fabric Unit GK
				bnameCEL48XSFD1G(688367),                -- Finished Board Unit,CloudEngine 16800,CEL48XSFD1-G,48-port 10GE interface card (FD1-G, SFP+)
				bnameCEL24LQFD1G(688368),                -- Finished Board Unit,CloudEngine 16800,CEL24LQFD1-G,24-port 40GE interface card (FD1-G, QSFP+)
				bnameCEL36LQFD1G(688369),                -- Finished Board Unit,CloudEngine 16800,CEL36LQFD1-G,36-port 40GE interface card (FD1-G, QSFP+)
				bnameCESFU04F1G(688370),                 -- Finished Board Unit,CE16800,CE-SFU04F1-G,CE16804 Switch Fabric Unit F1
				bnameCESFU08F1G(688371),                 -- Finished Board Unit,CE16800,CE-SFU08F1-G,CE16808 Switch Fabric Unit F1
				bnameCE688148T6CQ(688372),               -- CloudEngine 6800,CE6881-48T6CQ,CE6881-48T6CQ switch 
                bnameCE886832CQ8DQP(688373),             -- CloudEngine 8800,CE8868-32CQ8DQ-P,CE8868-32CQ8DQ-P Switch
                bnameCE885132CQ8DQP(688374),             -- CloudEngine 8800,CE8851-32CQ8DQ-P,CE8851-32CQ8DQ-P Switch
                bnameCE686848S8CQP(688375),              -- CloudEngine 6800,CE6868-48S8CQ-P,CE6868-48S8CQ-P switch 
                bnameCE686648S8CQP(688376),              -- CloudEngine 6800,CE6866-48S8CQ-P,CE6866-48S8CQ-P switch 
                bnameCESFU16JP(688377),                  -- Finished Board Unit,CE16800,CE-SFU16J-P,CE16816 Switch Fabric Unit J-P
                bnameCESFU08JP(688378),                  -- Finished Board Unit,CE16800,CE-SFU08J-P,CE16808 Switch Fabric Unit J-P
                bnameCESFU08HP(688379),                  -- Finished Board Unit,CE16800,CE-SFU08H-P,CE16808 Switch Fabric Unit H-P
                bnameCESFU04JP(688380),                  -- Finished Board Unit,CE16800,CE-SFU04J-P,CE16804 Switch Fabric Unit J-P
                bnameCESFU04HP(688381),                  -- Finished Board Unit,CE16800,CE-SFU04H-P,CE16804 Switch Fabric Unit H-P
                bnameCEMPUE(688382),                     -- Finished Board Unit,CE16800,CE-MPUE,CE16800 Main Processing Unit E
                bnameCEMPUD(688383),                     -- Finished Board Unit,CE16800,CE-MPUD,CE16800 Main Processing Unit D
                bnameCEL48XSHGAP(688384),                -- Finished Board Unit, CloudEngine 16800, CEL48XSHGA-P, 48-port 25GE and 2-port 100GE interface card with ENP (EGA, QSFP28)
                bnameCEL48CQHGP(688385),                 -- Finished Board Unit,CloudEngine 16800,CEL48CQHG-P,48-port 100GE interface card (HG-P, QSFP28)
                bnameCEL36DQHGP(688386),                 -- Finished Board Unit,CloudEngine 16800,CEL36DQHG-P,36-port 400GE interface card (HG-P,QSFP-DD)
                bnameCE688148T6CQK(688387),              -- CloudEngine 6800,CE6881-48T6CQ-F,CE6881-48T6CQ-F switch
				bnameCEL72XSHGAP(688388),                -- Finished Board Unit, CloudEngine 16800, CEL72XSHGA-P, 72-port 25GE and 6-port 100GE interface card with ENP 
				bnameCE588148T6CQ(688389),               -- CloudEngine 5800,CE5881-48T6CQ,CE5881-48T6CQ switch
				bnameCE885132CQ8DQK(688390),             -- CloudEngine 8800,CE8851-32CQ8DQ-K,CE8851-32CQ8DQ-K switch
				bnameCE686648S8CQK(688391),              -- CloudEngine 6800,CE6866-48S8CQ-K,CE6866-48S8CQ-K switch
				bnameDX110(688392),                      -- DX110
				bnameCEMPUDFT(688393),                   -- Finished Board Unit,CE16800,CE-MPUD-FT,CE16800 Main Processing Unit D (full-width)-TPM
				bnameCEMPUDHT(688394),                   -- Finished Board Unit,CE16800,CE-MPUD-HT,CE16800 Main Processing Unit D (half-width)-TPM
				bnameCESFU08FGK(688395),                 -- Finished Board Unit,CE16800,CE-SFU08F-GK,CE16808 Switch Fabric Unit F-GK
				bnameCE5855E48T4S2Q(688396),             -- CloudEngine 5800,CE5855E-48T4S2Q,CE5855E-48T4S2Q switch 
				bnameCE6857E48S6CQ(688397),              -- CloudEngine 6800,CE6857E-48S6CQ,CE6857E-48S6CQ switch
				bnameCE6857E48T6CQ(688398),              -- CloudEngine 6800,CE6857E-48T6CQ,CE6857E-48T6CQ switch 
				bnameCEL18CQFD(688399),                  -- Finished Board,CloudEngine 12800,CE-L18CQ-FD,18-Port-100GE Interface Card(FD, QSFP28)
				bnameCE6865E48S8CQ(688400),              -- CloudEngine 6800,CE6865E-48S8CQ,CE6865E-48S8CQ switch
				bnameCEL48CQHGX(688401),                 -- Finished Board Unit,CloudEngine 16800,CEL48CQHG-X,48-port 100GE interface card (HG-X, QSFP28)
				bnameCE6860SAN(688402),                  -- CloudEngine 6800,CE6860-SAN switch (48*25G SFP28, 8*100G QSFP28, without fan and power modules)(CM)
				bnameCE8850SAN(688403),                  -- CloudEngine 8800,CE8850-SAN switch (32*100G QSFP28, without fan and power modules)(CM)
				bnameCEL48CQSAN(688404),                 -- 48-port 100GE SAN interface card(SAN, QSFP28)(CM)
				bnameCEL72XSSAN(688405),                 -- 72-port 25GE and 6-port 100GE interface card with optical module bundle 1 (HGA-P, SFP28, QSFP28, 24*10GE+2*100GE port RTU, 3*(24*25GE capacity upgrade RTU), 72*25GBase-SR-MP) 
				bnameCEMPUFHALF1E(688406),                 -- Finished Board Unit,CE16800,CE-MPUF-HALF1E,CE16800 Main Processing Unit F (half-width)
				bnameCEMPUFFULL1E(688407),                 -- Finished Board Unit,CE16800,CE-MPUF-FULL1E,CE16800 Main Processing Unit F (full-width)
				bnameCEMPUFHT(688408),                   -- Finished Board Unit,CE16800,CE-MPUF-HT,CE16800 Main Processing Unit F-HT (half-width)
                bnameCEMPUFFT(688409), 	                 -- Finished Board Unit,CE16800,CE-MPUF-FT,CE16800 Main Processing Unit F-FT (full-width) 
				bnameCEL48CCQHGX(688410),                -- Finished Board Unit,CloudEngine 16800,CEL48CCQHG-B,48-port 200GE interface card (HG-B, QSFP56)
				bnameCE6820H48S6CQ(688411),              -- Assembling Components,CloudEngine 6800,CE6820H-48S6CQ-F,CE6820H-48S6CQ switch(48*10G SFP+,6*100GE QSFP28,2*AC power modules,4*fan modules,port-side exhaust)				
				bnameCE5855F48T4S2Q(688412),             -- 
				bnameCE6857F48S6CQ(688413),              -- 
				bnameCE6857F48T6CQ(688414),              -- 
				bnameCE6863E48S6CQ(688415),              -- 
				bnameCESFU16JX(688416),                  -- Finished Board Unit,CE16800,CE-SFU16J-X,CE16816 Switch Fabric Unit J-X
				bnameCESFU08JX(688417),                  -- Finished Board Unit,CE16800,CE-SFU08J-X,CE16808 Switch Fabric Unit J-X
				bnameCESFU08GE(688418),                  -- Finished Board Unit,CloudEngine 16800,CE-SFU08G-E,CE16808 Switch Fabric Unit G-E
				bnameCEL18CQFDE(688419),                 -- Finished Board Unit, CloudEngine 16800, CEL48CQHG-P, 48-port 100GE interface card (HG-P, QSFP28) (CM)
				bnameCEL48XSFDE(688420),                 -- Finished Board Unit,CloudEngine 16800,CEL48XSFD-E,48-port 10GE interface card (FD-E, SFP+)
				bnamePDC3000WA(688421),                  -- 
				bnameCE588248T4S(688422),                -- Assembling Components,CloudEngine 6800,CE6866-48S8CQ-F,CE6865E-48S8CQ-F switch (48*25G SFP28, 8*100G QSFP28, 2*AC power modules, 4*fan modules, port-side exhaust)
				bnameCEL36LQFDA(688423),                 -- Finished Board Unit,CloudEngine 16800,CEL36LQFD-A,36-Port 40GE Interface Card (FD-A, QSFP+)
				bnameCESFU04FA(688424),                  -- Finished Board Unit,CE16800,CESFU04F-A,CE16804 Switch Fabric Unit F-A
				bnameCESFU08FA(688425),                  -- Finished Board Unit,CE16800,CESFU08F-A,CE16808 Switch Fabric Unit F-A
				bnameCESFU04GA(688426),                  -- Finished Board Unit,CE16800,CE-SFU04G-A,CE16804 Switch Fabric Unit G-A		
				bnameCEL48XSFD-A(688427),                -- Finished Board Unit,CloudEngine 16800,CEL48XSFD-A,48-Port 10GE Interface Card (FD-A, SFP+)8)
				bnameCE6881H48S6CQ(688428),              -- Assembling Components,CloudEngine 6800,CE6881H-48S6CQ-F,CE6881H-48S6CQ-F switch (48*10G SFP+, 6*100G QSFP28, 2*AC power modules, 4*fan modules, port-side exhaust)
				bnameCE6863H48S6CQ(688429),              -- Assembling Components,CE6863H-48S6CQ-F,CE6863H-48S6CQ-F,CE6863H-48S6CQ-F switch (48*25GE SFP28, 6*100GE QSFP28, 2*AC power modules, 4*fan modules, port-side exhaust)
				bnameCE8850E32CQEI(688430),                -- Assembling Components,CE8800,CE8850E-32CQ-EI-F,CE8850E-32CQ-EI Switch(32-Port 100GE QSFP28,1-Port 10GE SFP+,2*AC Power Module,2*FAN Box,Port-side Exhaust)
				bnameCEMPUDFULL2(688431),                -- Finished Board Unit,CE16800,CE-MPUD-FULL2,CE16800 Main Processing Unit G (full-width)
				bnameCEMPUDHALF2(688432),                -- Finished Board Unit,CE16800,CE-MPUD-HALF2,CE16800 Main Processing Unit G (half-width)
				bnameCEMPUDF2K(688433),                  -- Finished Board Unit,CE16800,CE-MPUD-F2K,CE16800 Main Processing Unit G-FK (full-width)
				bnameCEMPUDH2K(688434),                  -- Finished Board Unit,CE16800,CE-MPUD-H2K,CE16800 Main Processing Unit G-HK (half-width)
				--bnameCEL36CQFD2G(688435),                 Finished Board Unit,CloudEngine 16800,CEL36CQFD-G,36-port 100GE interface card (FD2-G, QSFP28)
				--bnameCEL36CQFD2-GK(688436),               Finished Board Unit,CloudEngine 16800,CEL36CQFD-GK,36-port 100GE interface card (FD2-GK, QSFP28)
				bnameCEL36CQFDA(688437),                -- Finished Board Unit,CloudEngine 16800,CEL36CQFD-A,36-port 100GE interface card (FD-A, QSFP28)
				bnameCE8850E64CQ(688438)  ,               -- Assembling Components,CE8800,Switch(64-Port 100GE QSFP28,2*AC Power Module,3*FAN Box,Port-side Intake)
				bnameCESFU08GA(688439),                 -- Finished Board Unit,CE16800,CE-SFU08G-A,CE16808 Switch Fabric Unit G-A
				bnameCESFU16GA(688440),                 -- Finished Board Unit,CE16800,CE-SFU16G-A,CE16816 Switch Fabric Unit G-A
				--bnameCE6863E48S6CQK(688441),             Assembling Components,CE6863-48S6CQ-K,switch (48*25GE SFP28, 6*100GE QSFP28, without fan and power modules)
				bnameCESFU04JPK(688442),                 -- Finished Board Unit,CE16800,CE-SFU04J-PK,CE16804 Switch Fabric Unit J-PK
                bnameCESFU04HPK(688443),                 -- Finished Board Unit,CE16800,CE-SFU04H-PK,CE16804 Switch Fabric Unit H-PK
                bnameCESFU08JPK(688444),                 -- Finished Board Unit,CE16800,CE-SFU08J-PK,CE16808 Switch Fabric Unit J-PK
                bnameCESFU08HPK(688445),                 -- Finished Board Unit,CE16800,CE-SFU08H-PK,CE16808 Switch Fabric Unit H-PK 
                bnameCESFU16JPK(688446),                 -- Finished Board Unit,CE16800,CE-SFU16J-PK,CE16816 Switch Fabric Unit J-PK
                bnameCEL48XSFDEK(688447),                -- Finished Board Unit,CloudEngine 16800,CEL48XSFD-EK,48-port 10GE interface card (FD-EK, SFP+)
                bnameCEL24LQFDEK(688448),                -- Finished Board Unit,CloudEngine 16800,CEL24LQFD-EK,24-port 40GE interface card (FD-EK, QSFP+)
                bnameCEL36LQFDEK(688449),                -- Finished Board Unit,CloudEngine 16800,CEL36LQFD-EK,36-port 40GE interface card (FD-EK, QSFP+)
                bnameCEL18CQFDEK(688450),                -- Finished Board Unit,CloudEngine 16800,CEL18CQFD-EK,18-Port 100GE Interface Card (FD-EK, QSFP28)
                bnameCEL36CQFDEK(688451),                -- Finished Board Unit,CloudEngine 16800,CEL36CQFD-EK,36-port 100GE interface card (FD-EK, QSFP28)                    
                bnameCEL24LQFDE(688452),                 -- Finished Board Unit,CloudEngine 16800,CEL24LQFD-E,24-port 40GE interface card (FD-E, QSFP+)
                bnameCEL36LQFDE(688453),                 -- Finished Board Unit,CloudEngine 16800,CEL36LQFD-E,36-port 40GE interface card (FD-E, QSFP+)
                bnameCEL36CQFDE(688454),                 -- Finished Board Unit,CloudEngine 16800,CEL36CQFD-E,36-port 100GE interface card (FD-E, QSFP28)
				bnameCEMPUDFULL2E(688455),               --
				bnameCEMPUDHALF2E(688456),               --
				bnameCEMPUDF2EK(688457),                 --
				bnameCEMPUDH2EK(688458),                 --
				bnameCE687048S6CQEIA(688459),			 --
				bnameCE6881H48T6CQ(688460),			     --
				bnameCE6881H48T6CQK(688461),			 --
				bnameCE6820H48S6CQK(688462),			 --
				bnameCE6881H48S6CQK(688463),			 --
				bnameCE6863H48S6CQK(688464),			 --
				bnameCE6820S48S6CQ(688465),			     --
				bnameCEMPUDHALF3E(688466),               --
				bnameCEMPUDFULL3E(688467),               --
				bnameCESFU16DH1E(688468),                -- 
				bnameCESFU16DL1E(688469),                -- 
				bnameCESFU08DH1E(688470),                -- 
				bnameCESFU08DL1E(688471),                -- 
				bnameCESFU04DH1E(688472),                -- 
				bnameCESFU04DL1E(688473),                -- 
				bnameCESFU04DL1EK(688474),               -- 
				bnameCESFU04DH1EK(688475),               --
				bnameCESFU08DL1EK(688476),               --
				bnameCESFU08DH1EK(688477),               --   
				bnameCE6860HAM(688478),				     --
				bnameCE8850HAM(688479),                   --
				bnameCE686648S8CQP6(688480),
				bnameCEL36CQFDC1G(688481), 
				bnameCEL18CQFDC1G(688482), 
				bnameCEL36LQFDC1G(688483), 
				bnameCEL48XSFDC1G(688484), 
				bnameCE98604CEIA(688485),  -- CE V2R22C10
				bnameCEMPUDCFULL2C(688486),  -- CE V2R22C00
				bnameCEMPUDCHALF2C(688487), -- CE V2R22C00
				bnameCESFU08FH1E(688488),  -- CE V3R22C10
				bnameCEL36DQHGX(688489),  -- CE V3R22C10
				bnameCEMPUDH3ET(688491),  -- CE V3R22C10
				bnameCEMPUDF3ET(688492),  -- CE V3R22C10
				bnameDX511(688493),     	-- DX511	
				bnameDX112(688494),     	-- DX112
				bnameCESFU16FG1(688495),				-- CE V2R22C10
				bnameCE685548XS8CQ(688496),				-- CE V3R23C00
				bnameCE6885LL56F(688497),				-- CE V3R23C00
				bnameCE688548YS8CQ(688498),				-- CE V3R23C00
				bnameCE688548YS8CQT(688499),		    -- CE V3R23C00
				bnameCE6867HAM(688500),					-- CE V3R23C00
				bnameCE6885SAN56F(688501),				-- CE V3R23C00
				bnameCE885532CQ4BQ(688502),				-- CE V3R23C00			
				bnameCEL36CQJ(688503),					-- CE V3R23C00		
				bnameCEL48YSJ(688504),					-- CE V3R23C00
				bnameCEL48YSAJ(688505),					-- CE V3R23C00
				bnameCEXSFU04G(688506),					-- CE V3R23C00
				bnameCEXSFU08G(688507),					-- CE V3R23C00
				bnameCEXSFU16G(688508),					-- CE V3R23C00
				bnameCEL36LQJ(688509),				-- CE V3R23C00
				bnameCEL24CQJ(688510),				-- CE V3R23C00				
				bnameCESFU08GL(688511),			-- CE V3R23C00
				bnameCESFU04GL(688512),			-- CE V3R23C00
				--bnameCESFU04GH(688513),		 CE V3R23C10
				bnameCESFU16GL(688514),			-- CE V3R23C00				
				bnameCEL24XS12CQFDE(688515),		-- CE V3R22C10
				bnameCEXL48YSJ(688516),				-- CE V3R23C00
				bnameCEXL48YSAJ(688517),			-- CE V3R23C00
				bnameCEXL24CQJ(688518),				-- CE V3R23C00
				bnameCEXL36LQJ(688519),				-- CE V3R23C00
				bnameCEXL36CQJ(688520),				-- CE V3R23C00
				bnameCEXMPUDH(688523),				-- CE V3R23C00
				bnameCEXMPUDF(688524),				-- CE V3R23C00
				bnameCEXMPUEH(688525),				-- CE V3R23C00
				bnameCEXMPUEF(688526),				-- CE V3R23C00	
				bnameCE585548T4XS(688527),			-- CE V3R23C00
				bnameCE5855SH48T4XS(688528),		-- CE V3R23C00
				bnameCE5855SL48T4XS(688529),		-- CE V3R23C00
				bnamePAC600S12PF(688530),		-- CE V3R23C00
				bnamePAC1K2S12PF(688531),		-- CE V3R23C00
				bnamePDC1K2S12PB(688532),		-- CE V3R23C00
                bnameCEXSFU04GH(688533),              -- CE V3R23C10
                bnameCEXSFU08GH(688534),              -- CE V3R23C10
                bnameCEXSFU16GH(688535),              -- CE V3R23C10
                --bnameCESFU08GH(688536),              CE V3R23C10
                --bnameCESFU16GH(688537),              CE V3R23C10
                bnameCEX9SFU08GL(688538),              -- CE V3R23C10
                bnameCEX7SFU04GL(688539),              -- CE V3R23C10
                bnameCEX7SFU08GL(688540),              -- CE V3R23C10
                bnameCEX7SFU16GL(688541),              -- CE V3R23C10
                bnameCEX8SFU08GL(688542),              -- CE V3R23C10
                bnameCEX8SFU16GL(688543),              -- CE V3R23C10
                bnameCEXL36DQ2CQJ2(688544),              -- CE V3R23C10
                bnameCEXL48CQJ2(688545),              -- CE V3R23C10
                bnameCEL36DQJ2(688546),              -- CE V3R23C10
                --bnameCEL48CQJ2(688547),            CE V3R23C10
                bnameCEX9L36CQJ(688548),              -- CE V3R23C10
                bnameCEX9L24CQJ(688549),              -- CE V3R23C10
                bnameCEX9L36LQJ(688550),              -- CE V3R23C10
                bnameCEX9L48YSJ(688551),              -- CE V3R23C10
                bnameCEX7L36CQJ(688552),              -- CE V3R23C10
                bnameCEX7L24CQJ(688553),              -- CE V3R23C10
                bnameCEX7L36LQJ(688554),              -- CE V3R23C10
                bnameCEX7L48YSJ(688555),              -- CE V3R23C10
                bnameCEX8L36CQJ(688556),              -- CE V3R23C10
                bnameCEX8L24CQJ(688557),              -- CE V3R23C10
                bnameCEX8L36LQJ(688558),              -- CE V3R23C10
                bnameCEX8L48YSJ(688559),              -- CE V3R23C10
                bnameCEX9MPUEF(688560),              -- CE V3R23C10
                bnameCEX9MPUEH(688561),              -- CE V3R23C10
                bnameCEX7MPUEF(688562),              -- CE V3R23C10
                bnameCEX7MPUEH(688563),              -- CE V3R23C10
                bnameCEX8MPUEF(688564),              -- CE V3R23C10
                bnameCEX8MPUEH(688565),              -- CE V3R23C10
                bnameCE6885H48YS8CQ(688566),              -- CE V3R23C10
                bnameCE887524BQ8DQ(688567),              -- CE V3R23C10
                bnameCE8865SAN4C(688568),              -- CE V3R23C10
                bnameCE88654C(688569),              -- CE V3R23C10
                bnameCE6885T48YS8CQ(688570),              -- CE V3R23C10
                bnameCE6855T48XS8CQ(688571),              -- CE V3R23C10
                bnameCE8855T32CQ4BQ(688572),              -- CE V3R23C10
                bnameCE6885U48YS8CQ(688573),              -- CE V3R23C10
                bnameCE6855U48XS8CQ(688574),              -- CE V3R23C10
                bnameCE8855U32CQ4BQ(688575),              -- CE V3R23C10
                bnameCE6885M48YS8CQ(688576),              -- CE V3R23C10
                bnameCE6855M48XS8CQ(688577),              -- CE V3R23C10
                bnameCE885132CQ4BQ(688578),              -- CE V3R23C00
                bnameCE6863E48S8CQ(688579),              -- CE V3R23C00
                bnameCEXSFU04GL(688580),              -- CE V3R23C00
                bnameCEXSFU08GL(688581),              -- CE V3R23C00
                bnameCEXSFU16GL(688582),              -- CE V3R23C00
               bnameCEXL18EQJ2(688583),               -- CE V3R23C11
               bnameLQG311-L1(688584),
               bnameLQU311-L1(688585),
               bnameLQG311-L2(688586),
               bnameLQC311-L2(688587),
               bnameLQG311-L3(688588),
               bnameLQG311-L4(688589),
               bnameCEX9SFU16GL(688590),
               bnamePAC1K8S12PF(688591),
               bnamePHD2KS12PB(688592),
               bnamePDC2K2S12PB(688593),
               bnamePDC2K2S12PF(688594),
               bnameCEX9L36DQ2CQJ2(688595),
               bnameCEX7L36DQ2CQJ2(688596),
               bnameCEX8L36DQ2CQJ2(688597),
               bnameCEX7SFU04GH(688598),
               bnameCEX7SFU08GH(688599),
               bnameCEX8SFU08GH(688600),
               bnameCEX9SFU08GH(688601),
               bnameCEX7SFU16GH(688602),
               bnameCEX8SFU16GH(688603),
               bnameCEX9SFU16GH(688604),
               bnameXH168008(688605),
               bnameXH1680016(688606),
               bnameXHL36DQ2CQJ2(688607),
               bnameXHSFU08GH(688608),
               bnameXHSFU16GH(688609),
               bnameXHMPUEH(688610),
               bnameXHMPUEF(688611),
               bnameXH811024BQ8DQ(688612),
               bnameXH911024BQ8DQ(688613),
               bnameCE985532DQ(688614),
               bnameXH821032DQ(688615),
               bnameXH921032DQ(688616),
               bnameCE682048S6CQA(688617),
               bnameCE6885L48YS8CQ(688618),
               bnameCE98654C(688621),
               bnameCE9865U4C(688622),
               bnameCE9865M4C(688623),
               bnameCE9865T4C(688624),
               bnameCEL18DQJ(688625),
               bnameXHL40DQJ2(688626),
               bnameCEXL18DQJ(688627),
               bnameCEXL40DQJ2(688628),
				bnameGM510MERGE(688630),
				bnameGM510STORAGE(688631),
				bnameGM110OOB(688632),
				bnameGM110NIC(688633),
				bnameCE9855U32DQ(688634),
				bnameCE9855T32DQ(688635),
				bnameCE9855M32DQ(688636),
               bnameCESFU16GH2(688637),
               bnameCEX7SFU16GH2(688638),
               bnameCEX8SFU16GH2(688639),
               bnameCEX9SFU16GH2(688640),
               bnameXHSFU16GH2(688641),
               bnameCEXL72YS6CQJ2(688642),
               bnameCEX9L18DQJ(688643),
               bnameCEX8L18DQJ(688644),
               bnameCEX7L18DQJ(688645),
               bnameCEX9L48CQJ2(688646),
               bnameCEX7L48CQJ2(688647),
               bnameCEX8L48CQJ2(688648),
               bnameGM111MERGE(688649),
			   bnameCEXSFU16GH2(688650),
			   bnameXH90304C(688651),
			   bnameXH901032CQ4BQ(688652),
			   bnameXHL48CQJ2(688653),
			bnameXH932064EO(688654),
			bnameXH8230128DQLC(688655),
			bnameXH9230128DQLC(688656),
			bnameXH8230128DQ(688657),
			bnameXH9230128DQ(688658),
			bnameCE6820H24S6CQ(688659),
			bnameCE9866128DQLC(688660),
			bnameCE9866128DQ(688661),
			bnameCE987564EO(688662),
			bnameCE9875128EO(688663),
			bnameXH832064EO(688664),
		bnameLQC312L1(688665),
		bnameLQC313L1(688666),
		bnameLingQu630V1(688667),
		bnameXH9330128EO(688668),
		bnameCE6857S48S6CQ(688669),	
        bnameLQC315L1(688670),
		bnameLingQu620V1(688671),
        bnameCE588548T8YS(688672),
        bnameCE685548T8CQ(688673),
        bnameCE8855H32CQ8DQ(688674),
        bnameCE986664DQ(688675),
        bnameXH922064DQ(688676),
        bnameXH822064DQ(688677),
        bnameXH8330128EO(688678),
        bnameXH1680016LC(688679),
        bnameXHSFU16HHLC(688680),
        bnameXHL40DQJ2LC(688681),
        bnamePAC2KS12PB(688682),
        bnameCEX7SFU04GM(688683),
        bnameCEX7SFU08GM(688684),
        bnameCEX7SFU16GM(688685),
        bnameCEX8SFU08GM(688686),
        bnameCEX8SFU16GM(688687),
        bnameCEX9SFU08GM(688688),
        bnameCEX9SFU16GM(688689),
        bnameXHMPUG(688690),
        bnameCEXMPUG(688691),
        bnameCEMPUG(688692),
        bnameCE6855ULLM(688693),
        bnameCE6855ULL(688694),
        bnameCE986740DQ(688695),
        bnameXH922040DQ(688696),
        bnameXH822040DQ(688697),
        bnameCE986724DQ8EO(688698),
        bnameLQU520-SW1(688699),
        bnameLQU520-SW2(688701),
        bnameLQU520-2C(688702),
        bnameLQU520-8N(688703),
        bnameLQU520-1RN(688704),
        bnameLQU520-2RN(688705),
        bnameLQU520-DB(688706),
        bnameLQU520-QT(688707),
        bnameLingQu650V2(688708), 
        bnameLingQu651V2(688709),
        bnameLQ620V1(688710),
	    bnameCE885548CD8DQ(688711),
        bnameSMN(688712),
        bnameLQU521(688713),
        bnameLQU522(688714),
        bnameLQU523(688715),
        bnameCE9866U128DQ(688716),
        bnameCE9866M128DQ(688717),
        bnameCE9866T128DQ(688718),
        bnameCE8855HSAN40F(688719),
        bnameLingQu652V2(688724),    
        bnameXH991032DQ(688725),    
        bnameXH9930128DQ(688726),
        bnameLingQu550LBox(688727),
        bnameLingQu550BoxA(688728),
        bnameLingQu550BoxB(688729),

-- wlan:        0x000A9000~0x000A9fff(692224~696319)
                bnameH80D2ACMPS00(692224),              --Switching and Routing Unit Board
                bnameAC6605-26-PWR(692225),             --24port 10/100/1000Base-T 4 1000Base-X
                bnameAC6005-8(692226),
                bnameACU2(692227),
                bnameAP6010SN(692228),
                bnameAP6010DN(692229),
                bnameAP6510DN(692231),
                bnameAP6610DN(692232),
                bnameAP5010DN(692233),
                bnameAP5010SN(692234),
                bnameAP7110DN(692235),
                bnameAP3010DN(692237),
                bnameAP5030DN(692238),
                bnameAP5130DN(692239),
                bnameAC6005-8-PWR(692240),
                bnameAT815SN(692243),
                bnameAP8030DN(692245),
                bnameAP8130DN(692246),
                bnameAP9130DN(692247),
                bnameAP3030DN(692249),
                bnameAP4030DN(692250),
                bnameAP4130DN(692251),
                bnameAP9131DN(692253),
                bnameAP5030DN-S(692254),
                bnameAP9132DN(692255),
                bnameAP3010DN-V2(692259),
                bnameAC6005-8-RU(692260),
                bnameAC6005-8-PWR-RU(692261),
                bnameAC6605-26-PWR-RU(692262),
                bnameACU2-RU(692263),
                bnameAC6003-8(692264),
                bnameAC6003-8-PWR(692265),
                bnameAP4030DN-E(692269),
                bnameAP7050DN-E(692274),
                bnameAD9430DN-24(692266),
                bnameAD9430DN-12(692271),
                bnameAP6150DN(692277),
                bnameAP6050DN(692273),
                bnameAP4030TN(692276),
                bnameAP4050DN-E(692275),
                bnameAP4050DN-HD(692278),
                bnameAP7050DE(692272),
                bnameAP1010SN(692280),
                bnameAP2050DN(692281),
                bnameAP2050DN-S(692282),
                bnameAP2050DN-E(692283),
                bnameAP4050DE(692284),
                bnameAP5030DN-C(692289),
                bnameAP4051DN(692290),
                bnameAP4050DN(692291),
                bnameAP4151DN(692292),
                bnameAP4051DN-S(692293),
                bnameAP4050DN-S(692294),
                bnameAP8050DN(692295),
                bnameAP8050DN-S(692296),
                bnameAP8150DN(692297),
                bnameAP1050DN-S(692298),
                bnameAD9431DN-24X(692299),
                bnameAP7152DN(692300),
                bnameAP6052DN(692301),
                bnameAP8082DN(692302),
                bnameAP8182DN(692303),
                bnameAP7052DE(692304),
                bnameAP7052TN-WI(692305),
                bnameAP8050TN-HD(692306),
                bnameAP4051TN(692307),
                bnameAP7052DN(692308),
                bnameAP5050DN-S(692309),
                bnameAP2030DN-S(692310),
                bnameAP2051DN-E(692311),
                bnameAP2051DN(692312),
                bnameAP2051DN-S(692313),
                bnameAP7060DN(692314),
                bnameAC6800V(692315),
                bnameAP100EC(692316),
                bnameAP200EC(692317),
                bnameAP300EC(692318),
                bnameAC600EC(692319),
                bnameAC600EC-PWR(692320),
                bnameAC6508(692321),
                bnameAC6805(692322),
                bnameAC6507S(692323),
                bnameAP4050DE-M(692324),
                bnameAP4050DE-M-S(692325),
                bnameWA375DD-CE(692326),
                bnameAP2051DN-L-S(692327),
                bnameAP2051DE-GP(692328),
                bnameAP4050DE-B-S(692329),
                bnameAP3050DE(692330),
                bnameWAC9600S-S(692331),
                bnameAP6750-10T(692332),
                bnameAP5760S-10(692333),
                bnameAC6508-B(692334),
                bnameAC6507S-B(692335),
                bnameAP5760-10(692336),
                bnameAirEngine9700-M(692337),
                bnameAirEngine9700D-M(692338),
                bnameAC650-32AP(692339),
                bnameAC650-64AP(692340),
                bnameAP210(692341),
                bnameAP230(692342),
                bnameAP310(692343),
                bnameAP330(692344),
                bnameAP350(692345),
                bnameAirEngine9700-M1(692346),
                bnameAirEngine6760-51EI(692355),
                bnameAirEngine6761-21T(692356), 
                bnameAirEngine6761S-21T(692357),
                bnameAirEngine5761-21(692358),  
                bnameAirEngine6761-21E(692359), 
                bnameAirEngine5761S-21(692360), 
                bnameAirEngine5761-11(692361),  
                bnameAirEngine5761S-11(692362), 
                bnameAirEngine5761-12W(692363), 
                bnameAirEngine5761S-12W(692364),
                bnameAirEngine5761-11W(692365), 
                bnameAirEngine5761S-11W(692366),
                bnameAirEngine5761-11WD(692367),
                bnameAirEngine6761-21(692368),
                bnameAirEngine5761R-11(692369),
                bnameAirEngine5761RS-11(692370),
                bnameAirEngine5761R-11E(692371),
                bnameAirEngine6761S-21(692372),
                bnameAirEngine5761S-12(692373),
                bnameAirEngine5761S-13(692374),
                bnameAirEngine5761-10W(692375),
                bnameAirEngine5761-10WD(692376),
                bnameAirEngine5761S-10W(692377),
                bnameAP5761S-10(692378),
                bnameAP5761S-10W(692379),
                bnameAirEngine5762-12SW(692380),
                bnameAirEngine5762S-12SW(692381),
                bnameAirEngine5762-12(692383),
                bnameAirEngine5762S-12(692384),
                bnameAirEngine5762S-11(692385),
                bnameAirEngine5762-15HW(692386),
                bnameAirEngine5762-13W(692387),
                bnameAirEngine5762S-13W(692388),
                bnameAirEngine5762S-11SW(692389),
                bnameAP163(692390),
                bnameAP165(692391),
                bnameAP263(692392),
                bnameAP363(692393),
                bnameAP365(692394),
                bnameAP9700D-M1(692395),
                bnameAirEngine6761-22T(692396),
                bnameAirEngine5761-12(692397),
                bnameAirEngine9701-L(692398),
                bnameAirEngine5761-11EI(692399),
                bnameAirEngine5762-16W(692400),
                bnameAirEngine9700-H(692401),
                bnameAP161(692402),
                bnameAP162(692403),
                bnameAP362(692404),
                bnameAirEngine9700D-S(692405),
                bnameAirEngine8761-X1(692406),
                bnameAirEngine5762-17W(692407),
                bnameAirEngine5762-10(692408),
                bnameAirEngine5762-10SW(692409),
                bnameAirEngine6761-23T(692410),
		        bnameAirEngine8771-X1T(692411),
                bnameAirEngine5562-17W(692412),				
                bnameAirEngine5562-10(692413),               
                bnameAirEngine5562-10SW(692414),
                bnameAC650-128AP(692415),
                bnameAC650-256AP(692416),
                bnameAirEngine3562-10(692417),
                bnameAirEngine3562-10SW(692418),
                bnameAirEngine9701-L-T(692419),
		        bnameAirEngine9703-H(692420),	
                bnameAirEngine9703-S(692421),
                bnameAirEngine9703-H-T(692422), 	
                bnameAirEngine9703-S-T(692423),
                bnameAirEngine9500-LP(692424),
                bnameAirEngine5773-23HW(692425),
                bnameAirEngine5773-21(692426),
                bnameAirEngine6776-56TP(692427),
                bnameAirEngine6776-57T(692428),
		        bnameAP661(692429),
                bnameAP761(692430),
		        bnameMAP3000C-CIh(692431),
                bnameMAP3000P-CIh(692432),
                bnameMAP3000P-CIs(692433),
                bnameMAP6000P-CIh(692434),
                bnameMAP6000P-CIa(692435),
		        bnameAirEngine5776-26(692436), 
		        bnameAirEngine5773-23H(692437),
                bnameAirEngine5773-22P(692438),
		        bnameAP160(692439),
		        bnameAP361(692440),
		        bnameAirEngine5561-12(692441),
		        bnameAirEngine5561R-11E(692442),
                bnameAirEngine5562-15HW(692443),
                bnameAirEngine6561-21T(692444),
		        bnameAirEngine9501-L(692445),
		        bnameAirEngine9500-L1P(692446),
                bnameAirEngine6776I-X6TH(692447),
                bnameAirEngine5773-25HW(692448),
                bnameAirEngine5773-23WP(692449),
                bnameAirEngine5576-26(692450),
                bnameAirEngine6576-57T(692451),
                bnameAirEngine6776-58Ti(692452),
                bnameAirEngine5573-21(692453),
                bnameAirEngine3573-21(692454),
                bnameAirEngine6576-56TP(692455),
                bnameAP362E(692456),
                bnameAP265E(692458),
                bnameAP266(692459),
                bnameAP162E(692460),
                bnameAirEngine5763-11W(692461),
                bnameAirEngine9503-S(692462),
                bnameAC650-512AP(692463),
		        bnameAirEngine5573-23H(692464),
                bnameAirEngine5573-23HW(692465),
		        bnameAirEngine9701S-L(692466),
		        bnameAP673(692467),
		        bnameAirEngine6776I-X7TH(692468),
		        bnameAP371(692469),
			    bnameAirEngine5762C-10-V2(692470),
                bnameAirEngine5562-10-V2(692471),
                bnameAirEngine3562-10-M(692472),
                bnameAirEngine3562-10-T(692473),
                bnameAirEngine5762C-10SW-V2(692474),
                bnameAirEngine5562-10SW-V2(692475),
                bnameAirEngine3562-10SW-M(692476),
                bnameAirEngine3562-10SW-T(692477),
                bnameeKitEngine5763S-11(692478),
                bnameeKitEngine5763S-12(692479),
                bnameAP361E(692480),
                bnameeKitEngine5763S-12SW(692481),
                bnameeKitEngine6760S-56(692482),
			    bnameAirEngine5773-23W(692483),
                bnameAirEngine6776I-X6ETH(692484),
                bnameAirEngine5573-23W(692485),
                bnameAirEngine5576I-X6EH(692486),
                bnameeKitEngine5773S-21(692487),
                bnameeKitEngine5776RS-X6(692488),
                bnameAP673E(692489),
                bnameAP572(692490),
                bnameAP772(692491),
                bnameAP772E(692492),
                bnameAirEngine6776-X6H(692493),
                bnameAirEngine6776-X6ETH(692494),
                bnameAirEngine5776-56T(692495),
                bnameAirEngine5776I-X6H(692496),
                bnameAirEngine5776I-X6EH(692497),
                bnameAirEngine6776-58TI-K(692498),
                bnameAirEngine6776I-X6ETH-K(692499),
		        bnameAirEngine5762C-17W-V2(692500),
		        bnameAirEngine5562-17W-V2(692501),
                bnameAirEngine5776I-X7H(692502),
                bnameAP761E(692503),            
                bnameAirEngine5776-57T(692504), 
                bnameAirEngine5776-57(692505), 
		        bnameAP271E(692506),
                bnameAirEngine5773H-21(692507),
                bnameAirEngine8776-X7ET-T(692508),
                bnameAirEngine8776-X7F-T(692509),
                bnameAirEngine8776-X7T-T(692510),
                bnameAirEngine8776-X6THP(692511),
                bnameAirEngine5776E-26(692512),  
                bnameAirEngine5773E-21(692513),
                bnameAirEngine6776-26HD(692514),
                bnameAirEngine6776-26HD-X773(692515),
                bnameAirEngine5773-21HW(692516),
                bnameAP771(692517),
                bnameAirEngine5773E-23W(692518),  
                bnameAirEngine5773E-25HW(692519), 
                bnameAirEngine5773E-23HW(692520), 
                bnameAirEngine5776I-X7TH(692521), 
                bnameAirEngine7070-01-M(692524),  
                bnameAirEngine7070I-01-M(692525), 
                bnameAirEngine7070I-01-MS(692526),
                bnameAirEngine5773I-21(692527),   
                bnameAirEngine3573I-21-M(692528), 
                bnameAirEngine3576-56TP-M(692529),
                bnameAirEngine5776I-X7EH(692532),  
                bnameAirEngine8776I-X6ETHP-T(692534),
                bnameAirEngine8776-X5F-T(692536),
                bnameAirEngine6776-X7TH(692540),     
                bnameAP673H(692545),
                bnameAP361H(692547),
                bnameAP362H(692548),				
-- T8010:       0x000AA200~0x000AA7FF(696832~698367)
                bnameBT81CPOHT8010(696832),         --main control board of T8010 bits, with one slot.
                bnameBT81CPRHT8010(696833),         --main control board of T8010 bits, with two slots.
                bnameBT81HDOU(696834),              --32-port business board of T8010 bits.
                bnameBT82CPOHT8010(696835),         --main control board of T8010 bits, with one slot.
                bnameBT82CPRHT8010(696836),         --main control board of T8010 bits, with two slots.
                bnameBT82HDOU(696837),              --32-port business board of T8010 bits.
                bnameDPE1LAXF(696838),              --10 GE port board of T8010 bits.
                bnameBT82TODU(696839),              --8 clock port board of T8010 bits.

--service board for iODN products: range: 0x000B0000~0x000BFFFF  720,896~786,431
                bnameAF11TMSA(745473),              -- AF11TMSA
                bnameAF11TMUA(745474),              -- AF11TMUA
                bnameAF11TMLA(745475),              -- AF11TMLA
                bnameAF11TMPA(745476),              -- AF11TMPA
                bnameAF11STSA(745477),              -- AF11STSA
                bnameAF11STUA(745478),              -- AF11STUA
                bnameAF11STLA(745479),              -- AF11STLA
                bnameAF11STPA(745480),              -- AF11STPA
                bnameAF11SPSIA(745481),             -- AF11SPSIA
                bnameAF11SPUIA(745482),             -- AF11SPUIA
                bnameAF11SPLIA(745483),             -- AF11SPLIA
                bnameAF11SPPIA(745484),             -- AF11SPPIA
                bnameAF11SPSHA(745485),             -- AF11SPSHA
                bnameAF11SPUHA(745486),             -- AF11SPUHA
                bnameAF11SPLHA(745487),             -- AF11SPLHA
                bnameAF11SPPHA(745488),             -- AF11SPPHA
                bnameAF11SPSOA(745489),             -- AF11SPSOA
                bnameAF11SPUOA(745490),             -- AF11SPUOA
                bnameAF11SPLOA(745491),             -- AF11SPLOA
                bnameAF11SPPOA(745492),             -- AF11SPPOA
                bnameAF11SPSPA(745493),             -- AF11SPSPA
                bnameAF11SPUPA(745494),             -- AF11SPUPA
                bnameAF11SPLPA(745495),             -- AF11SPLPA
                bnameAF11SPPPA(745496),             -- AF11SPPPA
                bnameAF11SPSJA(745497),             -- AF11SPSJA
                bnameAF11SPUJA(745498),             -- AF11SPUJA
                bnameAF11SPLJA(745499),             -- AF11SPLJA
                bnameAF11SPPJA(745500),             -- AF11SPPJA
                bnameAF11SPSQA(745501),             -- AF11SPSQA
                bnameAF11SPUQA(745502),             -- AF11SPUQA
                bnameAF11SPLQA(745503),             -- AF11SPLQA
                bnameAF11SPPQA(745504),             -- AF11SPPQA
                bnameAF11SPSKA(745729),             -- AF11SPSKA
                bnameAF11SPUKA(745730),             -- AF11SPUKA
                bnameAF11SPLKA(745731),             -- AF11SPLKA
                bnameAF11SPPKA(745732),             -- AF11SPPKA
                bnameAF11SPSRA(745733),             -- AF11SPSRA
                bnameAF11SPURA(745734),             -- AF11SPURA
                bnameAF11SPLRA(745735),             -- AF11SPLRA
                bnameAF11SPPRA(745736),             -- AF11SPPRA
                bnameAF11SPSLA(745737),             -- AF11SPSLA
                bnameAF11SPULA(745738),             -- AF11SPULA
                bnameAF11SPLLA(745739),             -- AF11SPLLA
                bnameAF11SPPLA(745740),             -- AF11SPPLA
                bnameAF11SPSSA(745741),             -- AF11SPSSA
                bnameAF11SPUSA(745742),             -- AF11SPUSA
                bnameAF11SPLSA(745743),             -- AF11SPLSA
                bnameAF11SPPSA(745744),             -- AF11SPPSA
                bnameAF11SPSMA(745745),             -- AF11SPSMA
                bnameAF11SPUMA(745746),             -- AF11SPUMA
                bnameAF11SPLMA(745747),             -- AF11SPLMA
                bnameAF11SPPMA(745748),             -- AF11SPPMA
                bnameAF11SPSTA(745749),             -- AF11SPSTA
                bnameAF11SPUTA(745750),             -- AF11SPUTA
                bnameAF11SPLTA(745751),             -- AF11SPLTA
                bnameAF11SPPTA(745752),             -- AF11SPPTA
                bnameAF11STUB(745985),              -- AF11STUB
                bnameAF11STSB(745986),              -- AF11STSB
                bnameAF11STLB(745987),              -- AF11STLB
                bnameAF11STPB(745988),              -- AF11STPB
                bnameAF11STUC(745989),              -- AF11STUC
                bnameAF11STSC(745990),              -- AF11STSC
                bnameAF11STLC(745991),              -- AF11STLC
                bnameAF11STPC(745992),              -- AF11STPC
                bnameAF11TMUB(745993),              -- AF11TMUB
                bnameAF11TMSB(745994),              -- AF11TMSB
                bnameAF11TMLB(745995),              -- AF11TMLB
                bnameAF11TMPB(745996),              -- AF11TMPB
                bnameAF11TMUC(745997),              -- AF11TMUC
                bnameAF11TMSC(745998),              -- AF11TMSC
                bnameAF11TMLC(745999),              -- AF11TMLC
                bnameAF11TMPC(746000),              -- AF11TMPC
                bnameEDFAHFA1(746001),              --EDFAHFA1
                bnameEDFAFAN1(746002),              --EDFAFAN1
                bnameEDFAPWR1(746003),              --EDFAPWR1
                bnameEDFAEMU1(746004),              --EDFAEMU1
--hwRPS
                bnameCMU01(786632),              --Monitoring module board,with 0 port.
                bnameCFS01Monitor(786633),              --Fan module board,with 3 fan ports
                bnameCPF318-EN11PDBE(786634),    --Power input module board,with 0 port
                bnameCCM08(786635),              --Up converter module board,with 8 DC output ports
                bnameRC12S(786636),              --Down converter module board,with 12 DC input ports
                bnameCPF104Power(786637),        --BT-C Power input module board,with 0 port
                bnameCCM08B(786638),             --BT-C Up converter module board,with 8 DC output ports
                bnameRPR008S-B(786639),          --BT-C Down converter module board,with 12 DC input ports
                bnameCFS02Power(786640),         --BT-C Power input module board,with 0 port
                bnameCFS02Monitor(786641),       --BT-C Fan module board,with 3 fan ports
                bnameETP4830A1-Power(786642),    --BT-C AC-DC System monitor input module board,with 0 port
                bnameETP4890A2-Power(786643),    --BT-C AC-DC System monitor input module board,with 0 port
                bnameETP48150A3-Power(786644),   --BT-C AC-DC System monitor input module board,with 0 port
                bnameSMU01B(786645),             --AC-DC System monitor Monitoring module board
                bnameSMU01C(786657),             --AC-DC System monitor Monitoring module board
                bnameR4830G1(786646),            --AC-DC System Power Supply Unit
                bnameR4830N2(786647),            --AC-DC System Power Supply Unit
                bnameR4815G1(786648),            --AC-DC System Power Supply Unit
                bnameR4815N1(786649),            --AC-DC System Power Supply Unit
                bnameCFS01Power(786650),         --RTF-C Power input module board,with 0 port
                bnameCVM02(786651),              --RTF-V Up converter module board,with 8 DC output ports
                bnameRPF106Power(786653),        --RTF-V Power input module board,with 0 port
                bnameRMU01(786654),              --RTF-V Monitoring module board,with 0 port
                bnameRFS01(786655),              --RTF-V Fan module board,with 3 fan ports
                bnameRVM04(786656),              --RTF-V Down converter module board,with 12 DC input ports


--Security Product's TC-MIB value scope :       16711680 ~ 16777215  or Hex format:0x00ff0000 ~ 0x00ffffff  (Both 16711680 and 16777215 are included)

--USG2000/USG2100/Eudemon200E
                bnameFWF1MPUA(16719872),          -- FWF1MPUA,Main Process Unit Board,1*1  USG2100
                bnameFWF1MPUB(16719873),          -- FWF1MPUB,Main Process Unit Board,1*1  USG2100
                bnameFWF1ADPA(16719874),          -- FWF1ADPA,ADSL2+ MIC,3*1)  USG2100/USG2200
                bnameFWF1F1E1(16719875),          -- FWF1F1E1,1-PORT E1 Interface Board,3*1  USG2100/USG2200
                bnameFWF1F1CE1(16719876),         -- FWF1F1CE1,1-PORT CE1 Interface Board(DB15),3*1)  USG2100
                bnameFWF1E1FE(16719877),          -- FWF1E1FE,1-Port Fast Ethernet Electrical Interface Board(RJ45),3*1  USG2100/USG2200
                bnameFWF1E5FEA(16719878),         -- FWF1E5FEA,5-Port Fast Ethernet Switch Electrical Interface Board(RJ45),3*1)  USG2100/USG2200
                bnameFWG1MPUA(16719879),          -- FWG1MPUA,Main Process Unit Board,1*1  USG2200
                bnameFWG1E1GE(16719880),          -- FWG1E1GE,1-port GE Electrical Interface Card(RJ45),1*1  USG2200
                bnameFWG1C2E1(16719881),          -- FWG1C2E1,2-port Channelized E1 Interface Card,1*1  USG2200
                bnameFWG1F1SA(16719882),      -- USG2200,FWG1F1SA ,1-Channel Sync/Async Serial Port  Interface Card,3*1
                bnameFWG1WIFI(16719883),      -- USG2200,FWG1WIFI,WiFi MIC Card
                bnameFWG1F2E1(16719884),      -- USG2200,FWG1F2E1,2-port E1&Fractional E1 Interface Card,1*1
                bnameFWG1E180(16719885),          -- USG2200,Wireless Data Card,E180,HSUPA/HSDPA/UMTS/EDGE/GPRS/GSM USB STICK,White,HUAWEI Standard
                bnameFWG1ET128(16719886),         --USG2200,Wireless Data Card,ET128,HSDPA/TD-SCDMA/EDGE/GPRS/GSM USB STICK,HUAWEI Standard Version
                bnameFWG1EC169(16719887),         --USG2200,Wireless Data Card,EC169,CDMA2000 EV-DO Rev.A Rotatable USB Stick,White,Chinese Universal,RoHS
                bnameFWF2MPUA(16719888),          --USG2100,FWF2MPUA,USG2100 Main Process Unit,1*1
                bnameFWF2MPUB(16719889),          --USG2100,FWF2MPUB,USG2100 Main Process Unit,1*1
                bnameFWF2MPUC(16719890),          --USG2100,FWF2MPUC,USG2100 Main Process Unit,1*1
                bnameFWF2DB1M(16719891),          --USG2100,FWF2DB1M,USG2100 MIC Daughter Board,2*2
                bnameSU11FSHL(16719892),          --SRG20,SU11FSHL,4 Channel G.shdsl Interface Board,3*1
                bnameSU11FSHLB(16719893),         --SRG20,SU11FSHLB,2 Channel G.shdsl Interface Board,3*1
                bnameSU11FSHLC(16719894),         --SRG20,SU11FSHLC,1 Channel G.shdsl Interface Board,3*1
                bnameSU11F2SA(16719895),          --USG2200,SU11F2SA ,2-Channel Sync/Async Serial Port  Interface Card,3*1
                bnameSU113GWC(16719896),          --SRG20,SU113GWC,3G-WCDMA Service Board,3*1
                bnameSU113GCD(16719897),          --SRG20,SU113GCD,3G-CDMA2000 Service Board,3*1
                bnameSU113GTD(16719898),          --SRG20,SU113GTD,3G-TD-SCDMA Service Board,3*1
                bnameSU11E5FE(16719899),          --SRG20,SU11E5FE,5-Port Fast Ethernet Switch Electrical Interface Board(RJ45),3*1
                bnameFWF1SPUA(16719900),          --FWF1SPUA,Main Process Unit Board,1*1  USG2100
                bnameFWF1SPUB(16719901),          --FWF1SPUB,Main Process Unit Board,1*1  USG2100
                bnameFWF1MPUD(16719902),          --FWF1MPUD,Main Process Unit Board,1*1  USG2100
                bnameFWF1MPUC(16719903),          --FWF1MPUC,Main Process Unit Board,1*1  USG2100
                bnameSU11ADPAO2(16719904),          --SU11ADPA,Main Process Unit Board,1*1  USG2100  duplicated with bnameSU11ADPA(16719932), add 'O2'
                bnameSU11F8E1(16719905),          --SRG20,SU11F8E1,8-port E1 Interface Card-DB44-75ohm,1*1
                bnameSU11FC8E1(16719906),         --SRG20,SU11FC8E1,8-port Channelized E1 Interface Card-DB44-75ohm,1*1
                bnameSU11F4E1(16719907),          --SRG20,SU11F4E1,4-port E1 Interface Card-DB44-75ohm,1*1
                bnameSU11FC4E1(16719908),         --SRG20,SU11FC4E1,4-port Channelized E1 Interface Card-DB44-75ohm,1*1
                bnameSU11APWN(16719909),          --SRG20,SU11APWN,WLAN Service Board,3*1
                bnameSU21MPUA(16719910),          --USG5100,SU21MPUA,Main Process Unit Board,1*1
                bnameSU11MPUA(16719911),          --USG5100,SU11MPUA,Main Process Unit Board,1*1
                bnameFWE1E4GE(16719912),          --USG5100,FWE1E4GE,4-port Gigabit Ethernet Interface Card(RJ45),1*1
                bnameFWG1F2F2C(16719913),         --USG2200,FWG1F2F2C,2FE(RJ45)+2FE(RJ45&SFP) MIXED INTERFACE CARD,1*1
                bnameSU21F18S2(16719914),         --USG5100,SU21F18S2,18FE(RJ45)+2GE(SFP) Mixed Interface Card ,1*1
                bnameSU21G16S4(16719915),         --USG5100,SU21G16S4,16GE(RJ45)+4GE(SFP) Mixed Interface Card  ,1*1
                bnameSU11E8F2G(16719916),         --SRG20,SU11E8F2G,8FE(RJ45)+2GE(RJ45) Mixed Interface Card,3*1
                bnameSRGM1WCDMA(16719917),        --SRG,SRGM1WCDMA,USB 3G WCDMA Card
                bnameSRGM1CD2K(16719918),         --SRG,SRGM1CD2K,USB 3G CDMA2000
                bnameSRGM1TD(16719919),           --SRG,SRGM1TD,USB 3G TDSCDMA
                bnameSU11X86HS02(16719920),       --Safety Product,USG2200,SU11X86HS02,Enhanced Services Platform Enterprise Version,
                                                  -- X86 Board,CPU T7500,2GB Memory,160G Enterprise Hard Disk
                bnameSU11X86HS01(16719921),       --Safety Product,USG2200,SU11X86HS01,Enhanced Services Platform Common Version,
                                                  -- X86 Board,CPU T7500,2GB Memory,160G Universal Hard Disk
                bnameSU01MPUA(16719922),          -- SRG20,SU01MPUA,SRG20  Main Processing Unit ,2*1
                bnameSU01MPUB(16719923),          -- SRG20,SU01MPUB,SRG20  Main Processing Unit ,2*1
                bnameSU01MPUC(16719924),          -- SRG20,SU01MPUC,SRG20  Main Processing Unit ,2*1
                bnameSU01ADPA(16719925),          -- SRG20,SU01ADPA,ADSL2+Multi-PVCs,2*2
                bnameSU11SMX01(16719926),         -- Safety Product,SRG20,SU11SMX01,Enhanced Services Platform,ultra-low-end ,with CF Card, no Hard Disk
                bnameSU11DMX02(16719927),         -- Safety Product,SRG20,SU11DMX02,Enhanced Services Platform,low-end , 2.5'' Hard Disk
                bnameSU11DFX03(16719928),         -- Safety Product,SRG20,SU11DFX03, Enhanced Services Platform,mid-range , 2.5'' Hard Disk
                bnameSU11DFX04(16719929),         -- Safety Product,SRG20,SU11DFX04, Enhanced Services Platform,mid-range , two 2.5'' Hard Disk
                bnameSU11DFX05(16719930),         -- Safety Product,SRG20,SU11DFX05, Enhanced Services Platform,high-end ,with CF Card, two 2.5'' Hard Disk
                bnameFWG2MPUA(16719931),          -- USG2200,FWG2MPUA,Main Process Unit Board,1*1
                bnameSU11ADPA(16719932),          -- SRG20,SU11ADPA,ADSL2+Multi-PVCs,with HS General Security Platform Software,1*1
                bnameFWF1E1FEO(16719933),          -- USG2100,FWF1E1FE,1-Port Fast Ethernet Electrical Interface Board(RJ45),3*1  duplicated with bnameFWF1E1FE(16719877) add 'O'
                bnameSU11EPSEC(16719934),         -- USG5100,SU11EPSEC,High Speed IPsec Card,with HS General Security Platform Software
                bnameSU51E4BYO(16719935),          -- USG5100,SU51E4BY,4GE Electric Ports Bypass Card,with HS General Security Platform Software,1*1  duplicated with bnameSU51E4BY(16719960) add 'O'
--USG3000/USG50/USG5000/SVN
                bnameRTB21CT1(16719950),          --USG3000,RTB21CT1,1-port T1&Fractional T1 Interface Card,1*1
                bnameRRTB21CE1(16719951),         --USG3000,RTB21CE1,1-port CE1&Fractional CE1 Interface Card,1*1
                bnameRTB21T1(16719952),           --USG3000,RTB21T1,1-port T1&Fractional T1 Interface Card,1*1
                bnameRTB21E1(16719953),           --USG3000,RTB21E1,1-port E1&Fractional E1 Interface Card,1*1
                bnameSE21MPUA(16719954),           --SVN5300,Security virtual Gateway Mainboard(4GE)
                bnameWCDMA(16719955),             --SVN5300,Security 3G board(WCDMA)
                bnameTD-SCDMA(16719956),          --SVN5300,Security 3G board(TD-SCDMA)
                bnameCDMA2000(16719957),          --SVN5300,Security 3G board(CDMA2000)
                bnameSU51MPUB(16719958),          --USG5500,SU51MPUB,1U Main Processing Unit,1*1
                bnameSU51SACCO(16719959),          --USG5500,SU51SACC,Service Accelerate Card,1*1  duplicated with bnameSU51SACC(16719967) add 'O'
                bnameSU51E4BY(16719960),          --USG5500,SU51E4BY,4GE Electric Ports Bypass Card,with HS General Security Platform Software,1*1
                bnameSU51MPUA(16719961),          --USG5500,SU51MPUA,Main Processing Unit,1*1
                bnameSU51X2G8(16719962),          --USG5500,SU51X2G8,2*10GE Optical Ports+8GE Electric Ports Interface Card,with HS General Security Platform Software,1*1
                bnameSU51E2XSM(16719963),         --USG5500,SU51E2XSM,2*10GE Optical Ports Interface Card,with HS General Security Platform Software,3*1
                bnameSU51E8GF(16719964),          --USG5500,SU51E8GF,8GE Optical Ports Interface Card,with HS General Security Platform Software,2*1
                bnameSU51E8GE(16719965),          --USG5500,SU51E8GE,8GE Electric Ports Interface Card,with HS General Security Platform Software,1*1
                bnameSU51E2XSF(16719966),         --USG5500,SU51E2XSF,2*10GE Optical Ports Interface Card,with HS General Security Platform Software,1*1
                bnameSU51SACC(16719967),          --USG5500,SU51SACC,Service Accelerate Card,1*1
                bnameSU51F2BY(16719968),          --USG5500,2 Link LC/UPC Optical Interface Bypass Protect Card
                bnameSU51E8GFF(16719969),         --USG5500,8GE Optical Ports FIC Interface Card
                bnameSU71DFX01(16719970),         --Safety Product,NIP5100,SU71DFX01,Enhanced Services Platform,High-end,for IPS
                bnameSU51ESPA(16719971),          --NIP5100,ESP,SU51ESPA,X86 Process Card,1*1
                bnameSU51ESPC(16719972),          --NIP5100,ESP,SU51ESPC,IPS Process Card,1*1
                bnameSU51F2BY01(16719973),        --USG5500,SU51F2BY01,2 Link LC/UPC Multimode Optical Interface Bypass Protect Card,with HS General Security Platform Software
                bnameSU51F2BY02(16719974),        --USG5500,SU51F2BY02,2 Link LC/UPC Singlemode Optical Interface Bypass Protect Card,with HS General Security Platform Software
                bnameSUA1CPUA(16719975),          --Eudemon1000E-N CPU Card
                bnameSUA2MPUA(16719976),          --USG6600 Main Processing Unit
                bnameSUA2CSPUA(16719977),         --USG6600 Content Security Process Unit
                bnameSUA2X2G8(16719978),          --USG6600 2*10GE Optical Ports+8GE Electric Ports Interface Card
                bnameSUA2E2XSF(16719979),         --USG6600 2*10GE Optical Ports Interface Card
                bnameSUE3E8GF(16719980),          --USG6600 8GE Optical Ports Interface Card
                bnameSUE3E4BY(16719981),          --USG6600 4GE Electric Ports Bypass Card
                bnameSUE3E8GE(16719982),          --USG6600 8GE Electric Ports Interface Card
                bnameSUE5MPUA(16719983),          -- USG3600 Main Processing Unit
                bnameSUE5DSBB(16719984),          -- USG3600 HD Switch Board
                bnameSUA1MPUB(16719985),          -- USG3600 1U Main Processing Unit Board
                bnameSUE1EPSEC(16719986),         -- USG3600 The state password encryption Daughter card
                bnameSUE5FIBA(16719987),      --Fixed Interface Board
                bnameET1D2IPS0S00(16719988),      -- IPS Module A,with HW General Security Platform Software
                bnameET1D2FW00S00(16719989),      -- NGFW Module A,with HW General Security Platform Software
                bnameET1D2FW00S01(16719990),      -- NGFW Module B,with HW General Security Platform Software
                bnameET1D2FW00S02(16719991),      -- NGFW Module C,with HW General Security Platform Software
                bnameLE1D2FW00S01(16719992),      -- NGFW Module B,with HW General Security Platform Software
                bnameSUE6MPUA(16719993),      -- Manufactured Board,USG6600,SUE6MPUA,Main Processing Unit Board
                bnameSUE3MPUA(16719994),      -- Manufactured Board,USG6300,SUE3MPUA,Main Processing Unit Board
                bnameSUE3BPKA(16719995),      -- USG6300,SUE3BKPA,1U BackPlane Board
                bnameSUF1MPUA-8GE-WL(16744453),  -- USG6300 1U Main Processing Unit Board.
                bnameSUF1MPUA-8GE-W(16744452),  -- USG6300 1U Main Processing Unit Board.
                bnameSUF1MPUA-8GE(16744451),  -- USG6300 1U Main Processing Unit Board.
                bnameSUF1MPUA-4GE-W(16744450),  -- USG6300 1U Main Processing Unit Board.
                bnameSUF1MPUA-4GE(16744449),  -- USG6300 1U Main Processing Unit Board.

--SIG9800 Serie's TC-MIB vlaue scope:   16732160 ~ 16736255  or Hex format:0x00ff5000~0x00ff5fff    (Both 16732160 and 16736255 are included)
--SIG9800
                bnameSIG9800SPUA(16732160),          --SPUA Board
                bnameSIG9800SFUG(16732161),          --160G SFUG
                bnameSIG9800IG21SPUC02(16732162),    --40G X3 Service Processing Unit,with HS Service Inspection Gateway Software
                bnameSIG9800IG21SPUD02(16732163),    --40G X8&X16 Service Processing Unit,with HS Service Inspection Gateway Software
                bnameSIG9800IG2D00E1NS00(16732164),  --SIG9800-X,IG21E1NC00,1-Port 100GBase-CFP Integrated Line Processing Unit (LPUI-101)
                bnameSIG9800IG2DLPUFA000(16732165),  --SIG9800-X,IG21LPUF100CA00,Flexible Card Line Processing Unit(LPUF-101)
                bnameSIG9800IG21LPUF120A00(16732166),  --SIG9800-X,IG21LPUF120A00,Flexible Card Line Processing Unit(LPUF-120),with HW Service Inspection Gateway Software
                bnameSIG9800IG21LPUF240A00(16732167),  --SIG9800-X,IG21LPUF240A00,Flexible Card Line Processing Unit(LPUF-240),with HW Service Inspection Gateway Software
                bnameSIG9800IG21MPUD2(16732168),  --SIG9800-X,IG21MPUD2,X3 Main Processing Unit D2(Including 2G Memory and 2G USB),with HW Service Inspection Gateway Software


--Eudemon8000E/USG9000 Serie's TC-MIB vlaue scope:    16748544 ~ 16752639  or Hex format:0x00ff9000 ~ 0x00ff9fff    (Both 16748544 and 16752639 are included)
--Eudemon8000E/USG9000
                bnameE8000EKW51ESPU(16748544),        --SPU Board ,Service Processing Unit
                bnameE8000EDCU(16748545),         --DCU Board ,Detection and Clean Unit
                bnameE8000ESUP3SPUA02(16748546),          --Service Processing Unit,with HS General Security Platform Software
                bnameE8000ECR52LPUKD1(16748547),     --Flexible Card Line Processing Unit(LPUF-21,2 sub-slots) B
                bnameE8000ESUP3SPUA02IPS(16748548),  --IPS Service Processing Unit,with HS General Security Platform Software
                bnameE8000EKW51ESPUIPS(16748549),      --IPS SPU Board ,Service Processing Unit
        bnameE8000ESU91SPUC(16748550),      --Eudemon8000E-X,SU91SPUC,X3 Service Processiong Unit(Base Board),with HS General Security Platform Software
        bnameE8000ESU91SPUD(16748551),      --Eudemon8000E-X,SU91SPUD,X8&X16 Service Processiong Unit(Base Board),with HS General Security Platform Software

        bnameE8000ESU91SPUC01(16748552),    --Eudemon8000E-X,SU91SPUC01,40G X3 Firewall Service Processing Unit ,with HW General Security Platform Software,include SPUC and 1*SPCC01
        bnameE8000ESU91SPUC02(16748553),    --Eudemon8000E-X,SU91SPUC02,20G X3 Firewall Service Processing Unit(oversea),with HW General Security Platform Software,include SPUC and 1*SPCB02
        bnameE8000ESU91SPUC03(16748554),    --Eudemon8000E-X,SU91SPUC03,60G X3 Firewall Service Processing Unit ,with HW General Security Platform Software
        bnameE8000ESU91SPUD01(16748555),    --Eudemon8000E-X,SU91SPUD01,40G X8&X16 Firewall Service Processing Unit ,with HW General Security Platform Software,include SPUD and  1*SPCC01
        bnameE8000ESU91SPUD02(16748556),    --Eudemon8000E-X,SU91SPUD02,80G X8&X16 Firewall Service Processiong Unit,with HW General Security Platform Software,include SPUD and 1*SPCB01
        bnameE8000ESU91SPUD03(16748557),    --Eudemon8000E-X,SU91SPUD03,20G X8&X16 Firewall Service Processing Unit(oversea),with HW General Security Platform Software,include SPUD and 1*SPCB02

        bnameE8000ESU91SPUC04(16748570),    --Eudemon8000E-X,SU91SPUC04,40G X3 Firewall Service Processing Unit ,Double CPUs,with HW General Security Platform Software,include SPUC and 1*SPCB04
                bnameE8000ESU91SPUD05(16748571),    --Eudemon8000E-X,SU91SPUD05,40G X8&X16 Firewall Service Processing Unit ,Double CPUs,with HW General Security Platform Software,include SPUD and  1*SPCB04
                bnameE8000ESU91LPUF100CA00(16748572),   --Eudemon8000E-X,SU91LPUF100CA00,Flexible Card Line Processing Unit(LPUF-101,4 sub-slots),with HW General Security Platform Software
                bnameE8000ESU91LPUF100CA0(16748573),    --Eudemon8000E-X3,SU91LPUF100CA01,X3 Flexible Card Line Processing Unit(LPUF-100,4 sub-slots),with HW General Security Platform Software
                bnameE8000ESU91LPUI100CA00(16748574),   --Eudemon8000E-X,SU91LPUI100CA00,10-Port 10GBase LAN/WAN-SFP+ Integrated Line Processing Unit (LPUI-100) ,with HW General Security Platform Software
                bnameE8000ESU91E1NC00(16748575),    --Eudemon8000E-X,SU91E1NC00,1-Port 100GBase-CFP Integrated Line Processing Unit (LPUI-101),with HW General Security Platform Software
                bnameEudemon8000ESU91EDXFB0(16748576),  --Eudemon8000E-X,SU91EDXFB0,16-Port 10GBase LAN-SFP+ Integrated Line Processing Unit (LPUI-100) ,with HW General Security Platform Software
                bnameEudemon8000ESU91E4XFA0(16748577),  --Eudemon8000E-X,SU91E4XFA0,4-Port 10GBase LAN-SFP+ Flexible Card(P100,1/4wide,Occupy one sub-slots)
                bnameEudemon8000ESU91LBXF0(16748578),   --Eudemon8000E-X,SU91LBXF0,12-Port 10G Base LAN/WAN-SFP+ Flexible Card A(P120-A)
                --add by jiaoningfei wx299524 20160413
                --firewall product board scope 16744448~16748543 or Hex forrmat 0x00ff8000~0x00ff8fff

                --added by usg
                bnameSPU5UPUC(16744448),                --0x00ff8000
                bnameSPUA-NAT-X8X16-E8KE(16744455),     --0x00ff8007
                bnameSPU-NAT-X8X16-E8KE(16744456),      --0x00ff8008
                bnameSPUB-H(16744466),                  --0x00ff8012
                bnameSPUB-M(16744467),                  --0x00ff8013
                bnameSPUB-20-O-M(16744468),             --0x00ff8014
                bnameSPUB-20-O-H(16744469),             --0x00ff8015
                bnameNIP-MPU-X3(16744470),              --0x00ff8016
                bnameNIP-LPUA(16744471),                --0x00ff8017
                bnameNIP-SPU-A(16744472),               --0x00ff8018
                --end added

                bnameE8KE-X-LPUF-120(16748606),     -- Finished Board Unit,Eudemon8000E-X,E8KE-X-LPUF-120,Flexible Card Line Processing Unit(LPUF-120,2 sub-slots)(0x00ff903e)
                bnameE8KE-X-LPUF-240(16748607),     -- Finished Board Unit,Eudemon8000E-X,E8KE-X-LPUF-240,Flexible Card Line Processing Unit(LPUF-240,2 sub-slots)(0x00ff903f)
                bnameSPUB-X8X16-E8KE(16748627),     -- X8&X16 Firewall Service Processing Unit B (0x00ff9053)
                bnameSPUA-X8X16-E8KE(16748628),     -- X8&X16 Firewall Service Processing Unit A (0x00ff9054)
                bnameSPUB-X3-E8KE(16748629),     -- X3 Firewall Service Processing Unit B (0x00ff9055)
                bnameSPUA-X3-E8KE(16748630),     -- X3 Firewall Service Processing Unit A (0x00ff9056)
                bnameSPU-X3-B2(16748633),     -- X3 Service Processing Unit 2(Base Board) (0x00ff9059)
                bnameSPU-X8X16-20-B-E8KE(16748634),     -- 20G X8&X16 Firewall Service Processing Unit B(oversea)(0x00ff905a)
                bnameSPU-X8X16-20-A-E8KE(16748635),     -- 20G X8&X16 Firewall Service Processing Unit A(oversea)(0x00ff905b)
                bnameSPU-X3-20-A-E8KE(16748636),     -- 20G X3 Firewall Service Processing Unit A(oversea)(0x00ff905c)
				bnameSPU-X3-20-B-E8KE(16744461),     -- 20G X3 Firewall Service Processing Unit B(oversea)(0x00ff800d)
				bnameSPUA-H(16744457),     -- X8&X16 Firewall Service Processing Unit(0x00ff8009)
				bnameSPUA-M(16744458),     -- X3 Firewall Service Processing Unit(0x00ff800a)
				bnameSPUA-20-O-H (16744459),     -- 20G X8&X16 Firewall Service Processing Unit (oversea)(0x00ff800b)
				bnameSPUA-20-O-M(16744460),     -- 20G X3 Firewall Service Processing Unit (oversea)(0x00ff800c)
				bnameSPUB-NAT-X8X16-E8KE(16744454),     -- X8&X16 NAT Service Processing Unit B(0x00ff8006)
-- NIP6800
                bnamebnameNIP-SPU-B(16744462),     -- NIP6800 Service Processing Unit(Base Board)(0x00ff800e)
				bnameNIP-LPUF-120 (16744463),     -- NIP6800 Flexible Card Line Processing Unit(120G,2 sub-slots)(0x00ff800f)
				bnameNIP-LPUF-240 (16744464),     -- NIP6800 Flexible Card Line Processing Unit(240G,2 sub-slots)(0x00ff8010)
				bnameNIP6800-X8-SRUA-200 (16744465),     -- NIP6800 X8 200Gbps Switch and Route Processing Unit A(0x00ff8011)
				bnameNIP-LPUF-51(16744491),	           	 --Finished Board Unit,NIP6800,NIP-LPUF-51,Flexible Card Line Processing Unit(LPUF-51,2 sub-slots)
				bnameNIP-SPU-A2SP(16744492),	         --Finished Board Unit,NIP6800,NIP-SPU-A2,NIP6830 Service Processing Unit 2(Base Board)

-- USG9100 Board/Card :


-- AntiDDoS8000:
				bnameADS-SPUC-B2SP(16744488),	  --Finished Board Unit,AntiDDoS8000,ADS-SPUC-B2,AntiDDoS8030 Service Processing Unit 2(Base Board)
				bnameADS-SPUC-BSP(16748603),	  --Finished Board Unit,AntiDDoS8000,ADS-SPUC-B,AntiDDoS8030 Service Processing Unit(Base Board)
				bnameADS-SPUD-BSP(16748604),	  --Finished Board Unit,AntiDDoS8000,ADS-SPUD-B,AntiDDoS8080&AntiDDoS8160 Service Processing Unit(Base Board)

-- Eudemon8000E-X :
				bnameE8KE-X-LPUF-51SP(16744489),	            --Finished Board Unit,Eudemon8000E-X,E8KE-X-LPUF-51,Flexible Card Line Processing Unit(LPUF-51,2 sub-slots)
				bnameE8KE-X3-MPUSP(16748605),	                --Finished Board Unit,Eudemon8000E-X,E8KE-X3-MPU,X3 Main Processing Unit(Including 1*2G Memory and 1*2G USB Disk)

-- SeMG9811 :
				bnameSEMG-X8-SRUA-200SP(16744481),	    	--Finished Board Unit,SeMG9811,SEMG-X8-SRUA-200,X8 200Gbps Switch and Route Processing Unit A
				bnameSEMG-X16-MPUSP(16744482),	            --Finished Board Unit,SeMG9811,SEMG-X16-MPU,X16 Main Processing Unit
				bnameSEMG-X3-MPUSP(16744483),		            --Finished Board Unit,SeMG9811,SEMG-X3-MPU,X3 Main Processing Unit
				bnameSEMG-LPUF-101SP(16744484),	            --Finished Board Unit,SeMG9811,SEMG-LPUF-101,Flexible Card Line Processing Unit(LPUF-101,4 sub-slots)
				bnameSEMG-SPU-X3-40SP(16744485),	            --Finished Board Unit,SeMG9811,SEMG-SPU-X3-40,40G Protection X3 Service Processing Unit
				bnameSEMG-SPU-X8X16-40SP(16744486),	        --Finished Board Unit,SeMG9811,SEMG-SPU-X8X16-40,40G Protection X8 and X16 Service Processing Unit
				bnameSEMG-SPU-X8X16-80SP(16744487),	        --Finished Board Unit,SeMG9811,SEMG-SPU-X8X16-80,80G Protection X8 and X16 Service Processing Unit

-- USG9500 :
			    bnameFWCD0LPUKD01(16744473),	            	--Finished Board Unit,USG9500,FWC2LPUKD2,Flexible Card Line Processing Unit(LPUF-21,2 Sub-Slots) B
				bnameFWCD0LPUND01(16744474),	            	--Finished Board Unit,USG9500,SU91LPUF40A3,Flexible Card Line Processing Unit(LPUF-40,2 sub-slots) A
				bnameE8KE-X-LPUF-101(16744475),	    	    --Finished Board Unit,USG9500,SU91LPUF100CA05,Flexible Card Line Processing Unit(LPUF-101,4 sub-slots)
				bnameE8KE-X-101-1X100GE-CFP(16744476),		--Finished Board Unit,USG9500,SU91E1NC05,1-Port 100GBase-CFP Integrated Line Processing Unit (LPUI-101)
				bnameSPU-X3-20-O-E8KE(16744477),	    	    --Finished Board Unit,USG9500,SU91SPUC05,20G X3 Firewall Service Processing Unit(oversea),include SPUC and 1*SPCB02
				bnameSPU-X8X16-20-O-E8KE(16744478),	     	--Finished Board Unit,USG9500,SU91SPUD07,20G X8 and X16 Firewall Service Processing Unit(oversea),include SPUD and 1*SPCB02
				bnameSPU-X3-B(16744479),	                	--Finished Board Unit,USG9500,SU91SPUC06,X3 Service Processing Unit(Base Board)
				bnameSPU-X8X16-B(16744480),	            	--Finished Board Unit,USG9500,SU91SPUD08,X8 and X16 Service Processing Unit(Base Board)
				bnameFW-LPUF-51(16744490),	            	--Finished Board Unit,USG9500,FW-LPUF-51,Flexible Card Line Processing Unit(LPUF-51,2 sub-slots)
				bnameFW-LPUF-120SP(16748592),	                --Finished Board Unit,USG9500,FW-LPUF-120,120G Line Processing Unit
				bnameFW-LPUF-240SP(16748593),	           		--Finished Board Unit,USG9500,FW-LPUF-240,240G Line Processing Unit

-- USG12000 :
bnameLPUA-18CQ      (16748608),   --0x00ff9040
bnameE9KE-LPUA-18CQ (16748609),   --0x00ff9041
bnameLPUA-48XS      (16748610),   --0x00ff9042
bnameE9KE-LPUA-48XS (16748611),   --0x00ff9043
bnameLPUA-4CQ-24XS  (16748612),   --0x00ff9044
bnameE-LPUA-4CQ-24XS(16748613),   --0x00ff9045
bnameLPUA-2CQ-24XS  (16748614),   --0x00ff9046
bnameE-LPUA-2CQ-24XS(16748615),   --0x00ff9047
bnameMPUA-USG-X4X8  (16748616),   --0x00ff9048
bnameMPUA-E9KE-X4X8 (16748617),   --0x00ff9049
bnameSFUA-USG12008  (16748618),   --0x00ff904a
bnameSFUA-E9KE-X8   (16748619),   --0x00ff904b
bnameSPUA-USG-01    (16748620),   --0x00ff904c
bnameSPUA-USG-02    (16748621),   --0x00ff904d
bnameSPUA-USG-TP-01 (16748622),   --0x00ff904e
bnameSPUA-USG-TP-02 (16748623),   --0x00ff904f
bnameSPUA-E9KE-01   (16748624),   --0x00ff9050
bnameSPUA-E9KE-02   (16748625),   --0x00ff9051
bnameSPUA-E9KE-TP-01(16748626),   --0x00ff9052
bnameSPUA-E9KE-TP-02(16748639),   --0x00ff905f
bnameSPUA-ADS-01    (16748640),   --0x00ff9060
bnameSPUA-ADS-02    (16748641),	  --0x00ff9061
bnameMPUA-ADS-X4X8         (16748642),--0x00ff9062
bnameE9KE-LPUA-12CQ        (16748643),--0x00ff9063
bnameIPS-LPUA-48XS       (16748644),--0x00ff9064
bnameI-LPUA-4CQ-24XS        (16748645),--0x00ff9065
bnameI-LPUA-2CQ-24XS        (16748646),--0x00ff9066
bnameMPUA-IPS-X4X8        (16748647),--0x00ff9067
bnameSFUA-IPS12008        (16748648),--0x00ff9068
bnameSPUA-IPS-01       (16748649),--0x00ff9069
bnameSPUA-IPS-02       (16748650),--0x00ff906a
bnameE8KE-X8-SRUE-480       (16748651),--0x00ff906b
bnameE8KE-X16-SFUG-480       (16748652),--0x00ff906c
bnameE8KE-X8-SFUF-480       (16748653),--0x00ff906d
bnameSPUA-USG-03       (16748654),--0x00ff906e
bnameMPUA-U-X4X8-T        (16748655),--0x00ff906f
bnameMPUA-E-X4X8-T        (16748656),--0x00ff9070
bnameMPUB-IPS-X4X8        (16748657),--0x00ff9071
bnameMPUB-USG-X4X8        (16748658),--0x00ff9072
bnameMPUB-E9KE-X4X8       (16748659),--0x00ff9073
bnameMPUB-ADS-X4X8        (16748660),--0x00ff9074
bnameMPUB-A-X4X8-T        (16748661),--0x00ff9075
bnameMPUB-U-X4X8-T        (16748662),--0x00ff9076
bnameMPUB-E-X4X8-T        (16748663),--0x00ff9077
bnameSPUA-E9KE-03         (16748664),--0x00ff9078
bnameUSG6615F      (16748665),--0x00ff9079
bnameUSG6625F      (16748666),--0x00ff907a
bnameUSG6635F      (16748667),--0x00ff907b
bnameUSG6655F      (16748668),--0x00ff907c
bnameEudemon1000E-F15      (16748669),--0x00ff907d
bnameEudemon1000E-F25      (16748670),--0x00ff907e
bnameAntiDDoS1905      (16748671),--0x00ff907f
bnameIPS6585F      (16748672),--0x00ff9080
bnameIPS6615F      (16748673),--0x00ff9081
bnameEudemon1000E-F35      (16748674),--0x00ff9082
bnameEudemon1000E-F55      (16748675),--0x00ff9083
bnameIPS6625F      (16748676),--0x00ff9084
bnameSIC-2SM-BF      (16748677),--0x00ff9085
bnameSPUB-USG-01       (16748678),      --0x00ff9086
bnameSPUB-USG-02       (16748679),      --0x00ff9087
bnameSPUB-USG-TP-01       (16748680),      --0x00ff9088
bnameSPUB-USG-TP-02       (16748681),      --0x00ff9089
bnameSPUB-E9KE-01       (16748682),      --0x00ff908a
bnameSPUB-E9KE-02       (16748683),      --0x00ff908b
bnameSPUB-E9KE-TP-01       (16748684),      --0x00ff908c
bnameSPUB-E9KE-TP-02       (16748685),      --0x00ff908d
bnameSPUB-IPS-01       (16748686),      --0x00ff908e
bnameSPUB-IPS-02       (16748687),      --0x00ff908f
bnameSPUB-ADS-01       (16748688),      --0x00ff9090
bnameSPUB-ADS-02       (16748689),      --0x00ff9091
bnameUSG6603F-C-AC       (16748690),      --0x00ff9092
bnameUSG6620F-K-AC    (16748691),    --00ff9093
bnameAntiDDoS1905-K-AC    (16748692),    --00ff9094
bnameUSG6650F-K-AC    (16748693),    --00ff9095
bnameIPS6610FD-K-AC    (16748694),    --00ff9096
bnameIPS6610F-K-AC    (16748695),    --00ff9097
bnameSPUB-E9KE-02-L    (16748696),    --00ff9098
bnameUSG6725F    (16748697),    --00FF9099
bnameIPS6655F    (16748698),    --00FF909A
bnameAntiDDoS1908    (16748699),    --00FF909B
bnameUSG6715F    (16748700),    --00FF909C
bnameUSG6710F-K    (16748701),    --00FF909D
bnameEudemon1000E-F125    (16748702),    --00FF909E
bnameUSG6685F    (16748704),    --00FF90A0
bnameEudemon1000E-F85    (16748705),    --00FF90A1
bnameIPS6620F-K    (16748711),    --00FF90A7
bnameSRUA-USG-F4    (16748712),    --00FF90A8
bnameSRUA-USG-F4-T    (16748713),    --00FF90A9
bnameSRUB-USG-F8    (16748714),    --00FF90AA
bnameSRUB-USG-F8-T    (16748715),    --00FF90AB
bnameLPUF-USG-24XS    (16748716),    --00FF90AC
bnameLPUF-E9KE-24XS    (16748717),    --00FF90AD
bnameLPUF-IPS-24XS    (16748718),    --00FF90AE
bnameLPUF-U-2CQ-12XS    (16748719),    --00FF90AF
bnameLPUF-E-2CQ-12XS    (16748720),    --00FF90B0
bnameLPUF-I-2CQ-12XS    (16748721),    --00FF90B1
bnameSPUF-USG-03    (16748722),    --00FF90B2
bnameSPUF-USG-02    (16748723),    --00FF90B3
bnameSPUF-USG-01    (16748724),    --00FF90B4
bnameSPUF-USG-TP-03    (16748725),    --00FF90B5
bnameSPUF-E9KE-03    (16748726),    --00FF90B6
bnameSPUF-E9KE-02    (16748727),    --00FF90B7
bnameSPUF-E9KE-01    (16748728),    --00FF90B8
bnameSPUF-E9KE-TP-03    (16748729),    --00FF90B9
bnameSPUF-ADS-03    (16748730),    --00FF90BA
bnameSPUF-ADS-02    (16748731),    --00FF90BB
bnameSPUF-ADS-01    (16748732),    --00FF90BC
bnameSPUF-IPS-03    (16748733),    --00FF90BD
bnameEudemon1000E-F205    (16748734),    --00FF90BE
bnameAntiDDoS1908-K    (16748736),    --00FF90C0
bnameUSG6710F    (16748737),    --00FF90C1
bnameSRUA-E9KE-F4    (16748739),    --00FF90C3
bnameSRUA-E9KE-F4-T    (16748740),    --00FF90C4
bnameSRUB-E9KE-F8    (16748741),    --00FF90C5
bnameSRUB-E9KE-F8-T    (16748742),    --00FF90C6
bnameSRUA-ADS-F4    (16748743),    --00FF90C7
bnameSRUA-ADS-F4-T    (16748744),    --00FF90C8
bnameSRUB-ADS-F8    (16748745),    --00FF90C9
bnameSRUB-ADS-F8-T    (16748746),    --00FF90C10
bnameSRUA-IPS-F4    (16748747),    --00FF90C11
bnameSRUB-IPS-F8    (16748748),    --00FF90C12
bnameSPUF-USG-TP-02    (16748749),    --00FF90C13
bnameSPUF-USG-TP-01    (16748750),    --00FF90C14
bnameSPUF-IPS-02    (16748751),    --00FF90C15
bnameSPUF-IPS-01    (16748752),    --00FF90C16
bnameLPUA-4DQ    (16748753),    --00FF90C17
bnameLPUA-E-4DQ    (16748754),    --00FF90C18
bnameLPUA-12CQ    (16748755),    --00FF90C19
bnameMPUC-USG-X4X8    (16748756),    --00FF90C20
bnameMPUC-U-X4X8-T    (16748757),    --00FF90C21
bnameMPUC-E9KE-X4X8    (16748758),    --00FF90C22
bnameMPUC-E-X4X8-T    (16748759),    --00FF90C23
bnameMPUC-ADS-X4X8    (16748760),    --00FF90C24
bnameMPUC-A-X4X8-T    (16748761),    --00FF90C25
bnameMPUC-IPS-X4X8    (16748762),    --00FF90C26
bnameUSG6000F-E20    (16748763),    --00FF90DB
bnameUSG6000F-E15    (16748764),    --00FF90DC
bnameUSG6000F-E12    (16748765),    --00FF90DD
bnameUSG6000F-E09    (16748766),    --00FF90DE
bnameUSG6000F-E07    (16748767),    --00FF90DF
bnameUSG6000F-E05    (16748768),    --00FF90E0
bnameUSG6000F-E03    (16748769),    --00FF90E1
bnameUSG6000F-E01    (16748770),    --00FF90E2
bnameProbe1005    (16748771),    --00FF90E3
bnameProbe1010    (16748772),    --00FF90E4
bnameProbe1020    (16748773),    --00FF90E5
bnameProbe1030    (16748774),    --00FF90E6
bnamePDC2K2S54-CF    (16748775),    --00FF90E7
bnameFAN-240SM-B    (16748776),    --00FF90E8
bnameFAN-480SM-B    (16748777),    --00FF90E9
bnameUSG6000E-E03    (16748778),    --00FF90EA
bnameUSG6000E-E07    (16748779),    --00FF90EB
bnameUSG6000E-E10    (16748780),    --00FF90EC
bnameUSG6308E-B    (16748781),    --00FF90ED
bnameUSG6318E-B    (16748782),    --00FF90EE
bnameUSG6338E-B    (16748783),    --00FF90EF
bnameUSG6358E-B    (16748784),    --00FF90F0
bnameUSG6378E-B    (16748785),    --00FF90F1
bnameUSG6388E-B    (16748786),    --00FF90F2
bnameUSG6398E-B    (16748787),    --00FF90F3
bnameEudemon1000E-C1    (16716017),    --00FF10F1
bnameEudemon1000E-S1    (16716018),    --00FF10F2
bnameEudemon1000E-S5    (16716019),    --00FF10F3
bnameEudemon1000E-S8    (16716020),    --00FF10F4
bnameEudemon1000E-M1    (16716021),    --00FF10F5
bnameEudemon1000E-M2    (16716022),    --00FF10F6
bnameEudemon1000E-M3    (16716023),    --00FF10F7
bnameEudemon1000E-M5    (16716024),    --00FF10F8
bnameAntiDDoS1905-N    (16716025),    --00FF10F9
bnameMPUD-USG-X4X8    (16716026),    --00FF10FA
bnameMPUD-U-X4X8-T    (16716027),    --00FF10FB
bnameMPUD-E9KE-X4X8    (16716028),    --00FF10FC
bnameMPUD-E-X4X8-T    (16716029),    --00FF10FD
bnameMPUD-ADS-X4X8    (16716030),    --00FF10FE
bnameMPUD-A-X4X8-T    (16716031),    --00FF10FF
bnameMPUD-IPS-X4X8    (16716032),    --00FF1100
bnameASG5303    (16716033),    --00FF1101
bnameASG5305    (16716034),    --00FF1102
bnameASG5308    (16716035),    --00FF1103
bnameASG5310    (16716036),    --00FF1104
bnameASG5315    (16716037),    --00FF1105
bnameASG5320    (16716038),    --00FF1106
bnameASG5505    (16716039),    --00FF1107
bnameASG5510    (16716040),    --00FF1108
bnameASG5520    (16716041),    --00FF1109
bnameASG5530    (16716042),    --00FF110A
bnameASG5550    (16716043),    --00FF110B
bnameASG5610    (16716044),    --00FF110C
bnameASG5000-S1050    (16716045),    --00FF110D
bnameASG5000-S1055    (16716046),    --00FF110E
bnameASG5000-D1060    (16716047),    --00FF110F
bnameASG5000-S1100    (16716048),    --00FF1110
bnameASG5000-E1108    (16716049),    --00FF1111
bnameASG5000-D1120    (16716050),    --00FF1112
bnameASG5000-S1220    (16716051),    --00FF1113
bnameASG5000-D1300    (16716052),    --00FF1114
bnameASG5000-E1400    (16716053),    --00FF1115
bnameASG5000-S1460    (16716054),    --00FF1116
bnameASG5000-D1500    (16716055),    --00FF1117
bnameASG5000-E2100    (16716056),    --00FF1118
bnameASG5000-D2100    (16716057),    --00FF1119
bnameASG5000-D2250    (16716058),    --00FF111A
bnameASG5000-D2500    (16716059),    --00FF111B
bnameASG5000-D3100    (16716060),    --00FF111C
bnamePAC180S12-CN    (16716061),    --00FF111D
bnamePAC350S12-CR    (16716062),    --00FF111E
bnamePAC600S12-PB    (16716063),    --00FF111F
bnamePDC1K2S12-CE    (16716064),    --00FF1120
bnamePAC1K2S12-PB    (16716065),    --00FF1121
bnameUSG6505F-C    (16748838),    --00FF9126
bnameUSG6606F-C    (16748839),    --00FF9127
bnameIPS6525F    (16748840),    --00FF9128
bnameIPS6525FD    (16748841),    --00FF9129
bnameIPS6585FD    (16748842),    --00FF912A
bnameIPS6615FD    (16748843),    --00FF912B
bnameIPS6625FD    (16748844),    --00FF912C
bnameUSG6510F-D    (16748849),    --00FF9131
bnameUSG6530F-D    (16748850),    --00FF9132
bnameUSG6510F-DK    (16748851),    --00FF9133
bnameUSG6510F-DL    (16748852),    --00FF9134
bnameUSG6530F-DL    (16748853),    --00FF9135
bnameUSG6525F       (16748864),    --00FF9140
bnameUSG6555F       (16748865),    --00FF9141
bnameUSG6565F       (16748866),    --00FF9142
bnameUSG6585F       (16748867),    --00FF9143
bnameUSG6520F-K    (16748868),    --00FF9144
bnameUSG6560F-K    (16748869),    --00FF9145
bnameUSG6590F-K    (16748870),    --00FF9146
bnameIPS6520F-K    (16748871),    --00FF9147
bnameEudemon1000E-F08    (16748872),    --00FF9148
bnameUSG6502F-C    (16748874),    --00FF914A
bnameUSG6303E    (16748877),    --00FF914D
bnameLPUA-12CQ24XS    (16748878),    --00FF914E
bnameLPUA-E-12CQ24XS    (16748879),    --00FF914F
bnameSFUA-USG12008-v2    (16748880),    --00FF9150
bnameSFUA-E9KE-X8-v2   (16748881),    --00FF9151
bnameSFUA-IPS12008-v2    (16748882),    --00FF9152
bnameMPUD-E9KE-X16    (16748883),    --00FF9153
bnameMPUD-E9KE-X16-T    (16748884),    --00FF9154
bnameMPUD-ADS-X16    (16748885),    --00FF9155
bnameMPUD-ADS-X16-T    (16748886),    --00FF9156
bnameSFUA-USG12016    (16748887),    --00FF9157
bnameSFUA-E9KE-X16    (16748888),    --00FF9158
bnameSPUC-E9KE-02    (16748892),    --00FF915C
bnameEUDEMON1000E-M55    (16748893),    --00FF915D
bnameEUDEMON1000E-M10    (16748894),    --00FF915E
bnameEUDEMON1000E-S10    (16748895),    --00FF915F
bnameEUDEMON1000E-C10    (16748896),    --00FF9160
bnameEudemon1000E-T1    (16748902),    --00FF9166
bnameUSG6621F-O    (16748903),    --00FF9167
bnameUSG6620F-O    (16748904),    --00FF9168
bnameSIC-4GE-BC    (16748905),    --00FF9169
bnameUSG6510F-DPL    (16748906),    --00FF916A
bnameUSG6530F-DPL    (16748907),    --00FF916B
bnameEudemon1000E-C1A        (16748909),    --00FF916D
bnameEudemon1000E-M1A        (16748912),    --00FF9170
bnameEudemon1000E-M2A        (16748913),    --00FF9171
bnameEudemon1000E-S1A        (16748916),    --00FF9174
bnameEudemon1000E-T1A        (16748919),    --00FF9177
bnameMPUA-H6-T        (16748922),    --00FF917A
bnameProbe1001F        (16748923),    --00FF917B
bnameEudemon1000E-F01        (16748924),    --00FF917C
bnameEudemon1000E-F05        (16748925),    --00FF917D
bnameUSG6680E-ACC        (16748926),    --00FF917E
bnameUSG6585F-B        (16748933),    --00FF9185
bnameEudemon1000E-C5A        (16748936),    --00FF9188
bnameEudemon1000E-C8A        (16748937),    --00FF9189
bnameEudemon1000E-M3A        (16748938),    --00FF918A
bnameEudemon1000E-M5A        (16748939),    --00FF918B
bnameEudemon1000E-S5A        (16748940),    --00FF918C
bnameEudemon1000E-S8A        (16748941),    --00FF918D
bnameEudemon1000E-T3A        (16748942),    --00FF918E
bnameEudemon1000E-T5A        (16748943),    --00FF918F
bnameEudemon1000E-C10A        (16748944),    --00FF9190
bnameEudemon1000E-S10A        (16748945),    --00FF9191
bnameEudemon1000E-M10A        (16748946),    --00FF9192
bnameEudemon1000E-T10A        (16748947),    --00FF9193
bnameLPUG-E-16CQ24XS        (16748948),    --00FF9194
bnameLPUG-E-8CQ24XS        (16748949),    --00FF9195
bnameSPUG-E9KE-03        (16748950),    --00FF9196
bnameSPUG-E9KE-02        (16748951),    --00FF9197
bnameMPUA-H6        (16748952),    --00FF9198
bnameEudemon1000E-C1A-PL        (16748959),    --00FF919F
bnameEudemon1000E-M1A-PL        (16748960),    --00FF9200
bnameEudemon1000E-S1A-PL        (16748961),    --00FF9201
bnameEudemon1000E-T1A-PL        (16748962),    --00FF9202
bnamePAC80S12-CN        (16748963),    --00FF9203
bnameEudemon1000E-F10        (16748964),    --00FF9204
bnameEudemon1000E-F03-D        (16748965),    --00FF9205
bnameEudemon1000E-F03-DL        (16748966),    --00FF9206
bnameUSG6000F-S30       (16748967),    --00FF9207
bnameUSG6000F-S50       (16748968),    --00FF9208
bnameUSG6000F-S150       (16748969),    --00FF920A
bnameUSG6000F-S160       (16748970),    --00FF920B
bnameUSG6000F-S180       (16748971),    --00FF920C
bnameUSG6000F-S200       (16748972),    --00FF920D
bnameUSG6000F-S230       (16748973),    --00FF920E
bnameUSG6000F-S260       (16748974),    --00FF920F
bnameIPS6000F-S110       (16748975),    --00FF9210
bnameIPS6000F-S120       (16748976),    --00FF9211
bnameXH6655         	 (16748977),    --00FF9212
bnamePAH3KS54-CF         (16748978),    --00FF9213
bnameLPUG-U-16CQ24XS    (16748979),      --00FF9214
bnameLPUG-I-16CQ24XS    (16748980),      --00FF9215
bnameLPUG-U-8CQ24XS	    (16748981),      --00FF9216
bnameLPUG-I-8CQ24XS	    (16748982),      --00FF9217
bnameSPUG-USG-03        (16748983),      --00FF9218
bnameSPUG-DDOS-03       (16748984),      --00FF9219
bnameSPUG-IPS-03        (16748985),      --00FF922A
bnameSPUG-USG-02        (16748986),      --00FF922B
bnameSPUG-DDOS-02       (16748987),      --00FF922C
bnameSPUG-IPS-02        (16748988),      --00FF922D
bnameMPUA-USG-H6        (16748989),      --00FF922E
bnameMPUA-USG-H6-T      (16748990),      --00FF922F
bnameSPUG-DDOS-04       (16748991),      --00FF9220
bnameSPUG-IPS-04        (16748992),      --00FF9221
bnameMPUA-USG6636F        (16748993),      --00FF91C1
bnameMPUA-USG6656F        (16748994),      --00FF91C2
bnameMPUA-USG6686F        (16748995),      --00FF91C3
bnameMPUA-USG6000F-S115        (16748996),      --00FF91C4
bnameMPUA-USG6000F-S125        (16748997),      --00FF91C5
bnameSPUG-USG-04        (16748998),      --00FF91C6
bnameSPUG-E9KE-04        (16748999),      --00FF91C7
bnameMPUA-USG6560F-D        (16749001),      --00FF91C9
bnameMPUA-Eudemon1000E-F06-D        (16749002),      --00FF91CA
bnameMPUA-USG6000F-E06-D     (16749003),      --00FF91CB
bnameMPUA-USG6000F-E12-D     (16749004),      --00FF91CC
bnameMPUA-USG6000F-E06-DL     (16749005),      --00FF91CD
bnameMPUA-USG6000F-S112        (16749006),      --00FF91CE
bnameSPUD-USG         (16749007),      --00FF91CF
bnameSPUD-E9KE        (16749008),      --00FF91D0
bnameSPUD-ADS        (16749009),      --00FF91D1
bnameSPUD-IPS        (16749010),      --00FF91D2
bnameMPUA-USG6000F-S330(16749011),    --00FF91D3
bnameMPUA-USG6000F-S500(16749012),    --00FF91D4
bnameMPUA-USG6000F-S55L(16749013),    --00FF91D5
bnameLPUG-E-4CQ24XS(16749014),    --00FF91D7
bnameLPUG-U-4CQ24XS(16749015),    --00FF91D8
bnameLPUG-I-4CQ24XS(16749016),    --00FF91D9
bnameMPUA-USG6000F-S530        (16749017),      --00FF91D9
bnameMPUA-USG6000F-S600        (16749018),      --00FF91DA
bnameSPUG-E9KE-01        (16749019),      --00FF91DB
bnameSPUG-USG-01        (16749020),      --00FF91DC
bnameSPUG-DDOS-01        (16749021),      --00FF91DD
bnameSPUG-IPS-01        (16749022),      --00FF91DE
bnameUSG6000F-S12        (16749023),      --00FF91DF
bnameUSG6000F-S13        (16749024),      --00FF91E1
bnameUSG6855G        (16749025),      --00FF91E2
bnameUSG6875G        (16749026),      --00FF91E3
bnameUSG6885G        (16749027),      --00FF91E4
bnameEudemon1000E-W855        (16749028),      --00FF91E5
bnameEudemon1000E-W875        (16749029),      --00FF91E6
bnameEudemon1000E-W885        (16749030),      --00FF91E7
bnameAntiDDoS1907        (16749031),      --00FF91E7



--Security Product's TC-MIB end

-- CCU board of shelf Management: from 0x00ffa000 to 0x00ffafff (Both 0x00ff9000 and 0x00ff9fff are included)
                bnameCCUMAIN(16752640),             -- CCU main board
                bnameUEU(16752641),                 -- UEU board
                bnameEEU(16752642),                 -- EEU board
                bnameAIU(16752643),                 -- AIU board

-- Virtual board of Net Management: from 0X70000000
                bnameMDUUNKNOWN(1879048192),             -- Virtual remote board of type unknown
                bnameMDUMA5620E(1879048193),             -- Virtual remote board of MA5620E
                bnameMDUMA5626E(1879048194),             -- Virtual remote board of MA5626E

-- FutureMatrix: 0x000AF000~0x000AFFFF(716800~720895)
                bnameFM98604CEI(716800),
				bnameFM885032CQEI(716801),
				bnameFM885064CQEI(716802),
				bnameFM88614CEI(716803),
				bnameFM685748S6CQEI(716804),
                bnameFM686548S8CQEI(716805),
				bnameFM687048S6CQEI(716806),
				bnameFM687048T6CQEI(716807),
				bnameFMMPUA(716808),
				bnameFMSFU08F(716809),
				bnameFMSFU16F(716810),
				bnameFMSFU04G(716811),
                bnameFMSFU08G(716812),
				bnameFMSFU16G(716813),
				bnameFMCMUA(716814),
				bnameFMCMUB(716815),
				bnameFML18CQFDA(716816),
				bnameFML36CQFD(716817),
				bnameFML36LQFD(716818),
				bnameFML48XSFD(716819),
				bnameFML48XSFDA(716820),
				bnameFM5855E48T4S2Q(716821),
				bnameFM6857E48S6CQ(716822),
				bnameFM6857E48T6CQ(716823),
				bnameFM686548S8CQSI(716824),
				bnameFML36CQFD1(716825),
				bnameFML18CQFD(716826),	
		        bnameFM6865E48S8CQ(716827),				
				bnameFM88684CEI(716828),	
				bnameFM8850E32CQEI(716829),
				bnameFM5855S48T4S2Q(716830),
				bnameFM6857S48S6CQ(716831),
				bnameFMSFU04G1(716832),
                bnameFMSFU08G1(716833),
                bnamePDC2K2S12-PB(716834),
                bnamePDC2K2S12-PF(716835),
                bnamePAC2KS12-PB(716836),
                bnamePAC1K8S12-PF(716837),
                bnameFAN-150C-B(716838),
                bnameFAN-150C-F(716839),
                bnamePIU550W(716840),
                bnameXHMM002FBXC1(716841),
                bnameXHMM002FBXC2(716842),
                bnameXHMM002FBXC7(716843),
-- END
                bnameEND(2147483647)            -- End

                }

        HWSubPCBType ::= TEXTUAL-CONVENTION
            STATUS current
            DESCRIPTION
                "This data type is used as the syntax of the
                hwSubslotType object in the definition of
                HUAWEI-DEVICE-MIB's hwSubslotTable.

                The definition of this textual convention with the
                addition of newly assigned values is published
                periodically by the Huawei MIB Criterion Group, every
                value indicate a SubPCB produced by Huawei.
                "
            SYNTAX INTEGER
                {
                subbnameunknown(1),
                subbnameh511o2ctg(2),           -- Subboard that provides two 155M ATM ports (single-mode 30 km), which is used for MA
                subbnameh511o2ctb(3),           -- Subboard that provides two 155M ATM ports (multi-mode 2 km), which is used for MA
                subbnameh511o1ctg(4),           -- Subboard that provides one 155M ATM port (single-mode 30 km), which is used for MA
                subbnameh511o1ctb(5),           -- Subboard that provides one 155M ATM port (multi-mode 2 km), which is used for MA
                subbnameh511v2ht(6),            -- ARC subboard, which provides two 622M single-mode optical ports
                subbnameh511v1ht(7),            -- ARC subboard, which provides one 622M single-mode optical port and one electric port
                subbnameh512o8ffb(8),           -- Subboard that provides eight 100M Ethernet optical ports (multi-mode 2 km)
                subbnameh512o8fff(9),           -- Subboard that provides eight 100M Ethernet optical ports (single-mode 15 km)
                subbnameh511o1gfa(10),          -- Subboard that provides one GE optical port (multi-mode 500 m)
                subbnameh511o1gfe(11),          -- Unavailable
                subbnameh511o1gfg(12),          -- Unavailable
                subbnameh511o2cpb(13),          -- ATM subboard that provides two STM-1 optical ports (multi-mode, 2 km),which is used for MD
                subbnameh511o2cpg(14),          -- ATM subboard that provides two STM-1 optical ports (single-mode, 30 km), which is used for MD
                subbnameh511o1cpb(15),          -- ATM subboard that provides one STM-1 optical port (multi-mode, 2 km), which is used for MD
                subbnameh511o1cpg(16),          -- ATM subboard that provides one STM-1 optical port (single-mode, 30 km), which is used for MD
                subbnameh511o1hxc(17),          -- ATM subboard that provides one STM-4 optical port (single-mode, long-distance)
                subbnameh511o1hxb(18),          -- ATM subboard that provides one STM-4 optical port (single-mode, medium-distance)
                subbnameh511o1hxa(19),          -- ATM subboard that provides one STM-4 optical port (multi-mode, short-distance)
                subbnameh511e23t(20),           -- Subboard that provides two E3 ATM electric ports
                subbnameh511e13t(21),           -- Subboard that provides one E3 ATM electric port
                subbnameh511t23t(22),           -- Subboard that provides two T3 ATM electric ports
                subbnameh511t13t(23),           -- Subboard that provides one T3 ATM electric port
                subbnameh511o2cvb(24),          -- SDH subboard that provides two STM-1 optical ports (multi-mode 2 km)
                subbnameh511o2cvg(25),          -- SDH subboard that provides two STM-1 optical ports (single-mode, 30 km)
                subbnameh511e8it(26),           -- 8-port IMA subboard
                subbnameh511e81d(27),           -- 8-port E1 subboard
                subbnameh511e8vd(28),           -- 8-port V35 subboard
                subbnameh511s81d(29),           -- 8-port G.SHDSL subboard
                subbnamevc01sdsp(30),           -- VSP subboard

-- 20020619 New
                subbnameh511o1gfx(31),          -- Subboard that provides one GE optical port (single-mode 10 km)
                subbnameh511e8fi(32),           -- E8FI: subboard that provides 8 10M/100M Ethernet electric ports
                subbnameh511o1cvb(33),          -- SDH subboard that provides one STM-1 optical port (multi-mode, 2 km)
                subbnameh511o1cvg(34),          -- SDH subboard that provides one STM-1 optical port (single-mode, 30 km)

-- New IMA subboards of the UA3000
                subbnameh601e8ia(35),           -- Subboard that provides eight IMA E1 electric ports
                subbnameh601o1cng(36),          -- Subboard that provides one 155M, ATM, single-mode, and 30 km optical port (SC)
                subbnameh601o1cnb(37),          -- Subboard that provides one 155M, ATM, multi-mode, and 2 km optical port (SC)
                subbnameh601o2cng(38),          -- Subboard that provides two 155M, ATM, single-mode, and 30 km optical ports (SC)
                subbnameh601o2cnb(39),          -- Subboard that provides two 155M, ATM, multi-mode, and 2 km optical ports (SC)
                                                -- New subboards of the IAS
                subbnameh511e1ct(40),           -- Subboard that provides one 155M ATM electric port
                subbnameh511e2ct(41),           -- Subboard that provides two 155M ATM electric ports
                subbnameh531o1gaa(42),          -- Subboard that provides one GE multi-mode optical port
                subbnameh531o2gaa(43),          -- Subboard that provides two GE multi-mode optical ports
                subbnameh531o1gae(44),          -- Subboard that provides one GE single-mode optical port
                subbnameh531o2gae(45),          -- Subboard that provides two GE multi-mode optical ports
                subbnameh531e4fb(46),           -- Subboard that provides four 10M/100M Ethernet electric ports-for BASE
                subbnameh53104fbf(47),          -- Subboard that provides four 10M/100M Ethernet optical ports (single-mode 15 km, LC interface)-for BASA and BASE
                subbnameh53104fbb(48),          -- Subboard that provides four 10M/100M Ethernet optical ports (multi-mode 2 km, LC interface)-for BASA and BASE
-- MA5200
                subbnameaim1(50),
                subbnameaim2(51),
                subbnameaim3(52),
                subbnameaim4(53),
                subbnamepim1(54),
                subbnamepim2(55),
                subbnamepim3(56),
                subbnamepim4(57),
                subbnameh521E6FC(58),           -- 6-channel electric interface Subboard of speediness Ethernet
                subbnameh521O6FCSMTRJ(59),      -- Single-mode 6-channel MTRJ optical interface Subboard of speediness Ethernet
                subbnameh521O6FCMMTRJ(60),      -- Multi-mode 6-channel MTRJ optical interface Subboard of speediness Ethernet
                subbnameh521O6FCSLC(61),        -- Single-mode 6-channel LC optical interface of speediness Ethernet
                subbnameh521O1GCSMTRJ(62),      -- Single-mode 1-channel Gigabit MTRJ optical interface Subboard of speediness Ethernet
                subbnameh521O1GCMMTRJ(63),      -- Multi-mode 1-channel Gigabit MTRJ optical interface Subboard of speediness Ethernet
                subbnameh521O1GCSLC(64),        -- Single-mode 1-channel Gigabit LC optical interface Subboard of speediness Ethernet
                subbnameh521O1GCMLC(65),        -- Multi-mode 1-channel Gigabit LC optical interface Subboard of speediness Ethernet
                subbnameh521O2GCSMTRJ(66),      -- Single-mode 2-channel Gigabit MTRJ optical interface Subboard of speediness Ethernet
                subbnameh521O2GCMMTRJ(67),      -- Multi-mode 2-channel Gigabit MTRJ optical interface Subboard of speediness Ethernet
                subbnameh521O2GCSLC(68),        -- Single-mode 2-channel Gigabit LC optical interface Subboard of speediness Ethernet
                subbnameh521O2GCMLC(69),        -- Multi-mode 2-channel Gigabit LC optical interface Subboard of speediness Ethernet
                subbnameh521EGCSTKC(70),        -- Gigabit electric interface piling Subboard of Ethernet
                subbnameh521OGCSTKC(71),        -- Gigabit electric interface piling Subboard of Ethernet
                subbnameh521P1CCOC3(72),        -- 155M POS Subboard
                subbnameh521P1HCOC12(73),       -- 622M POS Subboard
-- ESR SubCard Type
                subbnameAtm155(130) ,           -- Include ATM155 and ATM155A.
                subbnameAtm622(131) ,           -- Include ATM622 and ATMA622.
                subbnamePos155 (132) ,          -- ESR not support by now, reserved for future.
                subbnamePos622(133) ,           -- BS22P2HA
                subbnameO2cc   (134) ,          -- Board subCard of CES(Circuit Emluator System ),Serial number:BS22O2CC
                subbnameE43a(135) ,             -- Realize ATM accessing of E3,Serial number:BS21E43A
                subbnameE8fi (136) ,            -- SN01E8FI
                subbnameO8fi (137) ,            -- SN01O8FI
                subbnameO1gi (138) ,            -- SN01O1GI
                subbnameE8f(139),               -- BS22E8FA/BS22E8FB electric port FE subcard   BS22LPUD subcard
                subbnameO8f (140) ,             -- BS22O8FA/BS22O8FB optical port FE subcard   BS22LPUD subcard
                subbnameO1g (141) ,             -- BS22O1GA,                        BS22LPUC subcard
                subbnameO2g (142) ,             -- BS22O2GA,BS22O2GB                BS22LPUC subcard
                subbnameO8g (143) ,             -- BS22O8GA                         BS22LPUC subcard
                subbnameAtm2g5(144) ,           -- Subboard that provides the 2.5G ATM access and can be inserted only in the LPUB.
                                                -- Its number is BS22O1SC (BS22LPUB subcard).
                subbnameBfm(145),               -- BS22BFMA, based on 01G; BS22BFMB, based on 02G
                subbnameh601e23a(146),          -- Subboard that provides two E3 ATM electric ports
                subbnameh601e13a(147),          -- Subboard that provides one E3 ATM electric port
-- New subboards for the LAND board
                subbnameH511o1GTG(148),         -- Subboard that provides one 1000M optical port (single-mode, 40 km, 1550nm) for the LAND board
-- VPRING subboards
                subbnameh511v2htg(151),         -- H511V2HTG VPRING subboard that provides two 622M optical ports (single-mode, 40 km, and SC interface)
                subbnameh511v1htg(152),         -- H511V1HTG VPRING subboard that provides one 622M optical port (single-mode, 40 km, SC interface)
                subbnameh511v2htb(153),         -- H511V2HTB VPRING subboard that provides two 622M optical ports (multi-mode, 2 km, and SC interface)
                subbnameh511v1htb(154),         -- H511V1HTB VPRING subboard that provides one 622M optical port (multi-mode, 2 km, and SC interface)
                subbnameh601v2haf(155),         -- H601V2HAF VPRING subboard that provides two 622M optical ports (single-mode, 15 km, and SC interface)
                subbnameh601v1haf(156),         -- H601V1HAF VPRING subboard that provides one 622M optical port (single-mode, 15 km, and SC interface)
                subbnameh601v2hag(157),         -- H601V2HAG VPRING subboard that provides two 622MM optical ports (single-mode, 40 km, and SC interface)
                subbnameh601v1hag(158),         -- H601V1HAG VPRING subboard that provides one 622M optical port (single-mode, 40 km, and SC interface)
                subbnameh601v2hab(159),         -- H601V2HAB VPRING subboard that provides two 622M optical ports (multi-mode, 2 km, and SC interface)
                subbnameh601v1hab(160),         -- H601V1HAB VPRING subboard that provides one 622M optical port (multi-mode, 2 km, and SC interface)
                subbnameh601cesa(165),          -- Subboard that provides eight IMA El electric ports
                subbnameh601v2ha(166),          -- Subboard that provides one 155M ATM optical port (single-mode, 30 km, and SC interface) //to be aborted
-- Subboards for the LAND board
                subbnameLande8fs(167),
                subbnameLando8fsb(168),
                subbnameLando8fsf(169),
                subbnameLando8fsg(170),
                subbnameLando4fsb(171),
                subbnameLando4fsf(172),
                subbnameLando4fsg(173),
                subbnameLando1gta(174),
                subbnameLando1gtf(175),
                subbnameLando1gth(176),
                subbnameh512e81d(177),
                subbnameLando2fsb(178),         -- Subboard that provides two 100M optical ports (multi-mode)
                subbnameLando2fsf(179),         -- Subboard that provides two 100M optical ports (single-mode, 15 km, and 1310 nm)
                subbnameLando2fsg(180),         -- Subboard that provides two 100M optical ports (single-mode, 40 km, and 1310 nm)
                subbnameLando1fsb(181),         -- Subboard that provides one 100M optical port (multi-mode)
                subbnameLando1fsf(182),         -- Subboard that provides one 100M optical port (single-mode, 15 km, and 1310 nm)
                subbnameLando1fsg(183),         -- Subboard that provides one 100M optical port (single-mode, 40 km, and 1310 nm)
-- 622M ATM subboard
                subbnamebs22o1hda(184),         -- ATM subboard that is based on the SD537 chipset and provides one 622M optical port (multi-mode, 0.5 km)
                subbnamebs22o1hdb(185),         -- ATM subboard that is based on the SD537 chipset and provides one 622M optical port
                                                -- (single-mode, medium-distance, 15 km)
                subbnamebs22o1hdc(186),         -- ATM subboard that is based on the SD537 chipset and provides one 622M optical port
                                                -- (single-mode, long-distance, and 40 km)
                subbnameH601e2fn(187),          -- Subboard that provides two 10M/100M Ethernet electric ports
                subbnameH601o2fnf(188),         -- Subboard that provides two 10M/100M Ethernet optical ports (single-mode, 15 km, 1310 nm, and LC interface)
                subbnameH601o2fnb(189),         -- Subboard that provides two 10M/100M Ethernet optical ports (multi-mode, 2 km, 1310 nm, and LC interface)
                subbnameH601o1fnf(190),         -- Subboard that provides one 10M/100M Ethernet optical port (single-mode, 15 km, 1310 nm, and LC interface)
                subbnameH601o1fnb(191),         -- Subboard that provides one 10M/100M Ethernet optical port (multi-mode, 2 km, 1310 nm, and LC interface)
                subbnameH601o1gne(192),         -- Subboard that provides one GE optical port (single-mode, 10 km, 1310 nm, and LC interface)
                subbnameH601o1gna(193),         -- Subboard that provides one GE optical port (multi-mode, 500 m, 850 nm, and LC interface)
                subbnameH601o1gng(194),         -- Subboard that provides one GE optical port (single-mode, 40 km, 1510 nm, and LC interface)
-- VPU subboards
                subbnamevpuh511etca(195),       -- VPU DSP 160-channel subboard
                subbnamevpuh511etcb(196),       -- VPU DSP 600-channel subboard
                subbnamevpuh511e2fn(197),       -- Subboard for the VPU board. This subboard provides two FE electric ports.
                subbnamevpuh511o2fnb(198),      -- Subboard for the VPU board. This subboard provides two FE optical ports.
                subbnamevpuh511o1gna(199),      -- Subboard for the VPU board. This subboard provides the FE electric port and the GE port.
-- Subboards for the MSUC board
                subbnameH511O1CSB(200),         -- Subboard for the MSUC board. This subboard provides one 155M optical port (SDH, multi-mode, and 2 km).
                subbnameH511O1CSF(201),         -- Subboard for the MSUC board. This subboard provides one 155M optical port (SDH, single-mode, and 15 km).
                subbnameH511O1CSG(202),         -- Subboard for the MSUC board. This subboard provides one 155M optical port (SDH, single-mode, and 40 km).
                subbnameH511E1CS(203),          -- Subboard for the MSUC board. This subboard provides one 155M SDH electric port.

-- Subboards for the VPU board
                subbnamevpuh511e1fn(204),       -- Subboard for the VPU board. This subboard provides one 10M/100M Ethernet electric port.
                subbnamevpuh511o2fnf(205),      -- Subboard for the VPU board. This subboard provides two 100M Ethernet optical ports (single-mode, 15 km).
                subbnamevpuh511o1fnb(206),      -- Subboard for the VPU board. This subboard provides one 100M Ethernet optical port (multi-mode, 2 km).
                subbnamevpuh511o1fnf(207),      -- Subboard for the VPU board. This subboard provides one 100M Ethernet optical port (single-mode, 15 km).
                subbnamevpuh511o1gne(208),      -- Subboard for the VPU board. This subboard provides one 1000M Ethernet optical port (single-mode, 10 km).
                subbnamevpuh511o1gng(209),      -- Subboard for the VPU board. This subboard provides one 1000M Ethernet optical port (single-mode, 40 km).

-- 155M ATM optical subboards
                subbnameH601O2CNH(210),         -- UA subboard H601O2CNH, which provides two 155M ATM optical ports (single-mode, 60 km)
                subbnameH601O1CNH(211),         -- UA subboard H601O1CNH, which provides one 155M optical port (single-mode, 60 km)
                subbnameH511O2CPH(212),         -- Subboard H511O2CPH, which provides two 155M optical ports (single-mode, 60 km)
                subbnameH511O1CPH(213),         -- Subboard H511O1CPH, which provides one 155M optical port (single-mode, 60 km)
                subbnameH511O2CPI(214),         -- Subboard H511O2CPI, which provides two 155M optical ports (single-mode, 90 km)
-- UA VPRING subboards
                subbnameH602V2HAF(215),         -- VPRING subboard H602V2HAF, which provides two 622M optical ports (single-mode, 15 km, SC interface, and SD537 chipset)
                subbnameH602V1HAF(220),         -- VPRING subboard H602V1HAF, which provides one 622M optical port (single-mode, 15 km, SC interface, and SD537 chipset)
                subbnameH602V2HAG(221),         -- VPRING subboard H602V2HAG, which provides two 622M optical ports (single-mode, 40 km, SC interface, and SD537 chipset)
                subbnameH602V1HAG(222),         -- VPRING subboard H602V1HAG, which provides one 622M optical port (single-mode, 40 km, SC interface, and SD537 chipset)
                subbnameH602V1HTF(223),         -- VPRING subboard H602V1HTF, which provides one 622M optical port (single-mode, 15 km, SC interface,
                                                -- SD537 chipset, and interconnected electric ports)
                subbnameH602V1HTG(224),         -- VPRING subboard H602V1HTG, which provides one 622M optical port (single-mode, 40 km, SC interface,
                                                -- SD537 chipset, and interconnected electric ports)

                subbnameH602V2HCF(225),         -- VPRING subboard H602V2HCF, which provides two 622M optical ports
                                                -- (single-mode, 15 km, SC interface, stratum-3 clock, and SD537 chipset)
                subbnameH602V1HCF(226),         -- VPRING subboard H602V1HCF, which provides one 622M optical port
                                                -- (single-mode, 15 km, SC interface, stratum-3 clock, and SD537 chipset)
                subbnameH602V2HCG(227),         -- VPRING subboard H602V2HCG, which provides two 622M optical ports
                                                -- (single-mode, 40 km, SC interface, SD537 chipset, and stratum-3 clock)
                subbnameH602V1HCG(228),         -- VPRING subboard H602V1HCG, which provides one 622M optical port
                                                -- (single-mode, 40 km, SC interface, SD537 chipset, and stratum-3 clock)
                subbnameH602V1HEF(229),         -- VPRING subboard H602V1HEF, which provides one 622M optical port
                                                -- (single-mode, 15 km, SC interface, SD537 chipset, interconnected electric ports, and stratum-3 clock)
                subbnameH602V1HEG(230),         -- VPRING subboard H602V1HEG, which provides one 622M optical port
                                                -- (single-mode, 40 km, SC interface, SD537 chipset, interconnected electric ports, and stratum-3 clock)


-- 8070
                subbnameRTC1ETPA(300),          -- Ethernet process card
                subbnameRTC1ETKA(301),          -- Ethernet back card
                subbnameRTC1ETKX(302),          -- Ethernet back card(fiber)
                subbnameRTC1GEM(303),           -- GE process card(fiber)
                subbnameRTC1GEPA(304),          -- GE process card
                subbnameRTC1GEKA(305),          -- GE back card(A)
                subbnameRTC1GEKB(306),          -- GE back card(B)
                subbnameRTC1GEKC(307),          -- GE back card(C)
                subbnameRTC1GEKD(308),          -- GE back card(D)
                subbnameRTC1GEPT(309),          -- GE process card(copper)
                subbnameRTC1SAPA(310),          -- 4SA process card
                subbnameRTC1SAKA(311),          -- 4SA back card
                subbnameRTC1POPA(312),          -- POS process card
                subbnameRTC1POK(313),           -- POS back card
                subbnameRTC2POPB(314),          -- POS++ process card
                subbnameRTC1CPOP(315),          -- CPOS process card
                subbnameRTC1CPOB(316),          -- CPOS process card that supports t1
                subbnameRTC1PAK(317),           -- CPOS/POS++ /8236 ATM back card
                subbnameRTC1ATPA(318),          -- 8230 ATM process card
                subbnameRTC1ATK(319),           -- 8230 ATM back card
                subbnameRTC1ATPB(320),          -- 8236 ATM process card
                subbnameRTC1T8IP(321),          -- 8-port T1 ATM process card
                subbnameRTC18TKA(322),          -- 8-port T1 ATM back card
                subbnameRTC18TKB(323),          -- 8-port T1 ATM back card
                subbnameRTC1E8IP(324),          -- 8-port E1 ATM process card
                subbnameRTC18EKA(325),          -- 8-port E1 ATM back card
                subbnameRTC18EKB(326),          -- 8-port E1 ATM back card
                subbnameRTC1ATSP(327),          -- 1-port ATM T3 process card
                subbnameRTC1CT3K(328),          -- 1-port ATM T3 back card
                subbnameRTC1AESP(329),          -- 1-port ATM E3 process card
                subbnameRTC1CE3K(330),          -- 1-port ATM E3 back card
                subbnameRTC1ATDP(331),          -- 2-port ATM T3 process card
                subbnameRTC1T3DK(332),          -- 2-port ATM T3 back card
                subbnameRTC1AEDP(333),          -- 2-port ATM E3 process card
                subbnameRTC1E3DK(334),          -- 2-port ATM E3 back card
                subbnameRTC1ATHP(335),          -- 622M ATM  process card
                subbnameRTC1PAHA(336),          -- 622M ATM back card
                subbnameRTC1PAHB(337),          -- 622M ATM back card
                subbnameRTC1PAHC(338),          -- 622M ATM back card
                subbnameRTC1CEPA(339),          -- 4-port CE1/e1 process card
                subbnameRTC14EPB(340),          -- 4-port CE1/e1 process card
                subbnameRTC14CEP(341),          -- 4-port CE1/e1 process card
                subbnameRTC1QEKA(342),          -- 4-port CE1/e1 back card
                subbnameRTC14EKA(343),          -- 4-port CE1/e1 back card
                subbnameRTC14EKB(344),          -- 4-port CE1/e1 back card
                subbnameRTC18EPA(345),          -- 8-port CE1/e1 process card
                subbnameRTC18EPB(346),          -- 8-port CE1/e1 process card
                subbnameRTC18CEP(347),          -- 8-port CE1/e1 process card
                subbnameRTC1E3PA(348),          -- E3 process card
                subbnameRTC1E3DP(349),          -- 2E3 process card
                subbnameRTC1CE3P(350),          -- CE3 process card
                subbnameRTC18TPA(351),          -- 8T1 process card
                subbnameRTC18TPB(352),          -- 8T1 process card
                subbnameRTC18CTP(353),          -- 8T1 process card
                subbnameRTC1T3PA(354),          -- T3 process card
                subbnameRTC1T3DP(355),          -- 2T3 process card
                subbnameRTC1CT3P(356),          -- CT3 process card
                subbnameRTC1CFPA(357),          -- flash card front
                subbnameRTC1FEPA(358),          -- FETH card front
                subbnameIMUETHP(359),           -- imu-eth card front
                subbnameIMUETHK(360),           -- imu-eth card back
                subbnameIMUGEOP(361),           -- imu-geo card front
                subbnameIMUGEOK(362),           -- imu-geo card back
                subbnameIMUGEEP(363),           -- imu-gee card front
                subbnameIMUGEEK(364),           -- imu-gee card back
                subbnameRTC14CTP(365),          -- NE05/08/16E:4t1 front
                subbnameRTC14TKA(366),          -- NE05/08/16E:4t1 back
                subbnameRTC1CPOC(367),          -- NE05/08/16E:CPOC front
-- 8011
                subbnameCR01P4CM(400),          -- For NE80 & NE40, daughter card with 4 155M POS multimode optical port at 1300nm wavelength
                subbnameCR01P4CS(401),          -- For NE80 & NE40, daughter card with 4 155M POS singlemode optical port at 1300nm wavelength (10-15km)
                subbnameCR01P1HM(402),          -- For NE80 & NE40, daughter card with 1 622M POS multimode optical port at 1300nm wavelength
                subbnameCR01P1HS(403),          -- For NE80 & NE40, daughter card with 1 622M POS singlemode optical port at 1300nm wavelength (10-15km)
                subbnameCR01P1UZ(404),          -- For NE80 & NE40, daughter card with 1 2.5G POS singlemode optical port at 1300nm wavelenght (2km)
                subbnameCR01P1US(405),          -- For NE80 & NE40, daughter card with 1 2.5G POS singlemode optical port at 1300nm wavelength (10-15km)
                subbnameCR01P1UL(406),          -- For NE80 & NE40, daughter card with 1 2.5G POS singlemode optical port at 1300nm wavelength (40km)
                subbnameCR01P1UV(407),          -- For NE80 & NE40, daughter card with 1 2.5G POS singlemode optical port at 1300nm wavelength (70km)
                subbnameCR01P1RZ(408),          -- For NE80 & NE40, daughter card with 1 2.5G channelized POS singlemode optical port at 1300nm wavelength (2km)
                subbnameCR01P1RS(409),          -- For NE80 & NE40, daughter card with 1 2.5G channelized POS singlemode optical port at 1300nm wavelength (10-15km)
                subbnameCR01P1RL(410),          -- For NE80 & NE40, daughter card with 1 2.5G channelized POS singlemode optical port at 1300nm wavelength (40km)
                subbnameCR01P1RV(411),          -- For NE80 & NE40, daughter card with 1 2.5G channelized POS singlemode optical port at 1300nm wavelength (70km)
                subbnameCR01P4HM(412),          -- For NE80 & NE40, daughter card with 4 622M POS multimode optical port at 1300nm wavelength
                subbnameCR01P4HS(413),          -- For NE80 & NE40, daughter card with 4 622M POS singlemode optical port at 1300nm wavelength (10-15km)
                subbnameCR01A8CM(414),          -- For NE80 & NE40, daughter card with 8 155M ATM multimode optical port at 1300nm wavelength
                subbnameCR01A8CS(415),          -- For NE80 & NE40, daughter card with 8 155M ATM singlemode optical port at 1300nm wavelength (10-15km)
                subbnameCR01R1UZ(416),          -- For NE80 & NE40, daughter card with 1 2.5G RPR singlemode optical port at 1300nm wavelength (2km)
                subbnameCR01R1US(417),          -- For NE80 & NE40, daughter card with 1 2.5G RPR singlemode optical port at 1300nm wavelength (10-15km)
                subbnameCR01R1UL(418),          -- For NE80 & NE40, daughter card with 1 2.5G RPR singlemode optical port at 1300nm wavelength (40km)
                subbnameCR01R1UV(419),          -- For NE80 & NE40, daughter card with 1 2.5G RPR singlemode optical port at 1300nm wavelength (70km)
                subbnameCR01C2CF(420),          -- For NE80 & NE40, daughter card with 2 155M CPOS optical port (include SFP module)
                subbnameCR01C4CF(421),          -- For NE80 & NE40, daughter card with 4 155M CPOS optical port (include SFP module)
                subbnameCR01EGFE(422),          -- For NE80 & NE40, daughter card with 16 FE port
                subbnameCR01EGFM(423),          -- For NE80 & NE40, daughter card with 16 FE multimode optical port at 1300nm wavelength
                subbnameCR01EGFS(424),          -- For NE80 & NE40, daughter card with 16 FE singlemode optical port at 1300nm wavelength (10-15km)
                subbnameCR01E2GP(425),          -- For NE80 & NE40, daughter card with 2 GE multimode optical port at 850nm wavelength
                subbnameCR01E2GS(426),          -- For NE80 & NE40, daughter card with 2 GE singlemode optiacl port at 1300nm (10-15km)
                subbnameCR01E2GQ(427),          -- For NE80 & NE40, daughter card with 2 GE singlemode optical port at 1550nm (40km)
                subbnameCR01E2GV(428),          -- For NE80 & NE40, daughter card with 2 GE singlemode optical port at 1300nm (70km)
                subbnameCR01E4GC(429),          -- For NE80 & NE40, daughter card with 4 GE optical port (include GIBC module)
                subbnameCR01E8FB(430),          -- For NE80 & NE40, daughter card with 8 FE electronic/optical port
                subbnameUR01A1CFF(431),
                subbnameUR01A2CFF(432),
                subbnameUR01A4CFF(433),
                subbnameUR01A8CFF(434),
                subbnameCR01A8CFF(435),
                subbnameCR01A4CFF(436),
                subbnameCR01SPUA(437),
                subbnameCR01SPUB(438),
                subbnameCR01SPUC(439),
                subbnameCR018CT1(440),
                subbnameCR01C1CF(441),
         -- New subboards for the SCUA board
               subbnameH511L24GA(450),      -- LAN switch subboard that provides two 5695s and 24 GE channels
               subbnameH511L12GA(451),      -- LAN switch subboard that provides one 5695 and 12 GE channels
               subbnameH511L02GA(452),      -- SERDES PHY subboard that provides two GE ports
               subbnameH511L02FA(453),      -- PHY subboard that provides two FE optical ports
               subbnameH511L02FE(454),          -- PHY subboard that provides two FE electric ports

        --New subboards for the IPMB board
               subbnameH601O2GNE(459),      -- Subboard that provides two GE optical ports (1310 nm, single-mode, 10 km, and LC interface)
               subbnameH601O2GNA(460),      -- Subboard that provides two GE optical ports (850 nm, multi-mode, 500 m, and LC interface)
               subbnameH601O2GNG(461),           -- Subboard that provides two GE optical ports (1510 nm, single-mode, 40 km, and LC interface

-- New subboards for the VPU board
               subbnamevpuh511O1FNG(462),      -- Subboard that provides one 100M Ethernet optical port (single-mode, 40 km)
               subbnamevpuh511O2FNG(463),      -- Subboard that provides two 100M Ethernet optical ports (single-mode, 40 km)
               subbnamevpuh511O2FNI(464),      -- Subboard that provides two 100M Ethernet optical ports (single-mode, 80 km)
               subbnamevpuh511O1GNI(465),      -- Subboard that provides one 1000M Ethernet optical port (single-mode, 80 km)
               subbnamevpuh511O1GNT(466),      -- Subboard that provides one 1000M Ethernet optical port (single-mode, 40 km)
-- A8010
                subbnameCkmb(65536),            -- CKMB: clock subboard
                subbnameP2ci(65537),            -- P2CI :subboard that provides two POS optical ports
                subbnameCsma(65538),            -- CSMA: CSM/six-chip DSP subboard
                subbnameCsmb(65539),            -- CSMB: CSM/12-M80310 chip DSP subboard
                subbnameCsmc(65540),            -- CSMC: Mapletree-chip DSP subboard
                subbnameCsmd(65541),            -- CSMD: CSM/12-M80320chip DSP subboard
                subbnameCkma(65542),            -- CKMA0: SDH&TDM clock subboard
                subbnameCkmc(65543),            -- CKMC0: TDM clock module (r002)
                subbnameO8fib(65544),           -- 08FIB: subboard that provides eight 100M Ethernet optical ports (multi-mode, 2 km)
                subbnameO8fif(65545),           -- 08FIF: subboard that provides eight 100M Ethernet optical ports (single-mode, 15 km)
                subbnameO1gie(65546),           -- 01GIE: subboard that provides one GE optical port (single-mode, 10 km)
                subbnameO1gig(65547),           -- 01GIG: subboard that provides one GE optical port (single-mode, 40 km)
                subbnameO1gii(65548),           -- 01GII: subboard that provides one GE optical port (single-mode, 70 km)
                subbnameO1gia(65549),           -- 01GIA: subboard that provides one GE optical port (multi-mode, 500 m)
                subbnameOgfib(65550),           -- 0GFIB: subboard that provides 16 100M Ethernet optical ports (multi-mode, 2 km)
                subbnameOgfif(65551),           -- 0GFIF: subboard that provides 16 100M Ethernet optical ports (single-mode, 15 km)
                subbnameO2gie(65552),           -- 02GIE: subboard that provides two GE optical ports (single-mode, 10 km)
                subbnameO2gia(65553),           -- 02GIA: subboard that provides two GE optical ports (multi-mode, 500 m)
                subbnameP2cig(65554),           -- P2CIG: subboard that provides two 155M POS optical ports (single-mode, 30 km)
                subbnameP2cib(65555),           -- P2CIB: subboard that provides two 155M POS optical ports (multi-mode, 2 km)
                subbname8efi(65556),            -- E8FI: subboard that provides 8 10M/100M Ethernet electric ports
                subbnameO2cib(65557),           -- 02CIB: subboard that provides two 155M ATM optical ports (multi-mode, 2 km)
                subbnameO2cig(65558),           -- 02CIG: subboard that provides two 155M ATM optical ports (single-mode, 30 km)
                subbnameE2ai(65559),            -- E2AI: subboard that provides two E3/T3 ATM electric ports   FRB
                subbnameE8vd(65560),            -- E8VD: subboard that provides eight V.35 ports
                subbnameE81d(65561),            -- E81d: subboard that provides eight E1/T1 twisted pairs
                subbnameLdcu(65562),            -- LDCU: LZS data compression unit subboard
                subbnameLiua(65563),            -- LIUA: subboard for the 16-channel E1 line (75 ohms) interface unit
                subbnameLiub(65564),            -- LIUB: subboard for the 16-channel E1 line (120 ohms) interface unit (r002)
                subbnameLiuc(65565),            -- LIUC: subboard for the 16-channel T1 line (100 ohms) interface unit (r002)
                subbnameSelf(65566),            -- Virtual subboard of the board


                subbnameCsme(65568),            -- CSME: CSM/6-chip DSP subboard
                subbnameCsmg(65569),            -- CSMG: 60-channel/12 signal processing subboard (M80310)
                subbnameCsmh(65570),            -- CSMH: 60-channel voice signal processing subboard (M80320)
-- MA5100
                subbnameApc(65836),             -- APC subboard for the IMA board of the MA5105
                subbnameH511O2GS(65837),
                subbnameH511O4GS(65838),
                subbnameH511E2FA(65839),
                subbnameH511O2FS(65840),
-- MA5300
                subbnameMa530016VPSL(65900),    -- 16-channel VDSL voice SPL board of the MA5300. Its BOM is 03024865.
                subbnameMa530024VPSL(65901),    -- 24-channel VDSL voice SPL board of the MA5300
                subbnameMa5300APSL(65902),      -- 48-channel ADSL voice SPL board of the MA5300
                subbnameMa5300FE(65903),        -- 8-port FE board of the MA5300. This board provides four FE multi-mode optical ports and four
                                                -- FE electric ports. Its BOM is 03025505.
                subbnameH531CQTA(65904),        -- Broadband line test subboard of the MA5100 and the MA5300. Its BOM is 03036794.
                subbnameH531O2FAB(65907),       -- Subboard that provides two 10M/100M Ethernet optical ports (multi-mode, 2 km, and LC interface)
                subbnameH53104FAF(65908),       -- Subboard that provides two 10M/100M Ethernet optical ports (single-mode, 15 km, and LC interface)
                subbnameH531O2GAX(65909),       -- Subboard that provides two single-mode and multi-mode GE optical ports. Upstream GE port:
                                                -- single-mode, LC interface, and 10 km. Downstream GE port: multi-mode, LC interface, and 500 m.
                subbnameH531R2HAF(65910),       -- Subboard that provides two 622M RPR optical ports (two 622M ports use one GE port)
                                                -- (single-mode, 15 km, and LC interface)
                subbnameH531R2HAX(65911),       -- Subboard that provides two 622M single-mode RPR optical ports (two 622M ports use one GE port)
                                                -- (15 km, LC interface + one single-mode GE port, LC interface, and 10 km)
                subbnameH531O1FAB(65912),       -- Subboard that provides one FE optical port (multi-mode, LC interface, and 2 km)
                subbnameH531O1FAF(65913),       -- Subboard that provides one FE optical port (single-mode, LC interface, 15 km)
                subbnameH531O1FAG(65914),       -- Subboard that provides one FE optical port (single-mode, LC interface, 40 km)
                subbname5300H531E2GA(65915),        -- Subboard that provides two GE electric ports
                subbnameTD91FEGA(65916),        -- Subboard that provides two GE electric ports and four FE electric ports
-- S3026V
                subbnameLS66GS1UA(65920),       -- 1000M single-mode optical port board (10 km)
                subbnameLS66GM1UA(65921),       -- 1000M multi-mode optical port board (500 m)
                subbnameLS66FS1UA(65922),       -- 100M single-mode optical port board (15 km)
                subbnameLS66FL1U(65923) ,       -- 100M single-mode optical port board (40 km)
                subbnameLS66FM1UA(65924),       -- 100M multi-mode optical port board (2 km)
                subbnameLS66GT1UA(65925),       -- 1000M electric port board
                subbnameLS66ST1U(65926),        -- 1000M overlaid board
                subbnameLS66GZ1UA(65927),       -- 1000M long-distance optical port board (70 km)
                subbnameLS61GL1UA(65928),       -- 1000M medium-distance optical port board (40 km)

-- MA5100
                subbnameH531E2GA(131082),           -- GE electric port board

                subbnameH561M2GA(131083),           --MPLS subboard
                subbnameH561L24GA(131084),          -- LSW subboard of the MA5600. It supports two 5695s and is similar to H511L24GA.
                subbnameH561O4FM(131085),           -- MA5600's subboard that provides four FE optical ports
                subbnameH561O2FM(131086),           -- MA5600's subboard that provides two FE optical ports
                subbnameH561E4GFA(131087),          -- MA5600's subboard that provides four GE electric ports

                --New subboards of the MA5100V3, which house control board ECUA
                subbnameH511LSWA(131090),       -- LAN switch subboard (one 5650), which provides four GE ports and eight FE ports
                subbnameH511LO2GB(131091),      -- PHY subboards
                subbnameH511O3GS(131092),       -- Subboard that provides three GE SFP optical ports
                subbnameH531E4FA(131093),       -- Subboard that provides four FE electric ports
                subbnameH531O4FS(131094),       -- Subboard that provides four FE SFP optical ports

-- MA5200 add definition of sub card type  0x21000(135168) ~ 0x21FFF(139263)
                subbnameH521P4CDM(135168),
                subbnameH521P4CDS(135169),
                subbnameH521P1HDM(135170),
                subbnameH521P1HDS(135171),
                subbnameH521P1UDZ(135172),
                subbnameH521P1UDS(135173),
                subbnameH521P1UDL(135174),
                subbnameH521P1UDV(135175),
                subbnameH521P1RDZ(135176),
                subbnameH521P1RDS(135177),
                subbnameH521P1RDL(135178),
                subbnameH521P1RDV(135179),
                subbnameH521P4HDM(135180),
                subbnameH521P4HDS(135181),
                subbnameCR01C4CF2(135182),
                subbnameCR01C2CF2(135183),
                subbnameH521E16FD(135184),
                subbnameH521O16FDM(135185),
                subbnameH521O16FDS(135186),
                subbnameH521O2GDP(135187),
                subbnameH521O2GDS(135188),
                subbnameH521O2GDQ(135189),
                subbnameH521O2GDV(135190),
                subbnameH521O4GDG(135191),
                subbnameH521O2GD(135192),
                subbnameH521O8FDB(135193),
                subbnameH521E4FD(135194),
                subbnameH5218E1(135195),
                subbnameH521E8FD(135196),
                subbnameH521O8FDM(135197),
                subbnameH521O8FDS(135198),
                subbnameH521O1GDG(135199),
                subbnameH521O2GDG(135200),
                subbnameH521A4CDM(135201),
                subbnameH521A4CDS(135202),
                subbnameH521A8CDM(135203),
                subbnameH521A8CDS(135204),
                subbnameH521A2HDF(135205),
                subbnameH521E8F(135206),
                subbnameH521EGFE(135207),
                subbnameH521E2GF(135208),
                subbnameH521A8CFF(135209),
                subbnameH521A2HFF(135210),
                subbnameH521E3(135211),
                subbnameH521T3(135212),
                subbnameH521E1(135213),
                subbnameH521T1(135214),
                subbnameH522GXCE1T(135215),
                subbnameH522GXCT1T(135216),
                subbnameH5218CE1(135217),
                subbnameH5218CT1(135218),
                subbnameH522P2CFT(135219),
                subbnameH522P4CFT(135220),
                subbnameH522GERPR(135221),
                subbnameH523POS10G(135222),
                subbnameH523GE10GLAN(135223),
                subbnameH523GE10GWAN(135224),
-- MA5600
                subbnameH801O2GS(143360),          -- Subboard that provides two upstream GE optical ports. It is used for the SCUA upstream service.
                subbnameH801O4GS(143361),          -- Subboard that provides four upstream GE optical ports. It is used for the SCUA upstream service.
                subbnameH801O4FS(143362),          -- Subboard that provides four upstream FE optical ports. It is used for the SCUA upstream service.
                subbnameH801E2GA(143363),          -- Subboard that provides two upstream GE electric ports. It is used for the SCUA upstream service.
                subbnameH801O2CS(143364),          -- Swappable subboard that provides two ATM 155M optical ports
                subbnameH801E4GA(143365),          -- Subboard for the H801SCUA board. It provides four electric ports.
                subbnameH801D4GA(143366),          -- H801D4GA: subboard for the control board

                subbnameH801O2FN(143367),          -- Subboard for the H801MCUA board. It provides two FE optical ports and provides the FE upstream service.
                subbnameH801O2GN(143368),          -- Subboard for the H801MCUA board. It provides two GE optical ports and provides the GE upstream service.

                subbnameH801EP1A(143371),          -- EPON upstream subboard, which is used for the MCUA upstream service
                subbnameH801GP1A(143372),          -- GPON upstream subboard, which is used for the MCUA upstream service

                subbnameH561EP1A(145920),          -- Subboard that provides one EPON port
                subbnameH561EP2A(145921),          -- Subboard that provides two EPON ports
                subbnameH561EP4A(145922),           -- Subboard that provides four EPON ports

                subbnameH531O4GS(145923),          -- MA5600's subboard that provides four GE optical ports
                subbnameH561BITS(145924),          -- BITS subboard for the H561AIUG board
                subbnameH822EP1A(145925),          -- Subboard for the H821MCUA board. It provides one EPON port and two GE electric ports.
--ofa5920
                subbnameH801TDMB(145933),          -- OFA5920 TDMoGEM subboard that supports two GPON boards and provides 8 E1 ports
                subbnameH801EH1A(145934),          -- Subboard that provides 16-channel E1/T1 for the TDMoP board
                subbnameH801CKMA(145935),          -- Clock subboard
                subbnameH802CKMA(146037),          -- MA5600T clock subboard:H802CKMA
                subbnameH801FLBA(145938),          -- Voice forwarding logic subboard
                subbnameH801NH1A(145940),          -- TDM subboard for the H801TOPA board
                subbnameH801CSSA(146017),          -- 2-channel STM-1 uplink subboard
                subbnameH801O2CE(146021),          -- 2-channel STM-1 uplink subboard
                subbnameH802GP1A(146022),          -- H801GP1A cost-reduce
                subbnameH801X1HA(146023),          -- Subboard for the H801ETHB board.
                subbnameH801CKMC(146024),          -- Clock subboard for the H801SCUL and H801SCUN board
                subbnameH801M2XA(146025),          -- New subboard for SCUN
                subbnameH801BITSB(146038),         -- Clock subboard for the H801CITD board
                subbnameH801CPCA(204923),          -- Clock subboard for the H801MCUD board.
                subbnameH801CPCB(204933),          -- Clock subboard for the H801MCUD1 board.
                subbnameH801CPCC(204934),          -- Clock subboard for the H801MCUE board.
                subbnameH801CKMD(888891),          -- Clock subboard.

--MA5800
                subbnameH901CKUA(148501),           -- Clock subboard of MA5800 H901MPLB
                subbnameH901CKUB(148502),           -- Clock subboard of MA5800 H901MPLB
                subnameSUBCMC(148511),              -- SUBCMC subboard
                subbnameH901CPCA(148512),           -- Clock subboard of MA5800-X2 H901MPSA
                subbnameH901CPCB(148513),           -- Clock subboard of MA5800-X2 H901MPSC.
                subbnameH901CPCC(148514),           -- Clock subboard of MA5800-X2 H901MPSD..
                subbnameH902CKUB(148515),           -- Clock subboard of MA5800.
                subbnameH902CKUA(148516),           -- Clock subboard of MA5800.
                subbnameReserve17(148517),          -- subboard of MA5800, reserve for support new subboard in old version.
                subbnameH901CKUF(148518),           -- CLock subboard of MA5800.
                subbnameH901OTD1(148519),         -- OTDR subboard of MA5800 H901OTEF.
                subbnameH902CKUF(148520),           -- CLock subboard of MA5800.
                subbnameH901OTD2(148521),           -- OTDR subboard of MA5800 H901OTHF.
                subbnameReserve22(148522),          -- subboard of MA5800, reserve for support new subboard in old version.
                subbnameH901CPCG(148523),           -- Clock subboard of MA5800-X2 H901MPSG.
                subbnameReserve24(148524),          -- subboard of MA5800, reserve for support new subboard in old version.
                subbnameH901CPCDE(148525),          -- Clock subboard of EA5800-X2 H901MPSDE.
                subbnameH903CKUF(148526),           -- CLock subboard of MA5800.
                subbnameHA01CKSA(148527),           -- CLock subboard of MA5800T.
                subbnameH901CPCJ(148528),           -- Clock subboard of MA5800-X2 H901MPSJ.
                subbnameReserve29(148529),          -- subboard of MA5800, reserve for support new subboard in old version.
                subbnameReserve30(148530),          -- subboard of MA5800, reserve for support new subboard in old version.
                subbnameReserve31(148531),          -- subboard of MA5800, reserve for support new subboard in old version.
                subbnameReserve32(148532),          -- subboard of MA5800, reserve for support new subboard in old version.
                subbnameReserve33(148533),          -- subboard of MA5800, reserve for support new subboard in old version.
                subbnameReserve34(148534),          -- subboard of MA5800, reserve for support new subboard in old version.
                subbnameReserve35(148535),          -- subboard of MA5800, reserve for support new subboard in old version.
                subbnameReserve36(148536),          -- subboard of MA5800, reserve for support new subboard in old version.
                subbnameReserve37(148537),          -- subboard of MA5800, reserve for support new subboard in old version.
                subbnameReserve38(148538),          -- subboard of MA5800, reserve for support new subboard in old version.
                subbnameReserve39(148539),          -- subboard of MA5800, reserve for support new subboard in old version.
                subbnameReserve40(148540),          -- subboard of MA5800, reserve for support new subboard in old version.
                subbnameReserve41(148541),          -- subboard of MA5800, reserve for support new subboard in old version.
                subbnameReserve42(148542),          -- subboard of MA5800, reserve for support new subboard in old version.
                subbnameReserve43(148543),          -- subboard of MA5800, reserve for support new subboard in old version.
                subbnameReserve44(148544),          -- subboard of MA5800, reserve for support new subboard in old version.
                subbnameReserve45(148545),          -- subboard of MA5800, reserve for support new subboard in old version.
                subbnameReserve46(148546),          -- subboard of MA5800, reserve for support new subboard in old version.
                subbnameReserve47(148547),          -- subboard of MA5800, reserve for support new subboard in old version.
                subbnameReserve48(148548),          -- subboard of MA5800, reserve for support new subboard in old version.
                subbnameReserve49(148549),          -- subboard of MA5800, reserve for support new subboard in old version.
                subbnameReserve50(148550),          -- subboard of MA5800, reserve for support new subboard in old version.
                subbnameReserve51(148551),          -- subboard of MA5800, reserve for support new subboard in old version.
                subbnameReserve52(148552),          -- subboard of MA5800, reserve for support new subboard in old version.
                subbnameReserve53(148553),          -- subboard of MA5800, reserve for support new subboard in old version.
                subbnameReserve54(148554),          -- subboard of MA5800, reserve for support new subboard in old version.
                subbnameReserve55(148555),          -- subboard of MA5800, reserve for support new subboard in old version.
                subbnameH901TPUA(148601),         -- TPM subboard of MA5800 H902MPLA

-- WA5700:
                subnameBWAE1(155648),             -- E1 subboard for the IDU control board of the BWA
                subnameBWAT1(155649),             -- T1 subboard for the IDU control board of the BWA
                subnameBWAGE(155650),             -- GE subboard for the IDU control board of the BWA
-- MA561X
                subbnameH831EP1A(155651),          -- EPON upstream subboard, which is used for the 561X upstream service
                subbnameH831GP1A(155652),          -- GPON upstream subboard, which is used for the 561X upstream service
                subbnameH831GE1A(155653),          -- GE   upstream subboard, which is used for the 561X upstream service
                subbnameH836ASDA(155654),          --VOIP DSP Subboard H836ASDA
                subbnameH831PSUH(155655),          --Power Subboard

-- MA5612
                subbnameH832EP2A(155656),          -- EPON upstream subboard, which is used for the 561X upstream service +-
                subbnameH833GP2A(155657),          -- GPON upstream subboard, which is used for the 561X upstream service


                subbnameH831UP2A(155658),          -- Auto adapt upstream subboard, which is used for the MDU upstream service
                subbnameH831UP2C(155659),          -- Auto adapt upstream subboard with Clock, which is used for the MDU upstream service
                subbnameH831GR1A(155660),          -- RF upstream subboard, which is used for the MDU upstream service
                subbnameH831UP2D(155661),          -- Auto adapt upstream subboard, which is used for the MA5631(SD5103) upstream service
                subbnameH836ASDM(155662),          --VOIP 128 Tunnel DSP Subboard H836ASDM
                subbnameH832TP2C(155663),          --10G EPON subboard
                subbnameH832TP2D(155664),          --10G EPON subboard
                subbnameH831XP1A(155665),          --10G GPON subboard
-- MA5662
                subbnameH821MODA(155666),          --56K MODEM subboard
                subbnameH821PRCA(155667),          --RFT-C subboard

                subbnameH832TP1C(155668),          --1*10G EPON subboard

-- MA5616
                subbnameASDF(155669),              -- VOIP DSP Subboard H836ASDF
                subbnameVPS(155670),               -- SUPER VECTOR Subboard VPS
                subbnameVPM(156062),               -- SUPER VECTOR Subboard VPM.
                subbnameH831GE4A(155688),          -- 4 GE upstream subboard.
                subbnameVPB(155934),               -- VECTOR Subboard VPB
                subbnameVPD(155949),               -- VECTOR Subboard VPD

-- MA5616A
                subbnameH833XP1A(155935),       -- 10 GPON Subboard
                subbnameH833XP1C(155936),       -- 10 GPON Subboard

-- MA5616
        subbnameVPA(155950),           -- VECTOR Subboard VPA

-- MA5694S
                subbnameH831VD4A(155951),       -- VD4A  Subboard for MA5694S

        subbnameH831UP2E(155952),       -- Auto adapt upstream subboard of MA5633, It supports EQAM
        subbnameH831UP2F(155953),       -- Auto adapt upstream subboard of MA5633, It not supports EQAM
        subbnameHS21PWBB(155954),       -- Virtual power subboard of MA5633
        subbnameHS21MIXB(155955),       -- Virtual mixer subboard of MA5633
        subbnameH822UX1A(155956),       -- 10GXPON subboard    H822UX1A

--MA5878
                subbnameH832XS1C(156044),          --XG-SPON subboard of the MA5878 device.
                subbnameH836ASDB(156048),      -- VOIP DSP Subboard H836ASDB.

--MA5818
                subbnameH831CKMA(156057),   --  Clock subboard of MA5818
                subbnameH836ASDJ(156063),   --  VOIP DSP Subboard H836ASDJ.

-- MA5821A
                subbnameH833XS1A(156061),      -- SD5118V2 XG-SPON subboard.

-- MA5811S
                subbnameH823CUVC(156064),      -- 8SV uplink Subboard of MA5811S-AE16(8SV uplink) device.

-- WLAN
                subbnameWA611POEA(160000),         --Power Subboard of WA611WACA

-- MD
                subbnamebs22o1hdi(200704),         -- ATM subboard that provides one long-distance 622M optical port (single-mode, SD537 chip, 70 km)

-- UA
                subbnameH601O1GNI(204805),       --H601O1GNI: subboard that provides one 1000M Ethernet optical port (single-mode, 80 km)
                subbnameH601O1GNT(204808),       --H601O1GNT: subboard that provides one 1000M Ethernet optical port (single-mode, 40 km, and 1310 nm).
                                                 -- The IPM control board supports this subboard.

-- AG
                subbnameBCM1510(204811),         --Subboard BCM1510, which uses the DSP chip and is attached to the PVM control board
                subbnameVPC1510(204812),         --Subboard VPC1510, which is a voice subboard and is attached to the PVM control board
                subbnameH602ETCA(204813),        --Subboard H602ETCA, which is a voice subboard and is attached to the PVM control board
                subbnameH601ETCA(204814),        --Subboard H601ETCA, which is a voice subboard and is attached to the PVM control board
                subbnameH801ETCA(204815),        --VoIP subboard with the TI chipset
                subbnameH802ETCA(204816),        --VoIP subboard with the MIRO chipset
                subbnameH602ETCB(204818),        --Subboard H602ETCB, which is a double-chip MIRO voice subboard and is attached to the PVM control board
                subbnameH602ETCC(204819),        --Subboard H602ETCC, which is a triple-chip MIRO voice subboard and is attached to the PVM control board


-- UA
                subbnameH601E13F(204820),        --Subboard for the APM or AIU board. It provides one front-access E3 port.
                subbnameH601E23F(204821),        --Subboard for the APM or AIU board. It provides two front-access E3 ports.
                subbnameH601T13F(204822),        --Subboard for the APM or AIU board. It provides one front-access T3 port.
                subbnameH601T23F(204823),        --Subboard for the APM or AIU board. It provides two front-access T3 ports.

                subbnameH601M2GS(204830),        -- MPLS subboard for the IPMP board. It provides four optical ports.


                subbnameH601ETCB(204831),        --Subboard H601ETCB, which is a double-chip TI voice subboard and is attached to the PVM control board
                subbnameH601ETCC(204832),        --Subboard H601ETCC, which is a triple-chip TI voice subboard and is attached to the PVM control board

                subbnameH601O2GNI(204833),       --Subboard that provides two GE optical ports (1550 nm, single-mode, 80 km, and LC interface)
                subbnameH601O2GNT(204834),       --Subboard that provides two GE optical ports (1310 nm, single-mode, 40 km, and LC interface)
                subbnameH602O1GNT(204835),       --Subboard that provides one GE optical port (1310 nm, single-mode, 40 km, and LC interface)
                subbnameH602O1GNI(204836),       --Subboard that provides one 1000M Ethernet optical port (single-mode, 80 km)
                subbnameH601O2FNG(204837),   --Subboard that provides two 100M Ethernet optical ports (single-mode, 40 km)
                subbnameH601O1FNG(204838),       --Subboard that provides one 100M Ethernet optical port (single-mode, 40 km)
                subbnameH601O1FNI(204839),   --Subboard that provides one 100M Ethernet optical port (single-mode, 80 km)
                subbnameH612O2FN(204840),         --Subboard that provides two FE optical ports
                subbnameH61202GN(204841),         --Subboard that provides two GE optical ports

            --tangrong changed for conflictted with  subbnameH612O2FN(204840)
                subbnameH602V1HAI(204842),         -- H602V1HAI: VPRING subboard that provides one 622M optical port (single-mode, 70 km, SC interface, and SD537)

                subbnameH602ETCM( 262144 ),        --Subboard H602ETCM, which is a single-chip MINI voice subboard and is attached to the PVM control board
                subbnameH602ETCN( 262145),         --Subboard H602ETCN, which is a double-chip MINI voice subboard and is attached to the PVM control board
                subbnameH601EO1A(262146),          -- EPON upstream subboard, which is used for the UA5000 upstream service
                subbnameH601GO1A(262147),          -- GPON upstream subboard, which is used for the UA5000 upstream service
                subbnameH601GE2A(262148),          -- GE   upstream subboard, which is used for the UA5000 upstream service
-- NE40&80
                subbname8CE1(528640),         --8 Ports,RJ45,Channelized E1,Flexible Card
                subbnameGCE1(528641),         -- 16-port Channelized E1,RJ45 Interface Line Card
                subbnameE4GS(528642),         -- 4-Port Gigabit Ethernet Optical Interface Line Process Card (MTRJ,Single-mode,10km)
                subbnameE4GP(528643),         -- 4-Port Gigabit Ethernet Optical Interface Line Process Card(MTRJ,Multi-mode,500m)
                subbnameE4GQ(528644),         -- 4-Port Gigabit Ethernet Optical Interface Line Process Card(LC,Single-mode,1550nm,40km)
                subbnameE4GV(528645),         -- 4-Port Gigabit Ethernet Optical Interface Line Process Card (LC,Single-mode,1550nm,70km)
                subbnameP2HM(528646),         -- 2-Port OC-12c/STM-4c POS Optical Interface Line Process Card(SC,Multi-mode,1300nm,500m)
                subbnameP2HS(528647),         -- 2-Port OC-12c/STM-4c POS Optical Interface Line Process Card(SC,Single-mode,1300nm,15km)
                subbnameP8CM(528648),         -- 8-Port OC-3c/STM-1 POS Optical Interface Line Process Card(MTRJ,Multi-mode,2km)
                subbnameP8CS(528649),         -- 8-Port OC-3c/STM-1 POS Optical Interface Line Process Card(MTRJ,Single-mode,15km)
                subbnameE4FE(528650),         --
                subbnameEGFE(528651),         -- 16-Port Fast Ethernet Electrical Interface Line Process Card(RJ45)
                subbnameEGFS(528652),         -- 16-Port Fast Ethernet Optical Interface Line Process Card(MTRJ,Single-mode,15km)
                subbnameEGFM(528653),         -- 16-Port Fast Ethernet Optical Interface Line Process Card(MTRJ,Multi-mode,1300nm,2km)
                subbnameE4GC(528654),         -- 4 Ports Gigabits Ethernet GBIC Interface Line Card_LAN
                subbnameEGFEM(528655),      -- Subboard that provides 16 FE RJ45 electric ports
                subbnameLGFSM(528656),      -- Subboard that provides 16 FE MTRJ optical ports (single-mode, 1300 nm, and 15 km)
                subbnameEGFMM(528657),      -- Subboard that provides 16 FE MTRJ optical ports (multi-mode, 1300 nm, and 2 km)
                subbnameE4GSM(528658),      -- Subboard that provides four GE MTRJ optical ports (single-mode, 1300 nm, and 10 km)
                subbnameE4GPM(528659),      -- Subboard that provides four GE MTRJ optical ports (multi-mode, 850 nm, and 500 m)
                subbnameE4GQM(528660),      -- Subboard that provides four GE optical ports (single-mode, 1550 nm, and 40 km, LC interface)
                subbnameE4GVM(528661),      -- LAN subboard that provides four GE optical ports (single-mode, 1550 nm, 70 km, and LC interface)
                subbnameE4GCM(528662),      -- Subboard that provides four GE ports and supports four hot swappable GBIC optical modules.
                                                -- Currently, the following optical modules are available: 850nm 500m, 1310nm 10km/30km, and 1550nm 70km.
                subbnameE4GEM(528663),      -- Subboard that provides four optical/electro (O/E) auto-sensing ports,
                                                -- and supports the SFP optical port or the RJ45 electric port.
                subbnameEWFEM(528664),      -- Subboard that provides 32 FE electric ports, and supports the MPLS service
                subbnameEGFEF(528665),        -- 16FE_RJ45 Flexible Card
                subbnameP1CFF(528666),        -- 1POS155_SFP Flexible Plug Card
                subbnameP2CFF(528667),        -- 2POS155_SFP Flexible Plug Card
                subbnameP4CFF(528668),        -- 4 Port POS155 SFP Optical Interface Line Process Card
                subbnameE8FF(528669),         -- 8*FE Optical Interface Line Card-SFP
                subbnameE1GFF(528670),        -- 1GE_SFP Flexible Plug Card
                subbnameE2GFF(528671),        -- 2GE_SFP Flexible Plug Card
                subbnameA2HFF(528672),        -- 2-Port OC-12C/STM-4C ATM Optical LC-SFP
                subbname3E3(528673),          -- 3 Ports,SMB,E3,Flexible Card
                subbname3T3(528674),          -- 3 Ports,SMB,T3,Flexible Card
                subbnameE0GFF(528675),        -- NAT Flexible Plug Card
                subbnameETGFF(528676),        -- NATPT Flexible Plug Card
                subbnameSNGFF(528677),        -- NetStream Flexible Plug Card
                subbnameSTGFF(528678),        -- L2TP Flexible Plug Card
                subbnameSGGFF(528679),        -- GRE Flexible Plug Card
                subbname8E1(528680),          -- 8 Ports E1 Interface Line Card_RJ45
                subbnameA2HF(528681),         --
                subbnameEGFEE(528682),        -- 16 Ports FE RJ45 Electrical Interface Line Card_LAN
                subbnameEWFE(528683),         --
                subbnameE4GE(528684),         --
                subbnameEGFSM(528685),        -- 16*FE 1300nm15km-MTRJ
                subbnameR1UF(528686),         -- 1*OC-48c/STM-16c RPR-SFP Optical Interface Line Card
                subbnameN2GB(528687),         -- Netstream
                subbnameP4CM(528688),         -- For NE80 & NE40, daughter card with 4 155M POS multimode optical port at 1300nm wavelength
                subbnameP4CS(528689),         -- For NE80 & NE40, daughter card with 4 155M POS singlemode optical port at 1300nm wavelength (10-15km)
                subbnameP1HM(528690),         -- For NE80 & NE40, daughter card with 1 622M POS multimode optical port at 1300nm wavelength
                subbnameP1HS(528691),         -- For NE80 & NE40, daughter card with 1 622M POS singlemode optical port at 1300nm wavelength (10-15km)
                subbnameP1UZ(528692),         -- For NE80 & NE40, daughter card with 1 2.5G POS singlemode optical port at 1300nm wavelenght (2km)
                subbnameP1US(528693),         -- For NE80 & NE40, daughter card with 1 2.5G POS singlemode optical port at 1300nm wavelength (10-15km)
                subbnameP1UL(528694),         -- For NE80 & NE40, daughter card with 1 2.5G POS singlemode optical port at 1300nm wavelength (40km)
                subbnameP1UV(528695),         -- For NE80 & NE40, daughter card with 1 2.5G POS singlemode optical port at 1300nm wavelength (70km)
                subbnameP1RZ(528696),         -- For NE80 & NE40, daughter card with 1 2.5G channelized POS singlemode optical port at 1300nm wavelength (2km)
                subbnameP1RS(528697),         -- For NE80 & NE40, daughter card with 1 2.5G channelized POS singlemode optical port at 1300nm wavelength (10-15km)
                subbnameP1RL(528698),         -- For NE80 & NE40, daughter card with 1 2.5G channelized POS singlemode optical port at 1300nm wavelength (40km)
                subbnameP1RV(528699),         -- For NE80 & NE40, daughter card with 1 2.5G channelized POS singlemode optical port at 1300nm wavelength (70km)
                subbnameP4HM(528700),         -- For NE80 & NE40, daughter card with 4 622M POS multimode optical port at 1300nm wavelength
                subbnameP4HS(528701),         -- For NE80 & NE40, daughter card with 4 622M POS singlemode optical port at 1300nm wavelength (10-15km)
                subbnameA8CM(528702),         -- For NE80 & NE40, daughter card with 8 155M ATM multimode optical port at 1300nm wavelength
                subbnameA8CS(528703),         -- For NE80 & NE40, daughter card with 8 155M ATM singlemode optical port at 1300nm wavelength (10-15km)
                subbnameR1UZ(528704),         -- For NE80 & NE40, daughter card with 1 2.5G RPR singlemode optical port at 1300nm wavelength (2km)
                subbnameR1US(528705),         -- For NE80 & NE40, daughter card with 1 2.5G RPR singlemode optical port at 1300nm wavelength (10-15km)
                subbnameR1UL(528706),         -- For NE80 & NE40, daughter card with 1 2.5G RPR singlemode optical port at 1300nm wavelength (40km)
                subbnameR1UV(528707),         -- For NE80 & NE40, daughter card with 1 2.5G RPR singlemode optical port at 1300nm wavelength (70km)
                subbnameC2CF(528708),         -- For NE80 & NE40, daughter card with 2 155M CPOS optical port (include SFP module)
                subbnameC4CF(528709),         -- For NE80 & NE40, daughter card with 4 155M CPOS optical port (include SFP module)
                subbnameE2GP(528710),         -- For NE80 & NE40, daughter card with 2 GE multimode optical port at 850nm wavelength
                subbnameE2GS(528711),         -- For NE80 & NE40, daughter card with 2 GE singlemode optiacl port at 1300nm (10-15km)
                subbnameE2GQ(528712),         -- For NE80 & NE40, daughter card with 2 GE singlemode optical port at 1550nm (40km)
                subbnameE2GV(528713),         -- For NE80 & NE40, daughter card with 2 GE singlemode optical port at 1300nm (70km)
                subbnameE8FB(528714),         -- For NE80 & NE40, daughter card with 8 FE electronic/optical port
                subbnameA1CFF(528715),        -- 1-port STS-3C/STM-1 ATM SFP Optical Interface Flexible Plug Card
                subbnameA2CFF(528716),        -- 2-port STS-3C/STM-1 ATM SFP Optical Interface Flexible Plug Card
                subbnameA4CFF(528717),        -- 4 Ports STS-3C/STM-1 ATM SFP Optical Interface Line Card
                subbnameA8CFF(528718),        -- 8-port STS-3C/STM-1 ATM SFP Optical Interface Flexible Plug Card
                subbname8CT1(528719),         --
                subbnameC1CF(528720),         -- 1-Port Channelized OC-3/STM-1 to DS0 SFP Optical Interface Line Card
                subbnameE8FEF(528721),        -- 8FE_RJ45 Flexible Card
                subbnameP1HF(528722),         --
                subbnameEWFEE(528723),        -- 32 Ports FE RJ45 Electrical Interface Line Card
                subbnameEGFT(528724),         -- 16-Port Fast Ethernet Optical Interface Line Process Card(Single-mode,1550nm,15km,LC)
                subbnameCR01OPMQ(528725),     -- Single-mode,1550nm,LC Interface Optical Protection Module
                subbnameCR01OPMZ(528726),     -- Single-mode,1300nm,LC Interface Optical Protection Module
                subbnameCR01OPMM(528727),     -- Multi-mode,1300nm,LC Interface Optical Protection Module
                subbnameCR01OPMP(528728),     -- Multi-mode,850nm,LC Interface Optical Protection Module
                subbnameSPCB(528729),         -- 4*FE-RJ45 And 4*FE-SFP And 4*OC-3c/STM-1 POS Multi-mode 1300nm 2km-MTRJ Interface Line Card
                subbnameEGFSE(528730),        -- CR01EGFSE0
                subbnameEGFME(528731),        -- CR01EGFME0
                subbnameP8CFF(528732),        -- 8 Port POS155 SFP Optical Interface Line Process Card
                subbnameE4GFF(528733),        -- 4-port GE SFP Interface Line Card
                subbnameEGFF(528734),         -- 16*FE Optical Interface Line Card-SFP
                subbnameP2HF(528735),         -- CR03P2HF-2*OC-12c/STM-4c-POS-SFP Optical Interface Card

-- 8031
                subbnameCX61E1XX0(536577),      -- CX600-1-port 10G Ethernet LAN Optical Interface LPU (Enhanced)
                subbnameCX61W1XX0(536578),      -- CX600 1-port 10G Ethernet WAN Optical Interface LPU (Enhanced)
                subbnameCX61EAGF0(536579),      -- CX600-10-port Gigabit Ethernet Optical Interface LPU (Enhanced)
                subbnameCX61EFGE0(536580),      -- CX600-24-port 10M/100M/1000M Ethernet Electrical Interface LPU(Enhanced)
                subbnameCX61E2XXE0(536581),     -- CX600-2-port 10G Ethernet LAN Optical Interface LPU
                subbnameCX61EFGEE0(536582),     -- CX600-24-port 10M/100M/1000M Ethernet Electrical Interface LPU
                subbnameCX61EFGFE0(536583),     -- CX600-24-port Gigabit Ethernet Optical Interface LPU
                subbnameCX61EMGEE0(536584),     -- CX600-48-port 10M/100M/1000M Ethernet Electrical Interface LPU
                subbnameCX61EMGFE0(536585),     -- CX600-48-port Gigabit Ethernet Optical Interface LPU
                subbnameCX61E1XS0(536586),      -- CX600-NetEngine-CR61E1XS0-1*10GE LAN 1310nm 10km-LC
                subbnameCX61E1XQ0(536587),      -- CX600-NetEngine-CR61E1XQ0-1*10GE LAN 1550nm 40km-LC
                subbnameCX61W1XS0(536588),      -- CX600-NetEngine-CR61W1XS0-1*10GE WAN 1310nm 10km-LC
                subbnameCX61W1XQ0(536589),      -- CX600-NetEngine-CR61W1XQ0-1*10GE WAN 1550nm 40km-LC
                subbnameCX61W1XV0(536590),      -- CX600-NetEngine-CR61W1XV0-1*10GE WAN 1550nm 80km-LC
                subbnameCX61R1XX(536591),       -- CX600-CX61R1XX0-1*OC-192c/STM-64c RPR-XFP
                subbnameCX61R4UF(536592),       -- CX600-CX61R4UF0-4*OC-48c/STM-16c RPR-SFP
                subbnameCX61R2GF(536593),       -- CX600-CX61R2GF0-2*GE/STM-16c RPR-SFP
                subbnameCX61R4GF(536594),       -- CX600-CX61R4GF0-4*GE/STM-16c RPR-SFP
                subbnameCX61EFFF(536595),       -- CX600-CX61EFFF0-24
                subbnameCX61R2UF(536596),       -- CX600-CX61R2UF0-2*OC-48c/STM-16c RPR-SFP
                subbnameCX61E1XXA(536597),      -- CX600-CX61E1XXA-1 10GE-Lan/Wan
                subbnameCX61EBGF(536598),       -- CX600-CR52EBGF0,12-port 100/1000Base-X SFP Flexible Interface Daughter Card
                subbnameCX61EBGE(536599),       -- CX600-CR52EBGE0,12-port 10/100/1000Base-TX RJ45 Flexible Interface Daughter Card
                subbnameCX61L1XX(536600),       -- CX600-CR52L1XX0,1-port 10GBase WAN/LAN XFP Flexible Interface Daughter Card
                subbnameCx61L4XX(536601),       -- CX600-CR52L4XX0,4-port 10GBase WAN/LAN-XFP Flexible Card(Occupy two sub-slots)
                subbnameCX61EKGE(536602),       -- CX600-CR52EKGE0,40-port 10/100/1000Base-RJ45 Flexible Card (Occupy two sub-slots)
                subbnameCX61EKGF(536603),       -- CX600-CR52EKGF0,40-Port 100/1000Base-SFP Flexible Card(Occupy two sub-slots)
                subbnameCX61P1XXB(536604),      -- CX600-CR52P1XXBZ0,1 port OC-192c/STM-64c POS-XFP Flexible Card
                subbnameCX67E8GF(536605),       -- CX600-X1 Interface
                subbnameCX67E8GFA(536606),      -- CX600-X1 Interface
                subbnameCX67E8FF(536607),       -- CX600-X1 Interface
                subbnameCX67E8FE(536608),       -- CX600-X1 Interface
                subbnameCX67DE1(536609),        -- CX600-X1 Interface
                subbnameCX67DE1A(536610),       -- CX600-X1 Interface
                subbnameCX67C1CF(536611),       -- CX600-X1 Interface
                subbnameCX67AUXQ(536612),       -- CX600-X1 Interface
                subbnameCX67VNPUICARD(536613),  -- CX600-X1 Interface
                subbnameCX22E2XX(536614),       -- CX22E2XX-4*10GE
                subbnameCX22E4GF(536615),       -- CX22E4GF-4*GE
                subbnameCX0235000d22E4GFA(536616), -- 0235000dCX22E4GFA-4*GE
                subbnameCX22E2XEA(536617),      -- CX22E2XEA-2*10GE,RJ45
                subbnameCX22E4XY(536618),       -- CX22E4XY-4*10GE,XFP
                subbnameCX22E2XY(536619),       -- CX22E2XY-2*10GE,XFP
                subbnameCXTPB(536620),          -- TPB
                subbnameCX0235000bFAN(536621),  -- 0235000bFAN
                subbnameCx0235000aPOWER(536622),-- 0235000aPOWER
                subbnameCX0235000cTPC(536623),  -- 0235000cTPC
                subbnameCX03020PWP22E4GFA(536624),-- 03020PWPCX22E4GFA-4*GE
                subbnameCX03020NPWTPC(536625),  -- 03020NPWTPC
                subbnameCX03020GFAFAN(536626),  -- 03020GFAFAN
                subbnameCX03020LXPPOWER(536627),-- 03020LXPPOWER
                subbnameCX03020LYXPOWER(536628),-- 03020LYXPOWER
                subbnameCX02316783POWER(536629),-- 02316783POWER
                subbnameCX02316784POWER(536630),-- 02316784POWER
                subbnameCX02351651FAN(536631),  -- 02351651FAN
                subbnameCX02130877POWER(536632),-- 02130877POWER,180w POE
                subbnameCX02130878POWER(536633),-- 02130878POWER,250W POE
                subbnameCX02130879POWER(536634),-- 02130879POWER,500W POE

                subbnameCX62E8GF0(536635),                  -- CX600-X1-DO/CX600-X2-DO 8-Port 100/1000Base-X-SFP High-speed Interface Card (HIC)
                subbnameCX62E8GFA0(536636),                 -- CX600-X1-DO/CX600-X2-DO 8-Port 100/1000Base-X-SFP High-speed Interface Card A (HIC, Supporting 1588v2)
                subbnameCX62E8FF0(536637),                  -- CX600-X1-DO/CX600-X2-DO 8-Port 100Base-X-SFP Flexible Interface Card (FIC, Supporting 1588v2)
                subbnameCX62E8FE0(536638),                  -- CX600-X1-DO/CX600-X2-DO 8-Port 100Base-RJ45 Flexible Interface Card (FIC, Supporting 1588v2)
                subbnameCX62C1CF0(536639),                  -- CX600-X1-DO/CX600-X2-DO 1-Port Channelized OC-3c/STM-1c POS-SFP Flexible Interface Card (FIC)
                subbnameCX62DE10(536640),                   -- CX600-X1-DO/CX600-X2-DO 16-Port E1(75ohm) Flexible Interface Card (FIC)
                subbnameCX62DE1A0(536641),                  -- CX600-X1-DO/CX600-X2-DO 16-Port E1(120ohm) Flexible Interface Card (FIC)
                subbnameCX62AUXQ0(536642),                  -- CX600-X1-DO/CX600-X2-DO Auxiliary Flexible Interface Card with 4-Port 100Base-RJ45(FIC, Supporting 1588v2)
                subbnameCX62E8GF1(536643),                  -- CX600-DO 8-Port 100/1000Base-X-SFP Flexible Card(S10)
                subbnameCX62E8GFB0(536644),                 -- CX600-DO 8-Port 100/1000Base-X-SFP Flexible Card A(S10-A,Supporting 1588v2)
                subbnameCX62A2HF0(536645),                  -- CX600-DO 2-Port OC-12c/STM-4c ATM-SFP Flexible Card(S10)
                subbnameCX62A4CF1(536646),                  -- CX600-DO 4-Port OC-3c/STM-1c ATM-SFP Flexible Card(S10)
                subbnameCX62C2CF0(536647),                  -- CX600-DO 2-Port Channelized OC-3c/STM-1c POS-SFP Flexible Card(S10)
                subbnameCX62CFE10(536648),                  -- CX600-DO 24-Port Channelized E1/T1-DB100 Flexible Card(S10)
                subbnameCX62L1XX0(536649),                  -- CX600-DO 8-Port 1-Port 10GBase LAN/WAN-XFP Flexible Card(S20)
                subbnameCX62EBGF0(536650),                  -- CX600-DO 12-Port 100/1000Base-X-SFP Flexible Card(S20)

                subbnameCX62EBGE0(536651),                  -- CX600-DO 8-Port 12-Port 10/100/1000Base-RJ45 Flexible Card(S20)
                subbnameCX62L1XXB0(536652),                 -- CX600-DO 8-Port 1-Port 10GBase LAN/WAN-XFP Flexible Card A(S20-A,Supporting 1588v2)
                subbnameCX62EBGFB0(536653),                 -- CX600-DO 12-Port 100/1000Base-X-SFP Flexible Card A(S20-A,Supporting 1588v2)
                subbnameCX62EKGF0(536654),                  -- CX600-DO 40-Port 100/1000Base-X-SFP Flexible Card(S20,Occupy two sub-slots)
                subbnameCX62EKGE0(536655),                  -- CX600-DO 40-Port 10/100/1000Base-RJ45 Flexible Card(S20,Occupy two sub-slots)
                subbnameCX62L4XX0(536656),                  -- CX600-DO 4-Port 10GBase LAN/WAN-XFP Flexible Card(S20,Occupy two sub-slots)
                subbnameCX62L2XEEGF0(53657),                -- CX600-DO 2-Port 10GBase LAN/WAN-XFP+20-Port 100/1000Base-X-SFP Flexible Card(S20,Occupy two sub-slots)

                subbnameCX62EMFE0(536658),                  -- CX600-DO 48-Port 10/100Base Delander Flexible Card(S20,Occupy one sub-slot)
                subbnameCX62L2XXN0(536659),                 -- CX600-DO 2-Port 10GBase LAN/WAN-XFP Flexible Card(S40)
                subbnameCX62EEGFN0(536660),                 -- CX600-DO 20-Port 100/1000Base-X-SFP Flexible Card(S40)
                subbnameCX62L2XXNB0(536661),                -- CX600-DO 2-Port 10GBase LAN/WAN-XFP Flexible Card A(S40-A,Supporting 1588v2)
                subbnameCX62EEGFNB0(536662),                -- CX600-DO 20-Port 100/1000Base-X-SFP Flexible Card A(S40-A,Supporting 1588v2)
                subbnameES510X2X(536663),                    -- ES510X2X-2*10GE
                subbnameES510G4S(536664),                    -- ES510G4S-4*GE
                subbnameES510G4SA(536665),                   -- ES510G4SA-4*GE
                subbnameES510X4S(536666),                    -- ES510X4S-4*10GE,XFP
                subbnameES510X2S(536667),                    -- ES510X2S-2*10GE,XFP
                subbnameTPC(536668),                         -- TPC

                subbnameLS510X4SA(536669),                -- 4-Port GE SFP or 10GE SFP+ Optical Interface Card (Used In HI Series)
                subbnameLS510X2SA(536670),                -- 2-Port GE SFP or GE SFP/10GE SFP+ Optical Interface Card (Used In HI Series)
                subbnameLS510G4SC(536671),                -- 4-Port GE SFP Optical Interface Card (Used In HI Series)
                subbnameLS310G2S(536672),                 -- 2-Port GE SFP Optical Interface Card (Used In HI Series)

                subbname02130911POWER(536673),            -- 02130911POWER
                subbname03020WFNPOWER(536674),            -- 03020WFNPOWER
                subbname02353514FAN(536675),              -- 02353514FAN
                subbnameCX61A4CFN(536721),                -- CX600-X1/X2,4-port STS-3C/STM-1 ATM SFP Optical Interface Flexible Plug Card
                subbnameCX67E4GF(536722),                -- CX600-X1/X2,4-port GE SFP Optical Interface Flexible Plug Card

                subbnameES510X4SA(536676),                -- ES510X4SA  4-Port GE SFP or 10GE SFP+ Optical Interface Card (Used In HI Series)
                subbnameES510X2SA(536677),                -- ES510X2SA 2-Port GE SFP or GE SFP/10GE SFP+ Optical Interface Card (Used In HI Series)
                subbnameES510G4SC(536678),                -- ES510G4SC 4-Port GE SFP Optical Interface Card (Used In HI Series)
                subbnameES310G2S(536679),                 -- ES310G2S 2-Port GE SFP Optical Interface Card (Used In HI Series)
                subbname02130965POWER(536680),            -- 02130965POWER
                subbname02310GBMPOWER(536681),            -- 02310GBMPOWER
                subbnameLS520G8S(536682),            -- S5700 LS520G8S 8-Port GE SFP Optical Interface Card 2*1
                subbnameLS520G8T(536683),            -- S5700 LS520G8T 8-Port GE RJ45 Interface Card 2*1
                subbnameLS521VST(536684),            -- S5700 LS521VST Stack Card 1*1

                subbnameCX6D0L2XFA10(536685),        -- 2-Port 10GBase LAN/WAN-SFP+ Flexible Card A(S50-A,Occupy one sub-slot)
                subbnameCX02317465POWER(536686),      -- 02317465POWER,500w POE
                subbname8090DEVCX67P4CF0(536687),     --4-Port OC-3c/STM-1c POS Flexible Interface Card
                subbname8090DEVCX6D00C2CF10(536688),  -- 2-Port Channelized OC-3c/STM-1c POS-SFP Flexible Card
                subbname8090DEVCX6D00L1XX10(536689),  --1-Port 10GBase LAN/WAN-XFP Flexible Card
                subbname8090DEVCX6D00EBGF10(536690),  --12-Port 100/1000Base-X-SFP Flexible Card
                subbname8090DEVCX6D00EEGE10(536691),  --20-Port 10/100/1000Base-RJ45 Flexible Card
                subbname8090DEVCX6D00L2XX10(536692),   --2-Port 10GBase LAN/WAN-XFP Flexible Card
                subbname8090DEVCX6D00EFGF10(536693),  --24-Port 100/1000Base-X-SFP Flexible Card
                subbname8090DEVCX6D0EBGFA11(536694),  --12-Port 100/1000Base-X-SFP Flexible Card A(S40-A,Supporting 1588v2)
                subbname8090DEVCX62L1XEAGB0(536695),  --1-Port 10GBase LAN/WAN-XFP+10-Port 100/1000Base-X-SFP Flexible Card A(S40-A,Supporting 1588v2)
                subbname8090DEVCR5D00E4GF70(536696),  --4-Port 100/1000Base-X-SFP High-speed Interface Card(HIC)
                subbnameES5D21X02S00(536697),         --2-Port GE SFP or 10GE SFP+ Optical Interface Card

                subbname02317465POWER(536700),        -- 02317465POWER
                subbname02310JFDPOWER(536701),        -- 02310JFDPOWER
                subbname02310JFAPOWER(536702),        -- 02310JFAPOWER
                subbname8090DEVCX6D00P8HF10(536703),  --8-Port OC-12c/STM-4c POS-SFP Flexible Card
                subbname8090DEVCX6D00P4CF10(536704),   --4-Port OC-3c/STM-1c POS-SFP Flexible Card
                subbname8090DEVCX6D00P8CF10(536705),  --8-Port OC-3c/STM-1c POS-SFP Flexible Card
                subbname02310JWVPOWER(536706),        -- 02310JWVPOWER
                subbname02130953POWER(536707),        -- 02130953POWER
                subbname02130984POWER(536708),        -- 02130984POWER
                subbname02310CNKPOWER(536709),        -- 02310CNKPOWER
                subbname02130966POWER(536710),        -- 02130966POWER
                subbnameES5D21G16S00(536711),          -- ES5D21G16S00 16-Port GE SFP Optical Interface Card
                subbnameES5D21G16T00(536712),          -- ES5D21G16T00 16-Port GE RJ45 Interface Card
                subbnameES5D21L04Q00(536713),          -- ES5D21L04Q00 4-Port 40GE QSFP+ Optical Interface Card
                subbnameES5D21X04S00(536714),          -- ES5D21X04S00 4-Port 10GE SFP+ Optical Interface Card
                subbnameLS5D21G08S00(536715),          -- LS5D21G08S00 8-Port GE SFP Optical Interface Card(Used In S5310 EI Series)
                subbnameLS5D21G08T00(536716),          -- LS5D21G08T00 8-Port GE RJ45 Interface Card(Used In S5310 EI Series)
                subbnameCX67P4CFA(536717),             -- CX67P4CFA 4-Port OC-3c/STM-1c POS-SFP Flexible Interface Card
                subbnameCX68L4XF(536718),              -- CX68L4XF 4-Port 10GBase-X-SFP+High-speed Interface Card
                subbnameCX68L1XE8GF(536719),           -- CX68L1XE8GF 1-Port 10GBase-X-SFP+ + 8-Port 100/1000Base-X-SFP High-speed Interface Card
                subbname02130971POWER(536720),         -- 02130971POWER

                -- For  CX600  V8R5  CH  (536730~)
                subbname8090DEVCX6D00L2XF10(536730),   -- CX68L2XFB, 2-Port 10GBase LAN/WAN-SFP+ Service Interface Card(SIC)
                subbname8090DEVCX6D00E8GF10(536731),   -- CX68E8GFC, 8-Port 100/1000Base-X-SFP Service Interface Card(SIC)
                subbname8090DEVCX6D00E8GE10(536732),   -- CX68E8GEB, 8-Port 10/100/1000Base-RJ45 Service Interface Card(SIC)

                subbname8090DEVCX6D00C4CF11(536733),   -- CX68C4CF,  4-Port Channelized STM-1c POS-SFP Service Interface Card(SIC)
                subbname8090DEVCX6D000IE110(536734),   -- CX68MIE1,  32-Port E1 Service Interface Card(SIC,75ohm)
                subbname8090DEVCX6D000IE111(536735),   -- CX68MIE1B, 32-Port E1 Service Interface Card(SIC,120ohm)
                subbname8090DEVCX6D000DE110(536736),   -- CX68MDE1A, 16-Port E1 Service Interface Card(SIC,75ohm)
                subbname8090DEVCX6D000DE111(536737),   -- CX68MDE1B, 16-Port E1 Service Interface Card(SIC,120ohm)
                subbname8090DEVCX6D00L4XF10(536739),   -- CX68L4XF, 4-Port 10GBase-X-SFP+High-speed Interface Card(SIC)
                subbname8090DEVCX6DL1XE8G10(536740),   -- CX68L1XE8GF, 1-Port 10GBase LAN/WAN-SFP+  8-Port 100/1000Base-X-SFP Service Interface Card(SIC)
                subbnameSwitchBAT4AHA(536741),         -- BAT-4AHA Lithiumion battery unit
                subbnameSwitchBAT8AHA(536742),         -- BAT-8AHA Lithiumion battery unit
                subbnameSwitchPBB12AHA (536743),       -- PBB-12AHA(12AH Power Backup Interface Card)
                subbnameLS5D21G16S00(536744),          -- 16-Port GE SFP Optical Interface Card
                subbnameLS5D21G16T00(536745),          -- 16-Port GE RJ45 Interface Card
                subbnameLS5D21L04Q00(536746),          -- 4-Port 40GE QSFP+ Optical Interface Card
                subbnameLS5D21X04S00(536747),          -- 4-Port 10GE SFP+ Optical Interface Card
                subbname02131063POWER(536748),         -- 350W AC Power Module
                subbname02131064POWER(536749),         -- 1150W AC Power Module
                subbname02356618FAN(536750),           -- Fan box(EF,Airflow Port side to power supply side)
                subbnameES5D21X04S01(536751),          -- 4 10 Gig SFP+ Interface Card(used in S5720HI series)
                subbnameES5D21VST000(536752),          -- Dedicated stack interface card(uesed QSFP interface,used in S5720HI series)
                subbname02310PQNPOWER(536753),         -- 350W DC Power Module
                subbname02355338FAN(536754),           -- Fan box(EA,Back to Front)

                subbnameES5D21X02S01(536755),          -- 2 10 Gig SFP+ Interface Card(used in S5720EI series)
                subbnameLS5D21X02S01(536756),          -- 2 10 Gig SFP+ Interface Card(used in S5320EI series)
                subbnameES5D21X02T01(536757),          -- 2 10 Gig RJ45 Interface Card(used in S5720EI series)
                subbnameLS5D21X02T01(536758),          -- 2 10 Gig RJ45 Interface Card(used in S5320EI series)
                subbnameES5D21X04S02(536759),          -- 4 10 Gig SFP+ Interface Card(used in S5720EI series)
                subbnameLS5D21X04S02(536760),          -- 4 10 Gig SFP+ Interface Card(used in S5320EI series)
                subbnameLS5D21VST000(536761),          -- Dedicated stack interface card(uesed QSFP interface,used in S5320EI series)
                subbnameFAN028AB(536762),              -- Fan box(F,FAN panel side intake)
                subbnameFAN028BB(536763),              -- Fan box(F,FAN panel side intake)
                subbnamePDC650WABEPOWER(536764),       -- DC-DC Module,650W
                subbnamePDC650WBBEPOWER(536765),       -- DC-DC Module,650W
                subbnamePAC600WCBPOWER(536766),        -- 600W AC Power Module
                subbnamePDC350WCBPOWER(536767),        -- 350W DC Power Module

                subbnameES5D21Q04Q01(536768),          -- 4 40 Gig QSFP+ interface card(used in S6720EI series)
                subbnameLS5D21Q04Q01(536769),          -- 4 40 Gig QSFP+ interface card(used in S6320EI series)
                subbnameFAN060BB(536770),              -- Fan box(B,FAN panel side exhaust)
                subbnameFAN060CB(536771),              -- Fan box(B,FAN panel side exhaust)
                subbnamePAC600WCBPOWERB(536772),       -- 600W AC Power Module(Gray)
                subbnamePDC350WCBPOWERB(536773),       -- 350W DC Power Module(Gray)
                subbnameLS5D21X04S01(536774),          -- 4 10 Gig SFP+ Interface Card(used in S5320HI series)
                subbnamePAC-60WA-L(536775),            -- 60W AC Power Module(Black)  for  S5720LI v2r11
                subbnamePAC-60WC-L(536776),            -- 60W AC Power Module(Gray)   for  S5320LI v2r11

                subbnameES5D21X02S02(536777),          -- 2 10 Gig SFP+ Interface Card(Used in S5720LI series) for v2r12
                subbnameES5D21X08T00(536778),          -- 8 Ethernet 100M/1G/2.5G/5G/10GBase-T Interface Card(Used in (S5X30SI/S6720EI/S6X20SI series) for v2r11
                subbnameES5D21X04T00(536779),          -- 4 Ethernet 100M/1G/2.5G/5G/10GBase-T Interface Card(Used in S5x30SI/S6x20SI series)  for v2r11
                subbnameES5D21X08S00(536780),          -- Data Communication,ES5D21X08S00,ES5D21X08S00,8 10 Gig SFP+ Interface Card(Used in S5x30SI/S6720EI/S6x20SI series) for v2r11
                subbnameES5D21Q02Q00(536781),          -- 2 40 Gig QSFP+ interface card(used in S5x30SI/S6x20SI series)  for v2r11
                subbnamePAC930D5612(536782),           -- 930W AC PoE Power Module for  S5320LI V2R11
                subbnameFAN040CB(536783),              --FAN for 6720SI

                subbnameES2D1POE4800(536784),           --03024PLK ES2D1POE4800  for lsw v2r11c50
                subbnameES2D1POE2403(536785),           --03024PLL ES2D1POE2403  for lsw v2r11c50
                subbnameES5D21Q06Q00(536786),           --03024PLJ ES5D21Q06Q00  for lsw v2r11c50
                subbnameES5D2CKM0000(536787),           --03024QVY ES5D2CKM0000  for lsw v2r11c50
                subbnameFAN40HAB(536788),                    --2359097 Fan box(HA,Back to Front,FAN panel side exhaust)
                subbnameSSD240GB(536789),                   --240GB SSD Card(Used in S5x30HI series)
                subbnameSSD32GB(536790),                     --32GB SSD Card(Used in S5x30HI series)
                subbnamePAC-260WA-E(536791),             --260W AC Power Module(Black)
                subnamePAC1000D5412(536792),             --1000W AC POWER MODULE for V2R13C00
                subnamePAC600S12CB(536793),              --600W AC power module (back to front,power panel side exhaust) for V2R13C99
                subnamePAC600S12CF(536794),              --600W AC Power Module (Front to Back,Power panel side intake) for V2R19C00
                subnamePAC1000S56CB(536795),            --1000W AC PoE Power Module for V2R19C00
                subnameFAN031AB(536796),                     --FAN-031A-B for V2R19C00
                subnameFAN023AB(536797),                     --FAN-023A-B for V2R13C02
                subnamePDC1000S12(536798),                 --Function Module,DC PSU,PDC1000S12-D for V2R19C00
                subnamePAC150S12(536799),                   --Function Module, AC PSU, PAC150S12-R, 150W AC Power Module for V2R19C00
                subnamePAC60S12AR(536800),                --Function Module,AC PSU,PAC60S12-AR,60W AC Power Module for V2R19C00
                subnameS7Q02000(536801),                      --subcard S7Q02000 for V2R19C00
                subnameS7M08000(536802),                     --subcard S7M08000 for V2R19C00
                subnameS7X08000(536803),                     --8-port 10GE SFP+ interface card (used in S5331H and S5731H series) for V2R19C10
                subnameS7X08000-K(536804),                 --8-port 10GE SFP+ interface card (used in S5331H and S5731H series) for V2R19C10
                subnameEN31PERE(536805),                   --Manufactured Board,PAC460S55,EN31PERET,poe 460w power board
                subnameS7Y08000(536806),           --8-port 25GE/10GE/GE SFP28 interface card for V2R20C00
                subnamePDC260S12DL(536807),           --260W DC Power Module for V2R20C00
                subnamePDC180S12CR(536808),           --180W DC Power Module for V2R20C00
                subnamePDC180S12CL(536809),           --PDC180S12-CL,Power Board for V2R20C00
                subnamePAC300S12CL(536810),           --300 AC Power Module for V2R20C00
                subnameFAN0031AF(536812),           --Fan box(F,FAN panel side intake) for V2R20C00
                subnamePAC1000S56-DB(536813),           --1000W AC&240V DC Power Module for V2R20C10
                subnamePAC600S12-DB(536814),             --600W AC Power Module(Back to Front, Power panel side exhaust) for V2R20C10
                subnamePAC-600WD-B(536815),               --600W AC Power Module(Back to Front,Power panel side exhaust) for V2R20C10
                subnamePAC460S55-D(536816),               --PoE 460W Power Board for V2R20C10
                subnamePDC1000S56-CB(536817),    --POE1000W DC Power Module (Back to Front, Power panel side exhaust) for v2r21c00
                subnameS7Q02001(536818),           --2-port 40GE QSFP+ interface card for V2R21C01
                subnamePAC600S56-CB(536819),    --600W AC&240V DC Power Module (Back to Front,Power panel side exhaust) for V2R21C10
                subnamePAC600S12-EB(536820),    --600W AC Power Module(Back to Front, Power panel side exhaust) for V600R021C10
                subnameFAN-240SM-B(536821),    --single-layer fan module with two fans for V600R021C10
                subnameFAN-480SM-B(536822),    --single-layer fan module with four fans for V600R021C10
                subnamePAC600S56-EB(536825), --Function Module,AC&240VDC PSU,PAC600S56-EB,600W AC&240V DC Power Module (66mm Width Case,Back to Front,Power panel side exhaust) for V2R22C00
                subnamePAC1000S56-EB(536826), --Function Module,AC&240VDC PSU,PAC1000S56-EB,1000W AC&240V DC Power Module(66mm Width Case,Back to Front, Power panel side exhaust) for V2R22C00
                subnamePDC1000S56-EB(536827), --Function Module,DC PSU,PDC1000S56-EB,POE1000W DC Power Module (66mm Width Case, Back to Front, Power panel side exhaust) for V2R22C00
                subnameS7C02000(536828), --2-port 100GE QSFP28 interface card for V2R22C00 
                subnamePAC180S12-CN(536829),     --PAC180S12-CN for V6R22C00
                subnamePAC600S12-PB(536830),     --PAC600S12-PB for V6R22C00
                subnamePAC1K2S12-PB(536831),     --PAC1K2S12-PB for V6R22C00
                subnamePDC1K2S12-CE(536832),     --PDC1K2S12-CE for V6R22C00
                subnamePAC80S12-CN(536833),      --PAC80S12-CN
                subnameHSIC-Y08S000(536834),     --HSIC-Y08S000 (8-port 25GE SFP28 interface card)
                subnameHSIC-X08S000(536835),     --HSIC-X08S000 (8-port 25GE/10GE SFP28 interface card(1/2/3/4 support 25GE))
                subnameXSIC-M26B000(536836),     --XSIC-M26B000 (card with 24*GE/2.5G/5G/10GBase-T ports and 2*40GE/100GE QSFP28 ports)
                subnameXSIC-X26B000(536837),     --XSIC-X26B000 (card with 24*10GE SFP+ ports and 2*100GE QSFP28 ports)
                subnameXSIC-Y26B000(536838),     --XSIC-Y26B000 (card with 24*25GE SFP28 ports and 2*100GE QSFP28 ports)
                subnameXSIC-C10H000(536839),     --XSIC-C10H000 (card with 10*100GE QSFP28 ports)
                subnameXSIC-L16Q000(536840),     --XSIC-L16Q000 (card with 16*40GE QSFP+ ports)
                subnameXSIC-C16H000(536841),     --XSIC-C16H000 (card with 16*100GE QSFP28 ports)
                subnameXSIC-D12B000(536842),     --XSIC-D12B000 (card with 8*25GE SFP28 ports and 4*400GE QSFP-DD ports)
                subnamePDC400S12-CB(536843),     --Function Module,DC PSU,PDC400S12-CB,400W DC Power Module(Rear Front Air Passage, Power Panel Side Air Outlet)
                subnamePDC240S12-CN(536844),     --Function Module,DC PSU,PDC240S12-CN,240W DC Power Module
                subnameSPE-F08T000(536845),      --Interface card with 8*10M SPE ports
                subnameFAN-023A-F(536846),       --Function Module,Fan Box,FAN-023A-F,Fan Box,Fan box(F,FAN panel side intake)

-- 8090


                subbname8090CFCARD(561151),         --CFCARD in MPUA or CFCARD2 in SRUA/MPUB
                subbname8090Unkown(561152),          --
                subbname8090E1XZ(561153),          --1*10GE LAN Single-mode Optical Interface LPU
                subbname8090W1XZ(561154),          --1*10GE WAN Single-mode Optical Interface LPU
                subbname8090EAGF(561155),          --10-port GbE SFP Optical Interface LPU
                subbname8090P4UF(561156),          --4-port 2.5G POS SFP Optical Interface LPU
                subbname8090GE(561157),            --GE card
                subbname8090FE(561158),            --Fe card
                subbname8090P1XZ(561159),          --1*OC-192c/STM-64c POS Optical Interface LPU
                subbname8090Pos622(561160),        -- Pos_622
                subbname8090Pos25G(561161),        -- Pos_2.5G
                subbname8090ATM(561162),           --ATM
                subbname8090DPT25G(561163),        -- DPT 2.5G
                subbname8090P16X155Channel(561164),-- POS_16x155_CHANNEL
                subbname8090P4HF(561165),          -- POS_4X622
                subbname8090Pos155(561166),        -- POS_155
                subbname8090E2XX(561167),          --2*10GBase LAN-XFP Optical Interface LPU C
                subbname8090W2XX(561168),          --2*10GBase WAN-XFP Optical Interface LPU C
                subbname8090P2XX(561169),          --2*OC-192c/STM-64c POS-XFP Optical Interface LPU C
                subbname8090EMGE(561170),          --48*10/100/1000Base-TX-RJ45 Electrical Interface LPU
                subbname8090A8CF(561171),          --ATM8X155M
                subbname8090RPR10G(561172),        --RPR_1X_10G_CARD
                subbname8090P8CF(561173),          --8*OC-3c/STM-1 POS-SFP Optical Interface LPU
                subbname8090EFGE(561174),          --24*10/100/1000Base-TX-RJ45 Electrical Interface LPU

                subbnameRNRPOS4X155(561175),          --4*OC-3c/STM-1 POS-SFP Optical Interface LPU
                subbnameRNRPOS1X622(561176),          --1 Port 622M POS Interface LPU
                subbnameRNRPOS1X25G(561177),          --1 Port 2.5G POS Interface LPU
                subbnameRNRPOS16X155(561178),         --16*OC-3c/STM-1 POS-SFP Optical Interface LPU
                subbnameRNRPOS4X622(561179),          --4 Port 622M POS Interface LPU
                subbnameRNRPOS8X155(561180),          --8*OC-3c/STM-1 POS-SFP Optical Interface LPU
                subbnameRNRATM8X155(561181),          -- 8 Port 155M ATM Interface LPU
                subbnameRNRATM2X622(561182),          -- 2 Port 622M ATM Interface LPU

                subbnameRNRETH4X100D(561183),        -- 4 Port 100M RJ45 Interface LPU
                subbnameRNRETH4X100G(561184),        -- 4 Port 100M Fiber Interface LPU

                subbnameRNRETH8X100D(561185),        -- 8 Port 100M RJ45 Interface LPU
                subbnameRNRETH8X100G(561186),        -- 8 Port 100M Fiber Interface LPU

                subbnameRNRETH16X100D(561187),       -- 16 Port 100M RJ45 Interface LPU
                subbnameRNRETH16X100G(561188),       -- 16 Port 100M Fiber Interface LPU

                subbnameRNRETH16X100OTHER(561189),   -- 16 Port 100M Interface LPU

                subbnameRNRETH4XGE(561190),           -- 4 Port GE RJ45/Fiber Interface LPU
                subbnameRNRETH4XGC(561191),           -- 4 Port GE GE_BIC RJ45/Fiber Interface LPU

                subbnameRNRETH2XGE(561192),           -- 2 Port GE Interface LPU
                subbnameRNRETH2XGC(561193),           -- 2 Port GE GE_BIC Interface LPU

                subbnameRNRDPTCARD(561194),           --FRR Card

                subbnameRNRCE1PDH2M(561195),        -- 8
                subbnameRNRCT1PDH1P5M(561196),      -- 8

                subbnameRNRE1PDH2M(561197) ,        -- 8
                subbnameRNRE3PDH34M(561198),        -- 3
                subbnameRNRT3PDH44M(561199),        -- 3

                subbnameRNRCPOSOC3(561200),          --1
                subbnameRNRPOSOC12C(561201),         --4
                subbnameRNRPOSOC48C(561202),         --1

                subbname8090P1UF(561203),              --1-port 2.5G POS SFP Optical Interface LPU
                subbname8090P2UF(561204),              --2-port 2.5G POS SFP Optical Interface LPU

                subbnameRNRATMA8CFFF(561205),        --8 Port 155M ATM Interface LPU
                subbnameRNRATMA2HFFF(561206),        --2 Port 622M ATM Interface LPU
                subbnameRNRRPR1X25(561207),           --1 Port 2.5G SDH RPR

                subbnameRNRPOSP4CFFF(561208),        --4 Port 155M POS
                subbnameRNRETHE8FFF(561209),         --8 Port 100M Fiber Interface LPU
                subbname8090EFGF(561210),               --24GE
                subbname8090EMGF(561211),               --48GE
                subbnameRNRCPOS2OC3(561212),          --2*CPOS OC-3/STM-1-SFP Optical
                subbmaneRNRCPOS4OC3(561213),      --4*CPOS OC-3/STM-1-SFP Optical
                subbmaneRNR8XCE1(561214),          --UR-PIM-8xCHE1-RJ45
                subbmaneRNRCPOSOC3FR(561215),    --1*CPOS OC-3/STM-1-SFP Optical
                subbmaneRNR8XCT1(561216),          --UR-PIM-8xCHT1-RJ45
                subbname8090R2UF(561217),               --2 Port 2.5G SDH RPR
                subbname8090R4UF(561218),               --4 Port 2.5G SDH RPR

                subbname8090R2GF(561219),               --2 Port GE RPR
                subbname8090R4GF(561220),               --4 Port GE RPR
                subbname8090EFFF(561221),               --24-port GE/FE SFP Phyiscal Interface Card

                subbname8090CR53P1XX(561222),               --1-port 10G POS XFP  Flexible Pluggable Interface Daughter Card
                subbname8090CR53E8GF(561223),               --8-port GE SFP Flexible Pluggable  Interface Daughter Card
                subbname8090CR53E8FF(561224),               --8-port FE SFP  Flexible Pluggable  Interface Daughter Card
                subbname8090CR53P1UF(561225),               --1-port 2.5G POS SFP Flexible Pluggable Interface Daughter Card
                subbname8090CR53A2HF(561226),               --2-port 622M ATM  SFP  Flexible Pluggable Interface Daughter Card
                subbname8090CR53A4CF(561227),               --4-port 155M ATM  SFP  Flexible Pluggable Interface Daughter Card

                subbname8090L1XX0(561228),              --1-port 10GBase WAN/LAN XFP Flexible Interface Daughter Card
                subbname8090EBGF(561229),               --12ports 100Base-FX/1000Base-X
                subbname8090EBGE(561230),                --12ports 10Base-T/100Base-TX/1000Base-T

                subbname8090EAGF2(561231),               -- 5 port GbE SFP Optical Interface LPU
             subbname8090P4CF(561232),               -- 4*OC-3c/STM-1 POS-SFP Optical Interface LPU

               subbname8090L4XX(561233),    -- 4-port 10G LAN/WAN XFP Optical Interface Daughter Card,1*1
               subbname8090EKGE(561234),    -- 40-port 10/100/1000M RJ-45 Interface Daughter Card,1*1
               subbname8090EKGF(561235),    -- 40-Port FE/GE SFP Optical Interface Daughter Card,1*1
               subbname8090P2UFZ(561236),   -- 2-port 2.5G POS SFP Flexible Pluggable Interface Daughter Card, 1*1
              subbname8090P4UFZ(561237),   -- 4-port 2.5G POS SFP Flexible Pluggable Interface Daughter Card, 1*1
              subbname8090P4HFZ(561238),   -- 4-port 622M POS SFP Flexible Pluggable Interface Daughter Card, 1*1
            subbname8090P8HFZ(561239),   -- 8-port 622M POS SFP Flexible Pluggable Interface Daughter Card, 1*1
            subbname8090P4CFZ(561240),   -- 4-port 155M POS SFP Flexible Pluggable Interface Daughter Card, 1*1
            subbname8090P8CFZ(561241),   -- 8-port 155M POS SFP Flexible Pluggable Interface Daughter Card, 1*1
             subbname8090C2CF(561242) ,    -- 2-Port Channelized OC-3c/STM-1c POS-SFP Flexible Card
             subbname80904E3CT3(561243),  -- 4-Port Clear Channel E3/Channelized T3-SMB Flexible Card
             subbname80908CE1CT1(561244), -- 8-Port Channelized E1/T1-RJ45 Flexible Card
             subbname8090P1XXB(561245),    -- 1 port OC-192c/STM-64c POS-XFP Flexible Card
             subbname8090OFCA(561246),               -- Cluster Optical Flexible Card A
            subbname8090CR53P1MZ(561247),               --1-port 40G POS XFP  Flexible Pluggable Interface Daughter Card
            subbname809055EMFE(561248),  -- 48-Port 10/100Base-TX-Delander Flexible Card
            subbname8090CR53E4XX(561249),               --4-port Eth Interface Daughter Card
            subbname8090CR52CKGFY(561250),   --40-port GF card
            subbname8090CR52EBGFB(561251),   --12-port GF card
            subbname8090CR52L1XXB(561252),   --1-port 10G LAN/WAN card
            subbname8090CR53D1MV(561253),               --1-port 40G WDM POS XFP  Flexible Pluggable Interface Daughter Card
            subbname8090CR53E8GFB(561254),   --8-port 100/1000Base-X SFP Flexible Interface Daughter Card
            subbname8090CR52EEGFN(561255),   --20-Port 100/1000Base-X-SFP Flexible Card
            subbname8090CR52EEGFNB(561256),  --20-Port 100/1000Base-X-SFP Flexible Card B
            subbname8090CR52L2XXN(561257),   --2-Port 10GBase WAN/LAN-XFP Flexible Card
            subbname8090CR52L2XXNB(561258),  --2-Port 10GBase WAN/LAN-XFP Flexible Card B
            subbname8090CR52L2XEEG(561259),  --2-Port 10GBase WAN/LAN-XFP and 20-Port 100/1000Base-X-SFP Flexible Card
            subbname8090CR52L2XEEGB(561260), --2-Port 10GBase WAN/LAN-XFP and 20-Port 100/1000Base-X-SFP Flexible Card B
            subbname8090CR53A4CFB(561261),   --4-Port OC-3c/STM-1c ATM-SFP Flexible Card
                subbname8090ME03E1XX(561262),     --1-Port 10G Ethernet LAN Card on LPUF-21
                subbname8090ME03EAGF(561263),     --10-Port Gigabit Ethernet Card on LPUF-21
                subbname8090CR55OFC40(561264),     --40G  Cluster Optical Flexible Card
            subbname8090CR52EKGFY(561265),        --40-port 1000Base-X-SFP card
             subbname8090ME03E6GFE(561266),        --6-Port 1000Base-SFP Flexible Card E
             subbname8090CR55OFC100A(561267),      --100G Cluster Optical Flexible Card A
         subbname8090CR55OFC100B(561268),      --100G Cluster Optical Flexible Card B

                subbname8090DEVCR57F4EFGF(561269),    --LPUF-40/41 24*GE SFP Optical Flexible Card, no 1588
                subbname8090DEVCR57F4L4XX(561270),    --LPUF-40/41 4*10GE convergence Flexible Card, no 1588
                subbname8090DEVCR57P2XXB(561271),     --LPUF-40/41 2*10G POS 1/2 width
                subbname8090DEVCR56L5XX(561272),      --LPUF-100/101 5*10GE 1/2 width, support 1588
                subbname8090DEVCR56L2XX(561273),      --LPUF-100/101 2*10GE 1/4 width, support 1588
                subbname8090DEVCR56D2XX(561274),      --LPUF-100/101 2*10G POS/OTN 1/4
                subbname8090DEVCR56P1MZ(561275),      --LPUF-100/101 1*40G POS 1/2
                subbname8090DEVCR56E4XF(561276),      --LPUF-101 4*10GE 1/4 width convergence, no 1588
                subbname8090DEVCR57EMGF(561277),      --LPUF-101 48*10GE 1/2 width BIDI, no 1588
                subbname8090DEVCR57EEGE(561278),      --LPUF-40/41 20*GE RJ45 1/2 width, no 1588
                subbname8090DEVCR56E1NC(561279),      --LPUF-101 1*100GE, test only
                subbname8090DEVCR57L2XXY(561280),     --LPUF-40/41 2*10GE TM card, support BRAS HQOS
                subbname8090DEVCR57EEGFY(561281),     --LPUF-40/41 20*GE TM card, support BRAS HQOS
                subbname8090DEVCR56P2XX(561282),      --LPUF-100/101 2*10G POS 1/4 width
                subbname8090DEVCR57EEGFB(561283),     --LPUF-41 20*GE SFP Optical card, 1/2 width, support 1588 and Y.1731
                subbname8090DEVCR57EFGF(561284),      --LPUF-100 24*GE SFP Optical card, 1/2 width, no 1588
                subbname8090DEVCR53L2XFA(561285),     --LPUF-50 2*10GE SFP Optical card,Support 1588
                subbname8090DEVCR57L5XF(561286),      --LPUF-101 5*10GE SFP+ Optical card, 1/2 width, no 1588
                subbname8090DEVCR57L2XXY1(561287),    --LPUF-40/41 2*10GE DPI card
                subbname8090DEVCR5D0L2XFA70(561288),  --2-Port 10GBase LAN/WAN-SFP+ Flexible Card A(P50-A,Occupy one sub-slot)
                subbname8090DEVCR57L1XEAG(561289),     --LPUF-41 1*10GE LAN/WAN XFP + 10*GE SFP Optical card, support 1588
                subbname8090CR5M0L1XXB20(561290),     --1-Port 10GBase LAN/WAN-XFP Flexible Card B(P20-B)
                subbname8090DEVCR56E1NCC(561291),     --CR56E1NCC0,1-Port 100GBase-CFP Flexible Card(NE5000E LPUF-200,2 sub-slots)
                subbname8090DEVCR56E1MC(561292),      --CR56E1MCA0,1-Port 40GBase-CFP Flexible Card(NE5000E LPUF-100,2 sub-slots)
                subbname8090DEVCR56LAXFA(561293),     --CR56L5XXA0,5-Port 10GBase LAN/WAN-XFP Flexible Card(CP100,2 sub-slots)
                subbname8090DEVCR5D00E8GF70(561294),  --CX600,CX67E8GF0,8-Port 100/1000Base-X-SFP High-speed Interface Card(HIC)
                subbname8090DEVCR5D0E8GFA70(561295),  --CX600,CX67E8GFB0,8-Port 100/1000Base-X-SFP High-speed Interface Card (HIC,Supporting 1588v2)
                subbname8090DEVCR5D00E8FE10(561296),  --CX600,CX67E8FE0,8-Port 100Base-X-RJ45 Flexible Interface Card (FIC,Supporting 1588v2)
                subbname8090DEVCR5D00E8FF10(561297),  --CX600,CX67E8FF0,8-Port 100Base-X-SFP Flexible Interface Card(FIC,Supporting 1588v2)
                subbname8090DEVCR5D00C1CF10(561298),  --CX600,CX67C1CF0,1-Port Channelized OC-3c/STM-1c POS-SFP Flexible Interface Card (FIC)
                subbname8090DEVCR5D000DE111(561299),  --CX600,CX67DE1A0,16-Port E1 Flexible Interface Card(FIC,120ohm)
                subbname8090DEVCR5D000DE110(561300),  --CX600,CX67DE10,16-Port E1 Flexible Interface Card(FIC,75ohm)
                subbname8090DEVCR5M0L5XFA71(561301),   --5-Port 10GBase LAN/WAN-SFP+ Flexible Card(P101-A,Occupy two sub-slots)
                subbname8090DEVCR5D00E2NC70(561302),   --2-Port 100GBase LAN-CFP Integrated Line Processing Unit (LPUI-200)
                subbname8090DEVCR5D00LEXF70(561303),   --20-Port 10GBase LAN/WAN-SFP+ Integrated Line Processing Unit (LPUI-200)
                subbname8090DEVCR5D00E2NC71(561304),   --2-Port 100GBase LAN-CFP Integrated Line Processing Unit (LPUS-200)
                subbname8090DEVCR5D00LEXF71(561305),   --20-Port 10GBase LAN/WAN-SFP+ Integrated Line Processing Unit (LPUS-200)
                subbname8090DEVCX6D0L2XFA10(561306),   --2-Port 10GBase LAN/WAN-SFP+ Flexible Card A(S50-A)
                subbname8090DEVCX6D0L5XFA10(561307),   --5-Port 10GBase LAN/WAN-SFP+ Flexible Card A(S51-A,Occupy two sub-slots)
                subbname8090DEVCX6D0L2XFA11(561308),   --2-Port 10GBase LAN/WAN-SFP+ Flexible Card A(S51-A)
                subbname8090DEVCX6D0L5XFA11(561309),   --5-Port 10GBase LAN/WAN-SFP+ Integrated Integrated Service Unit (ISUI-51,Supporting 1588v2,40Gbps is enabled by default)
                subbname8090DEVCX6D0EMGFA10(561310),   --48-Port 100/1000Base-X-SFP Integrated Integrated Service Unit (ISUI-51,Supporting 1588v2)
                subbname8090DEVCX6DL2XEIG1A(561311),   --2-Port 10GBase LAN/WAN-SFP++32-Port 100/1000Base-X-SFP Integrated Integrated Service Unit (ISUI-51,Supporting 1588v2,40Gbps is enabled by default)
                subbname8090DEVCX6D0L5XFA12(561312),   --5-Port 10GBase LAN/WAN-SFP+ Flexible Card A(S101-A,Occupy two sub-slots)
                subbname8090DEVCX6D0EFGFA10(561313),   --24-Port 100/1000Base-X-SFP Flexible Card A(S51-A)
                subbname8090DEVCX6D0LAXFA11(561314),   --10-Port 10GBase LAN/WAN-SFP+ Integrated Integrated Service Unit (ISUI-101,Supporting 1588v2)
                subbname8090DEVCR5M00L2XF70(561315),   --2-Port 10GBase WAN/LAN-SFP+ Flexible Card A
                subbname8090DEVCR5M00EFGF70(561316),   --24-Port 100/1000Base-SFP Flexible Card
                subbname8090DEVCR5M00E5XF70(561317),   --5-Port 10GBase LAN/WAN-SFP+ Flexible Card A
                subbname8090DEVCR5M00E2XF70(561318),   --2-Port 10GBase LAN/WAN-SFP+ Flexible Card A
                subbname8090DEVCR5D00L5XF70(561319),   --5-Port 10GBase LAN/WAN-SFP+ Integrated Line Processing Unit (LPUI-51,Supporting 1588v2)
                subbname8090DEVCR5D00L4XF70-LPUI(561320),   --4-Port 10GBase LAN/WAN-SFP+ Integrated Line Processing Unit (LPUI-51,Supporting 1588v2)
                subbname8090DEVCR5D00EMGF70(561321),   --48-Port 100/1000Base-SFP  Integrated Line Processing Unit (LPUI-51,Supporting 1588v2)
                subbname8090DEVCR5DEFGL2X70(561322),   --24-Port 100/1000Base-X-SFP 2-Port 10GBase LAN/WAN-X-SFP Integrated Line Processing Unit (LPUI-51,Supporting 1588v2)
                subbname8090DEVCR5D00L5XF71(561323),   --5-Port 10GBase LAN/WAN-SFP+ Integrated Line Processing Unit (LPUS-51)
                subbname8090DEVCR5D00L4XF71(561324),   --4-Port 10GBase LAN/WAN-SFP+ Integrated Line Processing Unit (LPUS-51)
                subbname8090DEVCR5D00EMGF71(561325),   --48-Port 100/1000Base-SFP  Integrated Line Processing Unit (LPUS-51)
                subbname8090DEVCR5DEFGL2X71(561326),   --24-Port 100/1000Base-X-SFP 2-Port 10GBase LAN/WAN-X-SFP Integrated Line Processing Unit (LPUS-51)
                subbname8090DEVCR5M00EFGF10(561327),   --24-Port 100/1000Base-X-SFP Flexible Card(Occupy two sub-slots)
                subbname8090DEVCR5M00L5XF71(561328),   --5-Port 10GBase LAN/WAN-SFP+ Flexible Card A(Supporting 1588v2)
                subbname8090DEVCR5M00E1MC70(561329),   --1-Port 40GBase LAN-CFP Flexible Card (Supporting 1588v2)
                subbname8090DEVCR5D00E2MC70(561330),   --2-Port 40GBase LAN-CFP Integrated Line Processing Unit (LPUI-101,Supporting 1588v2)
                subbname8090DEVCR5D00LAXX72(561331),   --10-Port 10GBase LAN/WAN-XFP Integrated Line Processing Unit (LPUI-101,Supporting 1588v2)
                subbname8090DEVCR5D00E2MC71(561332),   --2-Port 40GBase LAN-CFP Integrated Line Processing Unit (LPUI-101)
                subbname8090DEVCR5D00LAXX73(561333),   --10-Port 10GBase LAN/WAN-XFP Integrated Line Processing Unit (LPUI-101)
                subbname8090DEVVSUF80(561334),    --SPU2.0 Board Sub Card(VSUF80)
                subbname8090DEVCR52OFCV(561335),       --Cluster Virtual Optical Card

                -- for V800R003C00 Card SBOM
                subbname8090DEVCR5D00P2XX60(561336),   -- 2-Port OC-192c/STM-64c POS/OTU2-XFP Flexible Card(Dynamic switch between POS and OTN)(CP100,1 sub-slot)
                subbname8090DEVCR5M00E1MC60(561343),   -- 1-Port 40GBase-CFP Flexible Card(NE5000E LPUF-100,2 sub-slots)
                subbname8090DEVCR5D0OFCA060(561344),   -- 100G Cluster Optical Flexible Card B
                subbname8090DEVCR5M0OFCK050(561345),   -- 400G Cluster Optical Flexible Card A
                subbname8090DEVCR55OFC400B(561413),   -- 400G Cluster Optical Flexible Card B
                subbname8090DEVCR50OFC400C(561414),   -- 400G Cluster Optical Flexible Card C

                -- from 561348 to 561393 is for V6R6 packing card
                -- for NE40E
                subbname8090DEVNE40ECR5D0L2XFA70(561348),   --2-Port 10GBase WAN/LAN-SFP+ Flexible Card A
                subbname8090DEVCR5D00A8CF70(561349),   --8-Port OC-3c/STM-1c ATM-SFP Flexible Card
                subbname8090DEVCR5D00C8CF71(561350),   --8-Port Channelized OC-3c/STM-1c POS-SFP Flexible Card
                subbname8090DEVCR5D00C4CF70(561351),   --4-Port Channelized OC-3c/STM-1c POS-SFP Flexible Card
                subbname8090DEVCR53CFE1(564527),   --24-Port Channelized E1/T1-DB100 Flexible Card
                subbname8090DEVCR5D0EFGFA70(561352),   --24-Port 100/1000Base-X-SFP Flexible Card A(P51-A)
                subbname8090DEVCR5D0L5XFA70(561353),   --5-Port 10GBase LAN/WAN-SFP+ Flexible Card A(P51-A, Occupy two slots)
                subbname8090DEVCR5D0L2XFA71(561354),   --2-Port 10GBase LAN/WAN-SFP+ Flexible Card A(P51-A)
                subbname8090DEVCR5D0L5XFA72(561355),   --5-Port 10GBase LAN/WAN-SFP+ Flexible Card A(P101-A,Occupy two sub-slots)
                subbname8090DEVCR5D0EFGFA71(561356),   --24-Port 100/1000Base-X-SFP Flexible Card A(P101-A,Occupy two sub-slots)
                subbname8090DEVCR5D00E1MC70(561357),   --1-Port 40GBase LAN-CFP Flexible Card (P101-A,Occupy two sub-slots)
                subbname8090DEVCR57L5XFC0(561360),   --5-Port 10GBase LAN/WAN-SFP+ card
                subbname8090DEVCR57L4XEBG0(561361),   --4-Port 10GBase LAN/WAN-SFP++12-Port 100/1000Base-X-SFP card
                subbname8090DEVCR57L2XEIG0(561362),   --2-Port 10GBase LAN/WAN-SFP++32-Port 100/1000Base-X-SFP card
                subbname8090DEVCR57EMGFC0(561363),   --48-Port 100/1000Base-X-SFP card
                subbname8090DEVCR57EFGFC0(561364),   --24-Port 100/1000Base-X-SFP card
                subbname8090DEVCR57L1XEDG0(561365),   --1-Port 10GBase LAN/WAN-SFP++16-Port 100/1000Base-X-SFP card
                subbname8090DEVCR57L4XFC0(561367),   --4-Port 10GBase LAN/WAN-XFP card
                subbname8090DEVCR57L2XEEGB0(561368),   --2-Port 10GBase LAN/WAN-XFP+20-Port 100/1000Base-X-SFP card
                subbname8090DEVCR57EKGFD0(561369),   --40-Port 100/1000Base-X-SFP card
                subbname8090DEVCR57L4XFB2(561370),   --4-Port 10GBase LAN/WAN-SFP+ Card (Occupy two slots)
                subbname8090DEVCR57L5XFB2(561371),   --5-Port 10GBase LAN/WAN-SFP+ Card (Occupy two slots)
                subbname8090DEVCR57EFGFB2(561372),   --24-Port 100/1000Base-X-SFP Card
                subbname8090DEVCR57L2XFC2(561373),   --2-Port 10GBase LAN/WAN-SFP+ Card
                subbname8090DEVCR57E1MCB2(561374),   --1-Port 40GBase LAN-CFP card
                subbname8090DEVCR57E1NC0(561375),    --1-Port 100GBase-CFP card

                --V6R7 card packing NE&oversea CX
                subbname8090DEVCR57EIGF0(561376),        --32 Ports FE/GE card
                subbname8090DEVCR5D0L2XFE70(561377),     --2-Port 10GBase LAN/WAN-SFP+ Flexible Card E(P51-E)
                subbname8090DEVCR5D0L5XFE70(561378),     --5-Port 10GBase LAN/WAN-SFP+ Flexible Card E(P51-E, Occupy two slots)
                subbname8090DEVCR5D0EEGEA70(561379),     --20-Port 10/100/1000Base-RJ45 Flexible Card(P51-A)
                subbname8090DEVCR5D0L5XFE71(561380),     --5-Port 10GBase LAN/WAN-SFP+ Flexible Card E(P101-E)
                subbname8090DEVCR5D00LBXF72(561381),     --12-Port 10GBase LAN/WAN-SFP+ Flexible Card A(P120-A)
                subbname8090DEVCR5D0L6XFA70(561382),     --6-Port 10GBase LAN/WAN-SFP+ Flexible Card A(P101-A)
                subbname8090DEVCR5D00E1NC75(561383),     --1-Port 100GBase-CFP Flexible Card (P120)
                subbname8090DEVCR5D00LBXF71(561384),     --12-Port 10GBase LAN/WAN-SFP+ Flexible Card A(P240-A)
                subbname8090DEVCR5D00T4XF70(564522),   -- CR5D00T4XF70, 4-Port OTU2-SFP+ Physical Interface Card(PIC)
                subbname8090DEVCR2D00T4XF70(564524),   -- CR2D00T4XF70, 4-Port OTU2-SFP+ Physical Interface Card(PIC)
                subbname8090DEVCR5D00E1MF70(564523),   -- CR5D00E1MF70, 1-Port 40GBase-CFP Physical Interface Card(PIC)
                subbname8090DEVCR2D00E1MF70(564525),   -- CR2D00E1MF70, 1-Port 40GBase-CFP Physical Interface Card(PIC)
                subbname8090DEVCR57E8NCB0(561561),   --8*100Gbps CFP2 Interface Board
                subbnameCR53P8CF(659454),  --8-Port OC-3c/STM-1c POS-SFP Flexible Card
                subbnameCR5D00P2CF70(659455),  --2-Port OC-3c/STM-1C POS SFP Flexible Card
                subbname8090DEVCR5M0E8GFA30(561555),   --8-Port 100/1000Base-X-SFP Flexible Card A(P10-A,Supporting 1588v2)
                subbname8090DEVCR5D00C2CF70(564526),   --4-Port Channelized OC-3c/STM-1c POS-SFP Flexible Card
                subbname8090DEVCR5D00LAXF70(561548), -- 10-Port 10GBase LAN/WAN-SFP+ Flexible Card A(P240-A)
                subbname8090DEVCR5D00D2NT70(561549), -- 2-Port 100GE Tunable DWDM Integrated Line Processing Unit (LPUI-200)
               subbname8090DEVCX6D00EAGF10(561556), -- CX68EAGFD, 10-Port 100/1000Base-X-SFP Service Interface Card(SIC)
               subbname8090DEVCX6DL1XE8G11(561557), -- CX68L1XE8GFB, 1-Port 10GBase LAN/WAN-SFP+ + 8-Port 100/1000Base-X-SFP Service Interface Card(SIC)
               subbname8090DEVCX6D00E8GE11(561558), -- CX68E8GED, 8-Port 100/1000Base-RJ45 Service Interface Card(SIC)
               subbname8090DEVCX6D00L4XF11(561559), -- CX68L4XFD, 4-Port 10GBase LAN/WAN-SFP+ Service Interface Card(SIC)
               subbname8090DEVCX6D00L2XF11(561560), -- CX68L2XFC, 2-Port 10GBase LAN/WAN-SFP+ Service Interface Card(SIC)
               subbnameATNTND1EF8T(225625),       --8 Channels Fast Ethernet Electric Interface Board
               subbnameATNNED1EG4F(225626),       --4 Channels FE/GE Adaptive Optical Interface Board
               subbnameATNNED1EG4T(225627),       --4 Channels FE/GE Adaptive Electronic Interface Board
               subbnameATNNED1EM4TP(225628),      --4 Channels GE/FE PoE Electrical Interface Board
               subbnameATNNED3ML1A(225629),      --16 Channels E1 Interface Board(75ohm)
               subbnameATNNED3ML1B(225630),      --16 Channels E1 Interface Board(120ohm)
               subbnameATNNED2ML1A(225631),      --16 Channels E1 Interface Board(75ohm)
               subbnameATNNED2ML1B(225632),      --16 Channels E1 Interface Board(120ohm)
               subbnameATNTND1SQ1(225634),        --4 Channels Channelized OC-3c/STM-1c POS Optical Interface Board
               subbnameATNNED1MPAA(225635),       --4-Channel FXS/FXO+2-Channel E&M+2-Channel RS232+2-Channel RS485 Board
               subbnameATNNED1MP8A(225636),       --4 Channels C37.94 Optical Interface and 4 Channels CoDir64K Electric Interface Board
               subbnameATNNED1SA8(225637),        --8-Channel V.35/X.21/V.24 Board
               subbnameATNNED1AT6(225638),        --6 Channes E&M Interface Board

               subbname8090DEVCX6D00E4XF25(580903), -- CX6D00E4XF25, 4-Port 25GE(SFP28)/10GE(SFP+) Interface Card (PIC)
               subbname8090DEVCX6D0E5XMF90(580904), -- CX6D0E5XMF90, 2-Port 50GBase/1-Port 100GBase-QSFP28 Physical Interface Card(PIC)
               subbname8090DEVCX6D00E4XF20(580905), -- CX6D00E4XF20, 4-Port 10GBase-SFP+MACsec Interface Card
               subbname8090DEVCX6D00E1NB20(580906), -- CX6D00E1NB20, 1-Port 100GBase-QSFP28+MACsec Interface Card
               subbname8090DEVCX6DE2NE4X12(580907), -- CX6DE2NE4X12, 2-Port 100GBase-QSFP28/1-Port100GBase-QSFP28+4-Port 10GBase-SFP+MACsec Interface Card
               subbname8090DEVCX6D00E1NC98(580908), -- CX6D00E1NC98, 1-Port 100GBase-CFP2 Physical Interface Card(PIC)
               subbname8090DEVCX6D00LAXF90(580909), -- CX6D00LAXF90, 10-Port 10GBase LAN/WAN-SFP+ Physical Interface Card(PIC)
               subbname8090DEVCX6D0L2XFE71(580910), -- CX6D0L2XFE71, 2-Port 10GBase LAN/WAN-SFP+ Physical Interface Card E(PIC-E)

               subbname8090DEVCR5D00A2CF70(570047), -- CR5D00A2CF70, 2-Port OC-3c/STM-1c ATM-SFP Physical Interface Card
              subbname8090DEVCR2D00A2CF10(570048), -- CR2D00A2CF10, 2-Port OC-3c/STM-1c ATM-SFP Physical Interface Card
             subbname8090DEVCR5D00EEGF70(561562),       -- CX68EEGFAE, 20-Port 100/1000Base-X-SFP  Physical Interface Card(PIC)
             subbname8090DEVCR2D00EEGF10(675896),       -- CX68EEGFAE, 20-Port 100/1000Base-X-SFP Physical Interface Card
               subbname8090DEVME2D00E8GE12(570001),    -- ME2D00E8GE12, 8-Port 100/1000Base-RJ45 Physical Interface Card
               subbname8090DEVME2D00EAGF10(570002),    -- ME2D00EAGF10, 10-Port 100/1000Base-X-SFP Physical Interface Card
               subbname8090DEVME2D00L4XF11(570003),    -- ME2D00L4XF11, 4-Port 10GBase LAN/WAN-SFP+ Physical Interface Card
               subbname8090DEVME2DL1XE8G11(570004),    -- ME2DL1XE8G11, 1-Port 10GBase LAN/WAN-SFP+ + 8-Port 100/1000Base-X-SFP Physical Interface Card
               subbname8090DEVME2D00L2XF12(570005),    -- ME2D00L2XF12, 2-Port 10GBase LAN/WAN-SFP+ Physical Interface Card
               subbname8090DEVCR2D00C1CF11(570006),    -- CR2D00C1CF11, 1-Port Channelized STM-1c POS-SFP Physical Interface Card
               subbname8090DEVME0D00E8GE71(570007),    -- 8-Port 100/1000Base-RJ45 Physical Interface Card(PIC)
               subbname8090DEVME0D00EAGF70(570008),    -- 10-Port 100/1000Base-X-SFP  Physical Interface Card(PIC)
               subbname8090DEVME0D00L4XF72(570009),    -- 4-Port 10GBase LAN/WAN-SFP+  Physical Interface Card(PIC)
               subbname8090DEVME0DL1XE8G71(570010),    -- 1-Port 10GBase LAN/WAN-SFP+ + 8-Port 100/1000Base-X-SFP Physical Interface Card(PIC)
               subbname8090DEVME0D00L2XF71(570011),    -- 2-Port 10GBase LAN/WAN-SFP+  Physical Interface Card(PIC)
               subbname8090DEVME0D00L4XF70(570012),    -- 4-Port 10GBase LAN-SFP+  Physical Interface Card(PIC)
               subbname8090DEVME0DL1XE8G70(570013),    -- 1-Port 10GBase LAN/WAN-SFP+ + 8-Port 100/1000Base-X-SFP Physical Interface Card(PIC)
               subbname8090DEVME0D00L2XF70(570014),    -- 2-Port 10GBase LAN/WAN-SFP+  Physical Interface Card(PIC)
               subbname8090DEVME0D00E8GF71(570015),    -- 8-Port 100/1000Base-X-SFP  Physical Interface Card(PIC)
               subbname8090DEVME0D00E8GE70(570016),    -- 8-Port 100/1000Base-RJ45 Physical Interface Card(PIC)
               subbname8090DEVME0D00C4CF71(570017),    -- 4-Port Channelized STM-1c POS-SFP  Physical Interface Card(PIC)
               subbname8090DEVME0D000IE170(570018),    -- 32-Port E1 Physical Interface Card(PIC,75ohm)
               subbname8090DEVME0D000IE171(570019),    -- 32-Port E1 Physical Interface Card(PIC,120ohm)
               subbname8090DEVME0D000DE170(570020),    -- 16-Port E1 Physical Interface Card(PIC,75ohm)
               subbname8090DEVME0D000DE171(570021),    -- 16-Port E1 Physical Interface Card(PIC,120ohm)
               subbname8090DEVME0D00P4CF70(570022),    -- 4-Port OC-3c/STM-1c POS-SFP Flexible Interface Card(FIC)
               subbname8090DEVME0DP2C1HF70(570023),    -- 2-Port OC-3c/STM-1c (or 1-Port OC-12c/STM-4C) POS-SFP  Physical Interface Card(PIC)
               subbname8090DEVME0D00AUXQ10(570024),    -- Auxiliary  Flexible Interface Card with 4-Port 100Base-RJ45 (FIC,Supporting 1588v2)
               subbname8090DEVME0D08CWDM70(570025),    -- 8-Channel CWDM Multiplexing & Demultiplexing (1471/1491/1511/1531/1551/1571/1591/1611nm) Physical Interface Card(PIC)
               subbname8090DEVME0D00C4T370(570026),    -- 4-Port Clear Channel E3/Channelized T3 Physical Interface Card (PIC)
               subbname8090DEVME0D0L2XFH71(570027),    -- 2-Port 10GBase LAN/WAN-SFP+  Physical Interface Card H (PIC-H)
               subbname8090DEVME0D0EAGFH70(570028),    -- 10-Port 100/1000Base-X-SFP  Physical Interface Card H (PIC-H)
              subbname8090DEVANKD001EV106(225822),   --1 Channel 50G Base QSFP28 High Speed Interface Board
               subbname8090DEVCR5D00P2XX72(570030),     --2-Port OC-192c/STM-64c POS-XFP Flexible Card(P51-A)
               subbname8090DEVCR57L4XEBGFB(570031),     --4-Port 10GBase LAN/WAN-SFP++12-Port 100/1000Base-X-SFP Integrated Integrated Service Unit B(ISUI-51-B,Supporting 1588v2)
               subbname8090DEVCR57TBXF00(570032),         --12-Port OTU2-SFP+ Fixed Card
               subbname8090DEVCR57T6XF00(570033),         --6-Port OTU2-SFP+ Fixed Card(P120)


               subbname8090DEVCR57L6XE4GF0(537714),  -- 6-Port 10GBase LAN/WAN-SFP+ + 4-Port 100/1000Base-X-SFP Fixed Card
               subbname8090DEVCR57E4GFC0(537715),    -- 4-Port 100/1000Base-X-SFP Fixed Card A
               subbname8090DEVCX6D0EFGFA12(570034),       -- CX6D0EFGFA12,24-Port 100/1000Base-X-SFP Integrated Integrated Service Unit (ISUI-21,Supporting 1588v2)
               subbname8090DEVCX6DL1XEDG1A(570038),       -- CX6DL1XEDG1A,1-Port 10GBase LAN/WAN-SFP++16-Port 100/1000Base-X-SFP Integrated Integrated Service Unit (ISUI-21,Supporting 1588v2)
               subbname8090DEVCR5D0EFGFA73(570039),       -- CR5D0EFGFA73,24-Port 100/1000Base-X-SFP Integrated Integrated Service Unit (ISUI-21,Supporting 1588v2)
               subbname8090DEVCR5DL1XEDG70(570040),       -- CR5DL1XEDG70,1-Port 10GBase LAN/WAN-SFP++16-Port 100/1000Base-X-SFP Integrated Integrated Service Unit (ISUI-21,Supporting 1588v2)
               subbname8090DEVCR53P4UF0(570043),           -- CR53P4UF0,4-Port OC-48c/STM-16c POS-SFP Flexible Card
               subbname8090DEVCR53P2UF0(570044),           -- CR53P2UF0,2-Port OC-48c/STM-16c POS-SFP Flexible Card
               subbname8090DEVCR53P8HF0(570045),           -- CR53P8HF0,8-Port OC-12c/STM-4c POS-SFP Flexible Card
               subbname8090DEVCR53P1XX0(570046),           -- CR53P1XX0,1-Port OC-192c/STM-64c POS-XFP Flexible Card(Occupy two slots)
                -- for CX600 local
                subbname8090DEVLOCALCX6D0L2XFA10(561385),   --2-Port 10GBase LAN WAN-SFP+ Flexible Card A(S50-A)
                subbname8090DEVCX6D00A8CF10(561386),   --8-Port OC-3c STM-1c ATM-SFP Flexible Card(S50)
                subbname8090DEVCX6D00C8CF10(561387),   --8-Port Channelized OC-3c/STM-1c POS-SFP Flexible Card(S50)
                subbname8090DEVCX6D00C4CF10(561388),   --4-Port Channelized OC-3c/STM-1c POS-SFP Flexible Card(S50)
                subbname8090DEVLOCALCX6D0EFGFA10(561389),   --24-Port 100 1000Base-X-SFP Flexible Card A(S51-A)
                subbname8090DEVLOCALCX6D0L5XFA10(561390),   --5-Port 10GBase LAN WAN-SFP+ Flexible Card A(S51-A,Occupy two sub-slots)
                subbname8090DEVLOCALCX6D0L2XFA11(561391),   --2-Port 10GBase LAN WAN-SFP+ Flexible Card A(S51-A)
                subbname8090DEVLOCALCX6D0L5XFA12(561392),   --5-Port 10GBase LAN WAN-SFP+ Flexible Card A(S101-A,Occupy two sub-slots)
                subbname8090DEVCX6D0EFGFA11(561393),   --24-Port 100/1000Base-X-SFP Flexible Card A(S101-A,Occupy two sub-slots)
                subbname8090DEVVSUF160(561394),    --SPU2.0 Board Sub Card(VSUF160)
                subbname8090DEVDVSU2(561425),     --For V6R9C00 16G DVSU Card(VSUF160)

                -- for CX600 local V8R8 shoubian V8R5 561415-561419V8oid
                subbname8090DEVCX6D0LAXFA12(561442),   --10-Port 10GBase LAN/WAN-SFP+ Flexible Card A(S200-A) V5 561415
                subbname8090DEVCX6D0E3MFA10(561443),   --3-Port 40GBase-QSFP+ Flexible Card(S200-A)
                subbname8090DEVCX6D0E1NCA10(561444),   --1-Port 100GBase-CFP Flexible Card A(S102-A)
                subbname8090DEVCX6D0E1MCA10(561445),   --1-Port 40GBase LAN-CFP Flexible Card A(S102-A)
                subbname8090DEVME0D0LAXFB7H(561446),   --10-Port 10GBase LAN/WAN-SFP+ Flexible Card(BP240) V5 561419
                subbname8090DEVCR57L3XFA2(561447),   --3-Port 10GBase LAN/WAN-SFP+ Fixed Card
                -- for NE5000NE9000 V8R8C10 fixed card
                subbname8090DEVCR56E8NCB(561448),   -- NE5000E,CR56E8NCB,8*100Gbps CFP2 Interface Board
                subbname8090DEVCR56EFMBB(561449),   -- NE5000E,CR56EFMBB,24*40Gbps QSFP+ Interface Board
                subbname8090DEVCR58E8NCD(561450),   -- NE9000,CR58E8NCD,8-Port 100GBase-CFP2
                subbname8090DEVCR58EFMBD(561451),   -- NE9000,CR58EFMBD,24-Port 40GBase-QSFP+
                subbname8090DEVCR58EPXFB(561452),   -- NE9000,CR58EPXFB,60-Port 10GBase LAN/WAN-SFP+
                subbname8090DEVCR56EDNCV(561453),   -- NE5000E,CR56EDNCV,16-Port 100GBase-CFP4
                subbname8090DEVCR56EDNBV(561454),   -- NE5000E,CR56EDNBV, 16-Port 100GBase-QSFP28
                subbname8090DEVCR56E8NCE(561455),   -- NE5000E,CR56E8NCE , 8-Port 100GBase-CFP4
                subbname8090DEVCR56E8NLDXA(561456), --NE5000E,CR56E8NLDXA, 8-Port 100GBase-CFP4 + 16-Port 10GBase-QSFP+
                subbname8090DEVCR56EDNLIXV(561457), --NE5000E,CR56EDNLIXV, 16-Port 100GBase-QSFP28 + 32-Port 10GBase-QSFP+


                --for CX600 local(561398 is NE&oversea CX) V6R7 card packing
                subbname8090DEVCX6D0EEGEA10(561395),     --20-Port 10/100/1000Base-RJ45 Flexible Card(S51-A)
                subbname8090DEVCX6D0L6XFA10(561396),     --6-Port 10GBase LAN/WAN-SFP+ Flexible Card A(S120-A)
                subbname8090DEVCX6D0LBXFA10(561397),     --12-Port 10GBase LAN/WAN-SFP+ Flexible Card A(S120-A)
                subbname8090DEVCR5D00E1NC74(561398),     --1-Port 100GBase-CFP Flexible Card (P240)
                subbname8090DEVCR5D0EFGFE70(561399),     --24-Port 1000Base-X-SFP Flexible Card E(P51-E)
                subbname8090DEVL3XEFG7C(561400),         --3-Port 10GBase LAN/WAN-SFP+ Flexible Card A
                subbname8090DEVCR57EFGFE2(561401),       --24-Port 1000Base-X-SFP Fixed Card E
                subbname8090DEVCR57L2XFE2(561402),       --2-Port 10GBase LAN/WAN-SFP+ Fixed Card E
                subbname8090DEVCR57L5XFE2(561403),       --5-Port 10GBase LAN/WAN-SFP+ Fixed Card E
                subbname8090DEVCR57LBXF2(561404),        --12-port 10GBase LAN/WAN-SFP+ Fixed Card
                subbname8090DEVCR57E1NCB2(561405),        --1-Port 100GBase-CFP Fixed Card
                subbname8090DEVCR57L6XF0(561406),        --6-port 10GBase LAN/WAN-SFP+ Fixed Card
                subbname8090DEVCR57EFGFH0(561458),         --03031YYN, CR5D0EFGFH70, 24-Port 1000Base-X-SFP Flexible Card H(P51-H)
                subbname8090DEVME03EFGFH0(561459),         --03031YYT, ME0D0EFGFH7H, 24-Port 1000Base-X-SFP Flexible Card H(BP51-H)
                subbname8090DEVCR57L5XFI0(561460),         --03031XPT, CR5D0L5XFE70, 5-Port 10GBase LAN/WAN-SFP+ Flexible Card E(P51-E, Occupy two sub-slots)
                subbname8090DEVCR57L5XFI2(561461),         --03031XPU, CR5D0L5XFH71, 5-Port 10GBase LAN/WAN-SFP+ Flexible Card H(P51-H, Occupy two sub-slots)
                subbname8090DEVCR57L5XFI01(561462),        --03031XPV, CR5D0L5XFE71, 5-Port 10GBase LAN/WAN-SFP+ Flexible Card E(P101-E)
                subbname8090DEVCR57L5XFI02(561463),        --03031XPW, CR5D0L5XFH70, 5-Port 10GBase LAN/WAN-SFP+ Flexible Card H(P120-H)
                subbname8090DEVME03L5XFI1(561464) ,        --03031XPX, ME0D0L5XXE7F, 5-Port 10GBase LAN/WAN-SFP+ Flexible Card E(BP51-E,occupy 2 sub-slot)
                subbname8090DEVME03L5XFI2(561465),         --03031XPY, ME0D0L5XXH7F, 5-Port 10GBase LAN/WAN-SFP+ Flexible Card H(BP51-H,occupy 2 sub-slot)
                subbname8090DEVME03L5XFI0(561466),       --03031XQA, ME0D0L5XXE7H, 5-Port 10GBase LAN/WAN-SFP+ Flexible Card E(BP100-E)
                subbname8090DEVME03L5XFI3(561467),        --03031XQB, ME0D0L5XFH7H, 5-Port 10GBase LAN/WAN-SFP+ Flexible Card H(BP100-H)
                subbname8090DEVCR57L2XFI1(561468),         --03031YYP, CR5D0L2XFH70, 2-Port 10GBase LAN/WAN-SFP+ Flexible Card H(P51-H)
                subbname8090DEVCR57L2XFI0(561469),         --03031XQD, CR5D0L2XFE70, 2-Port 10GBase LAN/WAN-SFP+ Flexible Card E(P51-E)
                subbname8090DEVME03L2XFI0(561470),         --03031XQF, ME0D0L2XXE7H, 2-Port 10GBase LAN/WAN-SFP+ Flexible Card E(BP51-E)
                subbname8090DEVME03L2XFI1(561471),         --03031XQG, ME0D0L2XXE8H, 2-Port 10GBase LAN/WAN-SFP+ Flexible Card H(BP51-H)
                subbname8090DEVCR57EFGFH1(561472),         --03031XQJ, CR5D0EFGFE70, 24-Port 1000Base-X-SFP Flexible Card E(P51-E)
                subbname8090DEVME03EFGFH1(561473),         --03031XQM, ME0D0EFGFE7H, 24-Port 1000Base-X-SFP Flexible Card H(BP51-H)
                subbname8090DEVCX62L5XFH0(561474),         --03032AWL, CX6D0L5XFH10, 5-Port 10GBase LAN/WAN-SFP+ Flexible Card H(S102-H)
                subbname8090DEVBGW01L5XFH0(561475),        --03032AWM, BGWD0L5XFH71, 5-Port 10GBase LAN/WAN-SFP+ Flexible Card(BP100)
                subbname8090DEVCR57LAXFH0(561441) ,     --03031EAS, CX6D0LAXFH10, 10-Port 10GBase LAN/WAN-SFP+ Flexible Card H(S200-H)
                subbname8090DEVCR57L6XFI01(561476), --03031YYQ,  6-Port 10GBase LAN/WAN-SFP+ Flexible Card H(P120-H)
                subbname8090DEVME03L6XFI0(561477), --03031YYV,  6-Port 10GBase LAN/WAN-SFP+ Flexible Card H(BP120-H)
                subbname8090DEVCR57LBXFH1(561478), --03031YYS,  12-Port 10GBase LAN/WAN-SFP+ Flexible Card H(P240-H)
                subbname8090DEVME03LBXFH0(561479), --03031YYX,  12-Port 10GBase LAN/WAN-SFP+ Flexible Card H(BP200-H)
                subbname8090DEVCR57E1NCF0(561480), --03032GKY,  1-Port 100GBase-CFP2 Flexible Card A(P120-A)
                subbname8090DEVCR57E1NCF1(561481), --03032GLA,  1-Port 100GBase-CFP2 Flexible CardA (P240-A)
                subbname8090DEVME03E1NCF0(561482), --03032GLB,  1-Port 100GBase-CFP2 Flexible Card(BP100)
                subbname8090DEVME03E1NCF1(561483), --03032GLC,  1-Port 100GBase-CFP2 Flexible Card(BP240)
                subbname8090DEVCR57E1NCF2(561518), --03032GLD,  1-Port 100GBase-CFP2 Fixed Card
                subbname8090DEVTNR2EF1(561484),     --03032GLE,  1 Port 100 Gigabit Ethernet Processing Flexible Card (Supporting 1588v2)
                subbname8090DEVCX62E1NCF0(561485), --03032GLF,  1-Port 100GBase-CFP2 Flexible Card A(S102-A)
                subbname8090DEVCR57E1NBA0(561494), --CR5D00E1ND70, 1-Port 100GBase-QSFP28 Flexible Card A(P120-A)
                subbname8090DEVCR57E1NBA1(561495), --CR5D00E1ND73, 1-Port 100GBase-QSFP28 Flexible Card A(P240-A)
                subbname8090DEVCX62E1NBA0(561496), --CX6D0E1NDA10, 1-Port 100GBase-QSFP28 Flexible Card A(S102-A)
                subbname8090DEVME03E1NBA0(561497), --ME0D0E1NDB70, 1-Port 100GBase-QSFP28 Flexible Card(BP100)
                subbname8090DEVME03E1NBA1(561498), --ME0D0E1NDB71, 1-Port 100GBase-QSFP28 Flexible Card(BP240)
                subbname8090DEVCR5D0LEXFE71(561486),       --03032KGW,  20-Port 10GBase LAN/WAN-SFP+ Flexible Card H(P400-H)
                subbname8090DEVCR5D0E2NCE71(561487),      --03032KGV,  2-Port 100GBase-CFP2 Flexible Card H(P400-H)
                subbname8090DEVME0M0LEXFB71(561488),      --03032KGX,  20-Port 10GBase LAN/WAN-SFP+ Flexible Card H(BP400-H)
                subbname8090DEVME0M0E2NCB71(561489),      --03032KGY,  2-Port 100GBase-CFP2 Flexible Card H(BP400-H)
                subbname8090DEVCR5D0EAGFE70(561490),      --10-Port 100/1000Base-X-SFP Physical Interface Card E(PIC-E)
                subbname8090DEVCR2D0EAGFE10(561491),      --03032KLR,  10-Port 100/1000Base-X-SFP Physical Interface Card E(PIC-E)
                subbname8090DEVCR5D0L2XFE71(561492),      --2-Port 10GBase LAN/WAN-SFP+ Physical Interface Card E(PIC-E)
                subbname8090DEVCR2D0L2XFE10(561493),      --03032KLS,  2-Port 10GBase LAN/WAN-SFP+ Physical Interface Card E(PIC-E)
                subbname8090DEVCR9D00LFXF80(537455),    -- 24-Port 1000M/10GBase LAN/WAN-SFP+ Flexible Card
                subbname8090DEVCR9D00NBXF80(537456),    -- 12-Port 10G OTN/ETH-SFP+ Flexible Card
                subbname8090DEVCR9D00N6XF80(537457),    -- 6-Port 10G OTN/ETH-SFP+ Flexible Card
                subbname8090DEVCR9D00P8UF80(537458),    -- 8-Port OC-48/12/3 STM-16/4/1 POS-SFP Flexible Card
                subbname8090DEVCR9D00P4XX80(537459),    -- 4-Port OC-192/STM-64 POS-XFP Flexible Card
                subbname8090DEVCR5D00E5MF6B(537468),    -- 5-Port 40GBase-QSFP+ Flexible Card B(CP400,Occupy 1 sub-slot)
                subbname8090DEVCR5D00LEXF6B(537469),    -- 20-Port 10GBase LAN/WAN-SFP+ Flexible Card B(CP400,Occupy 1 sub-slot)
                subbname8090DEVCR57EFGFH3(537460),    -- 24-Port 1000Base-X-SFP Fixed Card E
                subbname8090DEVCR57L6XFI02(537461),   -- 6-Port 10GBase LAN/WAN-SFP+ Fixed Card E
                subbname8090DEVCR57LBXFE2(537462),    -- 12-Port 10GBase LAN/WAN-SFP+ Fixed Card E
                subbname8090DEVCR57E8NCB1(537463),    -- 8*100Gbps CFP2 Interface Board
             subbname8090DEVCR5D0LEXFE72(561520),    -- 20-Port 10GBase LAN/WAN-SFP+ Flexible Card A(P480-A)
             subbname8090DEVCR5D0LAXFE71(561521),    -- 10-Port 10GBase LAN/WAN-SFP+ Flexible Card A(P240-A)
             subbname8090DEVCR5D0L6XFE70(561522),    -- 6-Port 10GBase LAN/WAN-SFP+ Flexible Card E(P120-E)
             subbname8090DEVCR57E2NCF1(537493),         -- 2-Port 100GBase-CFP2 Fixed Card A
             subbname8090DEVCX6D000IT372(564517),       -- 4*T3 interface card
             subbname8090DEVCX6D00L1XE8GF70(564518),    -- 1x10GBase LAN/WAN-SFP+ 8x100/1000Base-X-SFP interface card
             subbname8090DEVCR56L5XFB1(688346),         -- 5-Port 10GBase LAN/WAN SFP+ Flexible Card(CP1T,Occupy 1 sub-slot)
             subbname8090DEVCR56L5XFK0(688347),         -- 5-Port 10GBase LAN/WAN SFP+ Flexible Card(CP1T,Occupy 1 sub-slot)
             subbname8090DEVCR56E3NBA0(688348),         -- 3-Port 100GBase QSFP28 Flexible Card(CP1T,Occupy 1 sub-slot)
             subbname8090DEVGPLI40CQES1(675822),         -- 40-Port 100GBase QSFP28 Integrated Line Process Unit
             subbname8090DEVGPLI72YSES1(675823),          -- 72-Port 25GE(SFP28)/10GE(SFP+)/GE(SFP) Integrated Line Processing Unit
             subbname8090DEVGPLI8KQ8CQES1(675824),    -- 8-Port 400GBase QSFPDD 8-Port 100GBase QSFP28 Integrated Line Process Unit
             subbname8090DEVGPLI40CQE2(675825),         -- 40-Port 100GBase QSFP28 Integrated Line Process Unit
             subbname8090DEVGPLI72YSE2(675826),         -- 72-Port 25GE(SFP28)/10GE(SFP+)/GE(SFP) Integrated Line Processing Unit
            subbname8090DEVGPLI8KQ8CQE2(675827),       -- 8-Port 400GBase QSFPDD 8-Port 100GBase QSFP28 Integrated Line Process Unit
            subbname8090DEVCR59E8NBM(719720),       -- 8-Port 100GBase QSFP28 Fixed card
            subbname8090DEVCR81VSUP100B1S(719702),   -- Multi-function Integrated Service Card(VSUP-100)
               subbname8090DEVCR81VSUP100B1(719703),   -- Multi-function Integrated Service Card(VSUPA-100)
               subbname8090DEVGPLI8KQ8CQE6(719704),       -- 8-Port 400GBase-QSFP-DD + 8-Port 100GBase-QSFP28 Integrated Line Processing Unit CM
               subbname8090DEVANKD001EV20A(719709),       -- 2 Channels 50G/1 Channel 100G Base QSFP28 High Speed Interface Board
               subbname8090DEVANKD001EV208(719710),       -- 2 Channels 50G/1 Channel 100G Base QSFP28 High Speed Interface Board
               subbname8090DEVGPI36YS10CQE2(719716),       -- 10-Port 100GBase-QSFP28 + 36-Port 25GE(SFP28)/10GE(SFP+)/GE(SFP) Integrated Line Processing Unit
               subbname8090DEVGPI40CQE3(719717),       -- 40-Port 100GBase-QSFP28 Integrated Line Processing Unit
               subbname8090DEVCR8DVSUFSPD0(719719),       -- Versatile Service Flexible Card E(SP800A-E-D)
               subbname8090DEVXHEDMSSP8HE1(210037),   -- V8R25C10 for XHEDMSSP8HE1(SBOM) Multi-Function Service Flexible Card E(MSP800A-E)
               subbname8090DEVXHEDMSSP8HS1(210038),   -- V8R25C10 for XHEDMSSP8HS1(SBOM) Multi-Function Service Flexible Card(MSP800A-S)
            subbname8090DEVANNDE4NB000(719750),  -- 4-Port 100GBase/50GBase-QSFP28 Physical Interface Card(PIC)
            subbname8090DEVCR8DVSUFWAE1(719751),  -- Versatile Service Flexible Card E(SP800A-E-G)
            subbname8090DEVCR8DE4LBFECP(719730),       -- 4-Port 800GBase-QSFP-DD FlexE MACsec Flexible Card CM(P6T4-CM)
            subbname8090DEVCR8DE4LBEECP(719731),       -- 4-Port 800GBase-QSFP-DD FlexE MACsec Flexible Card CM(P6T4-CM)
            subbname8090DEVCR8DE4LBELCP(719732),       -- 4-Port 800GBase-QSFP-DD FlexE MACsec Flexible Card L CM(P6T4-L-CM)
            subbname8090DEVCR8D8E4LBFC0(719733),       -- 4-Port 800GBase-QSFP-DD FlexE MACsec Flexible Card CM(P6T4-CM)
            subbname8090DEVCR8D8E4LBFL0(719734),       -- 4-Port 800GBase-QSFP-DD FlexE MACsec Flexible Card L CM(P6T4-L-CM)
            subbname8090DEVCR81VSUP100C1(719741),      -- CGN Versatile Service Flexible Card
            subbname8090DEVCR8DE1NE2VQ0(719743),       -- 2-Port 50GBase/1-Port 100GBase-QSFP28 Physical Interface Card(PIC)
            subbname8090DEVCR8D00EAGFQ0(719744),       --10-Port 100/1000Base-X-SFP  Physical Interface Card(PIC)
            subbname8090DEVCR5D00E8GEQ0(719745),       -- 8-Port 100/1000Base-RJ45 Physical Interface Card(PIC)
             subbnameCARDNetEngine8000M1A(333116),    --ATN910C-G virtual card,16*10GE(o), 12*GE /GE/FE(o),4*GE/FE(e)
            subbnameCARDATN910CK(333117),    --ATN910C-K virtual card,16*10GE(o), 8*GE /GE/FE(o),4*GE/FE(e)
            subbnameCARDATN910CM(333119),    --ATN910C-M virtual card,16*10GE(o), 8*GE /GE/FE(o),4*GE/FE(e)
            subbnameCARD2ATN910CK(333123),   --ATN910C-K virtual card,16E1
            subbnameCARDNetEngine8000M1C(333125),    --NetEngine8000 M1C virtual card,16*10GE(o), 8*GE /GE/FE(o),4*GE/FE(e)
            subbnameCARDNetEngine8000EM1A(333138),    --NetEngine8000E M1A
            subbnameCARDNetEngine8000EM1C(333139),    --NetEngine8000E M1C
            subbnameCARDNetEngine8000EM1D(333140),    --NetEngine8000E M1D
            subbname8090DEVCX6DE8VE4N10(225759),      --8-Port 50G/4-Port 100GBase-QSFP28 Flexible Card (P1T)
            subbname8090DEVCX62LEXFC00(225760),       --20-Port 10GBase LAN/WAN-SFP+ Integrated Integrated Service Unit
            subbname8090DEVCX62E2NBB00(225782),        --2-Port 100GBase-QSFP28 FlexE Integrated Integrated Service Unit
            subbname8090DEVCR5D000DE1C1(225775),      --16-Port E1 Physical Interface Card(PIC,75ohm/120ohm)
            subbname8090DEVCR5D00P4CFC1(225776),      --4-Port OC-3c/STM-1c POS-SFP Flexible Interface Card(FIC)
            subbname8090DEVCR5D00C4CFC1(225777),      --4-Port Channelized STM-1c POS-SFP Physical Interface Card(PIC)
            subbname8090DEVANND16E17500(225778),      --16 Channels E1 Interface Board
            subbname8090DEVANND00CQ1B00(225779),      --4 Channels Channelized OC-3c/STM-1c POS Optical Interface Board
            subbname8090DEVCR58EPYFA00(225780),       --60-Port 25GE-SFP28/10GE-SFP+ LAN/WAN MACSec Integrated Line Process Unit CM
            subbname8090DEVCR2D00E2NB00(225781),      --2-Port 100G/50G QSFP28 MACsec Interface Card
             subbname8090DEVCR5DE8VE4N70(225783),      --8-Port 50G/4-Port 100GBase-QSFP28 Flexible Card (P1T)
              subbname8090DEVCR57E4NBC00(225784),       --4-Port 50G/2-Port 100GBase or 4-Port 100GBase-QSFP28 FlexE/MACsec Integrated Line Processing Unit
              subbname8090DEVCR57E4NBC01(225785),       --4-Port 50G/2-Port 100GBase or 4-Port 100GBase-QSFP28 FlexE/MACsec Integrated Line Processing Unit
              subbname8090DEVCR57EKGFB01(225786),       --40-Port 100/1000Base-X-SFP or 10GBase LAN/WAN-SFP+ MACsec Integrated Line Process Unit
              subbname8090DEVCR57EKGFB00(225787),       --40-Port 100/1000Base-X-SFP or 10GBase LAN/WAN-SFP+ MACsec Integrated Line Process Unit
              subbname8090DEVCR57LEXEEGA00(225788),     --40-Port 100/1000Base-X-SFP or 10GBase LAN/WAN-SFP+ MACsec Integrated Line Process Unit
              subbname8090DEVANND0EM10F00(225789),      --10 Channels GE/FE Optical Interface Board
              subbname8090DEVANND0EM20F00(225790),      --20 Channels GE BIDI(CSFP)/10 Channels GE(SFP) Optical Interface Board
              subbname8090DEVCR5D00E1NC97(225791),      --1-Port 100GBase-CFP2 Physical Interface Card(PIC)
              subbname8090DEVCR5D00EEGF73(225792),      --20-Port 100/1000Base-X-CSFP/10-Port 100/1000Base-X-SFP Physical Interface Card(PIC)
              subbname8090DEVCR5D00EAGF95(225793),      --10-port 100/1000Base-X-SFP MACsec Physical Interface Card(PIC)
              subbname8090DEV910D-A(225794),            --CARD ATN 910D-A
              subbname8090DEV910D-B(115914),            --CARD ATN 910D-B
              subbname8090DEV910D-C(225978),            --CARD ATN 910D-C
              subbname8090DEVCR5D0E4YFM70(225795),       --4-Port 25GBase-SFP28 Flexible Card (P1T)
              subbname8090DEVCR5DE1NBFM70(225796),       --2-Port 50G/1-Port 100GBase-QSFP28 Flexible Card (P1T)
              subbname8090DEVCR5D0LFXFM70(225797),       --24-Port 10GBase-SFP+Flexible Card (P1T-E)
              subbname8090DEVCR5D0E8YFM70(225798),       --8-Port 25GBase-SFP28 Flexible Card (P1T)
              subbname8090DEVCR5DE2NBFM70(225799),       --4-Port 50G/2-Port 100GBase-QSFP28 Flexible Card (P1T)             
              subbname8090DEVCR5D0EFGFM70(225800),       --24-Port 1000Base-X-SFPFlexible Card (P1T)
              subbname8090DEVCR5D0LBXFM70(225801),       --12-Port 10GBase-SFP+ Flexible Card (P1T)
             subbname8090DEVGPI20CQE1(225802),          -- 20-Port 100GBase-QSFP28 Integrated Line Processing Unit    
             subbname8090DEVCR8D00E1NBC1(225804),      --1-Port 100GBase-QSFP28 FlexE MACsec Physical Interface Card(PIC)       
             subbname8090DEVANND001EN114(226001),      --1 Channel 100G Base QSFP28 High Speed Interface Board
             subbname8090DEVCR8D00E2VBC1(225805),      --2-Port 50GBase-QSFP28 FlexE MACsec Physical Interface Card(PIC)
             subbname8090DEVCR5D00C4CFC2(225806),      -- 4-Port Channelized STM-1c POS-SFP Physical Interface Card(PIC)
             subbname8090DEVCR8DC4CF00F0(225807),      -- 4-Port Channelized STM-1c POS-SFP Flexible Interface Card(PIC)
             subbname8090DEVCR8D00E2NBC1(225803),      --2-Port 100GBase-QSFP28 FlexE MACsec Physical Interface Card(PIC)       
             subbname8090DEVCR8D00E1VBC0(225808),       --1-port 50G Base (QSFP28) Physical Interface Card(PIC)       
             subbname8090DEVCR8D25E2XFC0(225809),       --2-port 25G (SFP28)/2 Channels 10G (SFP+) Physical Interface Card(PIC)       
             subbname8090DEVCR8D25E2XFC1(141601),       --2-port 25G (SFP28)/2 Channels 10G (SFP+) Physical Interface Card(PIC)
             subbname8090DEVCR8D00L4XFC5(115913),      --4-Port 10GE(SFP+)/GE(SFP) MACsec Physical Interface Card(PIC)
             subbname8090DEVME0D0LBXFM70(225819),       --12-Port 10GBase LAN/WAN-SFP+ MACsec Flexible Card(BP243)       
             subbname8090DEVME0D0E4YFM70(225821),       --4-Port 25GE(SFP28)/10GE(SFP+) MACsec Flexible Card (BP243)       
             subbname8090DEVME0DE1NBFM70(225824),       --2-Port 50GBase/1-Port 100GBase-QSFP28 FlexE/MACsec Flexible Card (BP243)       
             subbname8090DEVME0D0LFXFM70(225831),       --24-Port 10GBase LAN/WAN-SFP+ MACsec Flexible Card(BP483)       
             subbname8090DEVME0D0E8YFM70(225827),       --8-Port 25GE(SFP28)/10GE(SFP+) MACsec Flexible Card (BP483)       
             subbname8090DEVME0DE2NBFM70(225829),       --4-Port 50GBase/2-Port 100GBase-QSFP28 FlexE/MACsec Flexible Card (BP483)                
             subbname8090DEVME0D0EFGFM70(225817),       --24-Port 100/1000Base-X-SFP MACsec Flexible Card(BP53)       
             subbname8090DEVCX6D0LBXFM10(225820),       --12-Port 10GBase LAN/WAN-SFP+ MACsec Flexible Card(S243)       
             subbname8090DEVCX6D0E4YFM10(225823),       --4-Port 25GE(SFP28)/10GE(SFP+) MACsec Flexible Card(S243)       
             subbname8090DEVCX6DE1NBFM10(225825),       --2-Port 50GBase/1-Port 100GBase-QSFP28 FlexE/MACsec Flexible Card (S243)       
             subbname8090DEVCX6D0LFXFM10(225826),       --24-Port 10GBase LAN/WAN-SFP+ Flexible Card(S483)       
             subbname8090DEVCX6D0E8YFM10(225828),       --8-Port 25GE(SFP28)/10GE(SFP+) MACsec Flexible Card (S483)       
             subbname8090DEVCX6DE2NBFM10(225830),       --4-Port 50GBase/2-Port 100GBase-QSFP28 FlexE/MACsec Flexible Card (S483)                  
             subbname8090DEVCX6D0EFGFM10(225818),       --24-Port 100/1000Base-X-SFP MACsec Flexible Card(S53)       
             subbname8090DEVCR8D00L4XFC0(225813),       --4-Port 10GE(SFP+)/GE(SFP) MACsec Physical Interface Card(PIC))       
             subbname8090DEVCR8D00E2XFC0(225814),       --2-port 10GE(SFP+)/GE(SFP) Physical Interface Card(PIC)       
             subbname8090DEVCR8D00E2XFC1(115912),       --2-port 10GE(SFP+)/GE(SFP) Physical Interface Card(PIC)
             subbname8090DEVCR8D00EAGFC0(225815),       --10-port 100/1000Base-X-SFP MACsec Physical Interface Card(PIC)       
             subbname8090DEVCR8D00EEGFC0(225816),       --20-Port 100/1000Base-X-CSFP/10-Port 100/1000Base-X-SFP Physical Interface Card(PIC) 
             subbname8090DEVCR8D00EEGFC1(723820),       --20-Port 100/1000Base-X-CSFP/10-Port 100/1000Base-X-SFP Physical Interface Card(PIC)
             subbname8090DEVCR8D00EAGFC5(355930),       --10-port 100/1000Base-X-SFP MACsec Physical Interface Card(PIC)
              subbname8090DEVCR5D00C8CF72(225810),       --8-Port Channelized STM-1c POS-SFP Flexible Card(P1A)
              subbname8090DEVCR5D00P8CF70(225811),       --8-Port OC-3c/STM-1c POS-SFP Flexible Card(P1A)
              subbname8090DEVCR5D00CFE170(225812),       --24-Port Channelized E1/T1-DB100 Flexible Card(P1A)
              subbname8090DEVCR5D0E1NBF70(333121),       --2-Port 50GBase/1-Port 100GBase-QSFP28 Flexible Card(P243)
              subbname8090DEVANND001EV104(225836),       --1 Channel 50G Base QSFP28 High Speed Interface Board
              subbname8090DEVANND001EV203(225837),       --2 Channels 50G/1 Channel 100G Base QSFP28 High Speed Interface Board
              subbname8090DEVANND001EV103(225834),       --1 Channel 50G Base QSFP28 High Speed Interface Board
              subbname8090DEVANND00EX4S02(225835),       --4 Channels 10GE Optical Interface Board(SFP+)
              subbname8090DEVCR5D00E1KB70(225832),       --1-Port 400GBase-QSFP-DD Flexible Card(P1T)
              subbname8090DEVCR6D00E1KB10(225833),       --1-Port 400GBase-QSFP-DD Flexible Card(P1T)
             subbname8090DEVANND001EH100(225838),       --1 Channel 100G Base QSFP28 High Speed Interface Board
             subbname8090DEVCR58EENBD1(225839),           --20-Port 100GE-QSFP28 FlexE/MACSec Integrated Line Process Unit
              subbname8090DEVCR5D0EFGFMK0(225840),       --24-Port 100/1000Base-X-SFP MACsec Flexible Card(P53-K)
              subbname8090DEVCR5D0LBXFMK0(225841),       --12-Port 10GBase LAN/WAN-SFP+ MACsec Flexible Card(P243-K)
              subbname8090DEVCR5DE1NBFMK0(225842),       --2-Port 50GBase/1-Port 100GBase-QSFP28 FlexE/MACsec Flexible Card (P243-K)  
              subbname8090DEVCR8D00L4XFK1(225843),       --4-Port 10GE(SFP+)/GE(SFP) MACsec Physical Interface Card(PIC-K)
              subbname8090DEVCR8D00EAGFK2(225844),       --10-port 100/1000Base-X-SFP MACsec Physical Interface Card(PIC-K)
              subbname8090DEVCR8D000DE1K1(225845),       --16-Port E1 Physical Interface Card(PIC-K,75ohm/120ohm)             
              subbname8090DEVCR8D00C4CFK1(225846),       --4-Port Channelized STM-1c POS-SFP Physical Interface Card(PIC-K)
              subbname8090DEVCR8D00LAXFK1(225847),       --10-Port 10GE/GE LAN/WAN-SFP+ MACsec Physical Interface Card(PIC-K)
              subbname8090DEVCR8D00E2VBK1(225848),       --2-Port 50GBase/1-Port 100GBase-QSFP28 FlexE MACsec Physical Interface Card(PIC-K)
              subbname8090DEVCR8D00EAGFK1(225849),       --10-port 100/1000Base-X-SFP MACsec Physical Interface Card(PIC-K)
              subbname8090DEVCR8D00P4CFK1(225850),       --4-Port OC-3c/STM-1c POS-SFP Flexible Interface Card(PIC-K)
              subbname8090DEVCR5D00CFE171(225851),       --2-Port Channelized STM-1c POS-SFP + 24-Port Channelized E1 Flexible Card(P53)
              subbname8090DEVCR5D00P8E870(225852),       --8-Port 100/1000Base-X-SFP + 8-Port STM-4c POS-SFP Flexible Card(P53)
              subbname8090DEVCR5D00P8E8K0(225853),       --8-Port 100/1000Base-X-SFP + 8-Port STM-1c POS-SFP Flexible Card(P53-K)
              subbname8090DEVCR5D00CFE1K1(225854),       --2-Port Channelized STM-1c POS-SFP + 24-Port Channelized E1 Flexible Card(P53-K)
              subbname8090DEVCR5D00P8E871(225855),       --8-Port 100/1000Base-X-SFP + 8-Port STM-1c POS-SFP Flexible Card(P53)
              subbname8090DEVCR5D00P8E8K1(225856),       --8-Port 100/1000Base-X-SFP + 8-Port STM-4c POS-SFP Flexible Card(P53-K)
              subbname8090DEVCR57C2CFE1A(225857),        --2-Port Channelized STM-1c POS-SFP + 24-Port Channelized E1 Flexible Card(P53)
              subbname8090DEVCR57C2CFE1A1(225858),       --2-Port Channelized STM-1c POS-SFP + 24-Port Channelized E1 Flexible Card(P53-K)
              subbname8090DEVCR57E8GP4UA0(225859),       --8-Port 100/1000Base-X-SFP + 8-Port STM-1c POS-SFP Flexible Card(P53)
              subbname8090DEVCR57E8GP8HA0(225860),       --8-Port 100/1000Base-X-SFP + 8-Port STM-4c POS-SFP Flexible Card(P53)
              subbname8090DEVCR57E8GP4UA2(225861),       --8-Port 100/1000Base-X-SFP + 8-Port STM-1c POS-SFP Flexible Card(P53-K)
              subbname8090DEVCR57E8GP8CA2(225862),       --8-Port 100/1000Base-X-SFP + 8-Port STM-4c POS-SFP Flexible Card(P53-K)
              subbname8090DEVANND001EV205(225863),       --2 Channels 50G Base QSFP28 High Speed Interface Board
              subbname8090DEVANKD001EV207(225864),       --2 Channels 50G/1 Channel 100G Base QSFP28 High Speed Interface Board CM (Default Enable 1*50GE)
              subbname8090DEVANND001EV207(225865),       --2 Channels 50G/1 Channel 100G Base QSFP28 High Speed Interface Board CM (Default Enable 1*50GE)
              subbname8090DEVANND00EM8T02(225866),       --8 Channels GE/FE Electrical Interface Board
              subbname8090DEVCR5D00P8E871-(225867),      --8-Port 100/1000Base-X-SFP + 8-Port OC-3c/STM-1c POS-SFP Flexible Card(P53)
              subbname8090DEVCR5D00P8E870-(225868),      --8-Port 100/1000Base-X-SFP + 8-Port OC-12c/STM-4c POS-SFP Flexible Card(P53)
              subbname8090DEVCR5D00CFE171-(225869),      --2-Port Channelized STM-1c POS-SFP + 24-Port Channelized E1 Flexible Card(P53)
             subbname8090DEVCR5D00P8E8K0-(225870),       --8-Port 100/1000Base-X-SFP + 8-Port OC-12c/STM-4c POS-SFP Flexible Card(P53-K)
              subbname8090DEVCR5D00P8E8K1-(225871),      --8-Port 100/1000Base-X-SFP + 8-Port OC-3c/STM-1c POS-SFP Flexible Card(P53-K)
             subbname8090DEVCR5D00CFE1K1-(225872),       --2-Port Channelized STM-1c POS-SFP + 24-Port Channelized E1 Flexible Card(P53-K)
              subbname8090DEVCR8D00E8GEC1(225873),        --8-Port 100/1000Base-RJ45 Physical Interface Card(PIC)
              subbname8090DEVNetEngine-8000-M1D(225874),  --CARD NetEngine 8000 M1D
              subbname8090DEVNetEngine-8000-M1D-B(115915), -- CARD NetEngine 8000 M1D-B
              subbname8090DEVNetEngine-A813(115916),       -- CARD NetEngine A813
              subbname8090DEVATN-905-S(115918),            -- CARD ATN 905-S
              subbname8090DEVNetEngine-A831-E(115919),     -- CARD NetEngine A831 E
              subbname8090DEVNetEngine-A822-E(115920),     -- CARD NetEngine A822 E
			  subbname8090DEVNetEngine-A822(115925),     -- CARD NetEngine A822
              subbname8090DEVCR5D00C2CF71(225875),       --2-Port Channelized STM-1c POS-SFP + 24-Port Channelized E1 Flexible Card(P53)
              subbname8090DEVCR5D00E8GF72(225876),       --8-Port 100/1000Base-X-SFP + 8-Port STM-4c POS-SFP Flexible Card(P53)
              subbname8090DEVCR5D00E8GF73(225877),       --8-Port 100/1000Base-X-SFP + 8-Port STM-1c POS-SFP Flexible Card(P53)
              subbname8090DEVCR5D00E8GF73-(225878),      --8-Port 100/1000Base-X-SFP + 8-Port OC-3c/STM-1c POS-SFP Flexible Card(P53)
              subbname8090DEVCR5D00E8GF72-(225879),      --8-Port 100/1000Base-X-SFP + 8-Port OC-12c/STM-4c POS-SFP Flexible Card(P53)
              subbname8090DEVCR5D00C2CF71-(225880),      --2-Port Channelized STM-1c POS-SFP + 24-Port Channelized E1 Flexible Card(P53)
              subbname8090DEVCR8D00E8GEC2(225881),       --8-Port 100/1000Base-RJ45 Physical Interface Card(PIC)
              subbname8090DEVCR59LJXFE(225882),          --36-Port 10GE/GE SFP+ Integrated Card
              subbname8090DEVCR59E2KBC(225883),          --2-Port 400G QSFP-DD Integrated Card
              subbname8090DEVCR59E8NBG(225884),          --8-Port 100G QSFP28 Integrated Card
              subbname8090DEVCR58EKNBBS0(225885),        --40-Port 100GE/50GE-QSFP28 Integrated Line Process Unit
              subbname8090DEVCR58EKNBB0(225888),         --40-Port 100GE/50GE-QSFP28 Integrated Line Process Unit
              subbname8090DEVCR58E8KE8NCS0(225886),      --8-Port 400GE-QSFP-DD + 8-Port 100GE-QSFP28 Integrated Line Process Unit
              subbname8090DEVCR58E8KE8NC0(225887),       --8-Port 400GE-QSFP-DD + 8-Port 100GE-QSFP28 Integrated Line Process Unit
              subbname8090DEVGPLI40CQES3(225889),        --40-Port 100GBase QSFP28 Integrated Line Process Unit
              subbname8090DEVGPLI40CQE4(225890),         --40-Port 100GBase QSFP28 Integrated Line Process Unit
              subbname8090DEVIG2DE4NE8V01(225891),       --8-Port 50G/4-Port 100GBase-QSFP28 Flexible Card (P1T)
              subbname8090DEVIG2D00E1KB01(225892),       --1-Port 400GBase-QSFP-DD Flexible Card(P1T)
              subbname8090DEVIG2D0LFXFM01(225893),       --24-Port 10GBase LAN/WAN-SFP+ MACsec Flexible Card(P483)
              subbname8090DEVIG2D0EFGFM01(225894),       --24-port 100/1000Base-X-SFP MACsec Flexible Card (P53)
              subbname8090DEVCX6D00E1KB10(225895),        --1-Port 400GBase-QSFP-DD Flexible Card(S1T)
              subbname8090DEVCR57LEXFD0(225896),         --20-Port 10Gase LAN/WAN-SFP+ FlexE Integrated Line Processing Unit CM
              subbname8090DEVCR57LEXFD1(225897),         --20-Port 10Gase LAN/WAN-SFP+ FlexE Integrated Line Processing Unit
              subbname8090DEVCR57E2NBI0(225898),         --2-Port 100GBase-QSFP28 FlexE Integrated Line Processing Unit CM
              subbname8090DEVCR57E2NBI1(225899),         --2-Port 100GBase-QSFP28 FlexE Integrated Line Processing Unit
              subbname8090DEVCR8D00L4XFC2(225900),       --4-Port 10GE-SFP+ Physical Interface Card(PIC)
              subbname8090DEVCR8D00EAGFC2(225901),       --10-port 100/1000Base-X-SFP Physical Interface Card(PIC)
              subbname8090DEVCR8D00L4XFC1(225902),       --4-Port 10G-SFP+ Physical Interface Card(PIC)
              subbname8090DEVCR8DE1NE2VC1(225903),       --2-Port 50GBase/1-Port 100GBase-QSFP28 Physical Interface Card(PIC)
              subbname8090DEVCR8D00EAGFC1(225904),       --10-port 100/1000Base-X-SFP Physical Interface Card(PIC)
              subbname8090DEVCR8D00E4YBC1(225905),       --4-Port 25GE-SFP28 Physical Interface Card (PIC)
              subbname8090DEVCR8D00LAXFC1(225906),       --10-Port 10GE/GE(SFP+) Physical Interface Card(PIC)
              subbname8090DEVVIRTUALPIC(225907),         --FLEXE_VIRTUAL
              subbname8090DEVDSVIRTUALPIC(709990),       --DS_FLEXE_VIRTUAL_CARD
             subbname8090DEVCX6DE2NBFM11(225908),      --2-Port 100GBase-QSFP28 FlexE Flexible Card(S483)
             subbname8090DEVANND001EY400(225909),       --4 Channels 25G (SFP28)/4 Channels 10G (SFP+) High Speed Interface Board
             subbname8090DEVANND001EY200(225910),      --2 Channels 25G (SFP28)/2 Channels 10G (SFP+) High Speed Interface Board
             subbname8090DEVANND0EM10F01(225911),      --10 Channels GE/FE Optical Interface Board
            subbname8090DEVCR5D0LEXFM70(225913),       --20-Port 10GBase LAN-SFP+ Flexible Card(P483)
            subbname8090DEVCR5DE2NBFM71(225914),      --2-Port 100GBase-QSFP28 FlexE Flexible Card(P483)
            subbname8090DEVCR5DE4NE8V71(225915),      --8-Port 50GBase/4-Port 100GBase-QSFP28 FlexE Flexible Card(P1T)
            subbname8090DEVCR5D00LBXF70(225916),       --12-Port 10GBase LAN-SFP+ Flexible Card(P243)
            subbname8090DEVCR5D00LFXF70(225917),      --24-Port 10GBase LAN-SFP+ Flexible Card(P483)
            subbname8090DEVCR5D0E4NBF70(225918),      --4-Port 50GBase/2-Port 100GBase-QSFP28 FlexE Flexible Card(P483)
            subbname8090DEVANDD001EV100(225919),      --1 Channel 50G Base QSFP28 High Speed Interface Board
            subbname8090DEVCX6DE1NBFM11(225920),      --2-Port 50GBase/1-Port 100GBase-QSFP28 FlexE Flexible Card (S243)
            subbname8090DEVCX6D00EFGF12(225922),      --24-Port 100/1000Base-X-SFP Flexible Card(S53)
            subbname8090DEVCR5D00EFGF71(225921),      --24-Port 100/1000Base-X-SFP Flexible Card(P53)
            subbname8090DEVCR5D00LAXF73(225923),      --10-Port 10GBase LAN-SFP+ Flexible Card(P243)
            subbname8090DEVCR5D00LFXF71(225924),       --24-Port 10GBase LAN-SFP+ Flexible Card(P483)
           subbname8090DEVCX6DE4NE8V11(225925),       --8-Port 50GBase/4-Port 100GBase-QSFP28 FlexE Flexible Card(S1T)
          subbname8090DEVCX6D0E2NBF10(225926),        --4-Port 50GBase/2-Port 100GBase-QSFP28 FlexE Flexible Card(S483)
          subbname8090DEVCX6DE2NBFM12(225927),        --2-Port 100GBase-QSFP28 FlexE Flexible Card(S483)
          subbname8090DEVCX6D0LEXFM10(225928),        --20-Port 10GBase LAN/WAN-SFP+ Flexible Card(S483)
          subbname8090DEVCX6D0E1NBF10(225929),        --1-Port 100GBase-QSFP28 FlexE Flexible Card (S243)
          subbname8090DEVCX6D00LBXF10(225930),        --12-Port 10GBase LAN/WAN-SFP+ Flexible Card(S243)
          subbname8090DEVCX6D00LAXF10(225931),        --10-Port 10GBase LAN/WAN-SFP+ Flexible Card(S243)
          subbname8090DEVGPLI20CQES1(225932),       --20-Port 100GBase-QSFP28 Integrated Line Processing Unit
          subbname8090DEVGPLI20CQE2(225933),        --20-Port 100GBase-QSFP28 Integrated Line Processing Unit
          subbname8090DEVGPLI72YSE6(225934),        --72-Port 10GE-SFP+ Integrated Line Processing Unit
          subbname8090DEVME0DE4NE8V7Q(225935),   --8-Port 50G/4-Port 100GBase-QSFP28 Flex Flexible Card(BP1T)
          subbname8090DEVGPLI72YSES5(225936),       --72-Port 25GE(SFP28)/10GE(SFP+)/GE(SFP)Integrated Line Processing Unit
          subbname8090DEVGPLI40CQES5(225937),       --40-Port 100GBase QSFP28 Integrated Line Process Unit
          subbname8090DEVGPLI40CQE6(225938),        --40-Port 100GBase QSFP28 Integrated Line Process Unit
              subbname8090DEVCR8D00E8GEC3(225939),      --8-Port 100/1000Base-RJ45 Physical Interface Card(PIC)
              subbname8090DEVCR8D00E8GED2(567354),      --8-Port 100/1000Base-RJ45 Physical Interface Card(PIC)
              subbname8090DEVCR8D00P8CFC1(225940),      --8-Port STM-1c/8-Port STM-4c POS Card(PIC)
              subbname8090DEVCR5D00E1KB71(225941),      --1-Port 400GBase-QSFP-DD Flexible Card(P1T-CM, enable 100G)
              subbname8090DEVCR58EENBHS0(225942),       --20-Port 100GE/50GE-QSFP28 Integrated Line Process Unit
              subbname8090DEVCR58EENBH0(225943),        --20-Port 100GE/50GE-QSFP28 Integrated Line Process Unit
              subbname8090DEVCR8D00E1KBC0(225944),      --1-Port 400GBase-QSFP-DD Physical Interface Card(PIC)
              subbname8090DEVCR5DE4NE8V72(225945),      --8-Port 50GBase/4-Port 100GBase-QSFP28 FlexE Flexible Card(P1T)
              subbname8090DEVCR5D0E2NBF72(225946),      --4-Port 50GBase/2-Port 100GBase-QSFP28 FlexE Flexible Card(P483)
              subbname8090DEVME0D00E1KB70(225947),      --1-Port 400GBase-QSFP-DD Flexible Card(BP1T)
              subbname8090DEVME0DE4NE8V72(225948),      --8-Port 50GBase/4-Port 100GBase-QSFP28 FlexE Flexible Card(BP1T)
              subbname8090DEVGPLI20CQES3(225949),      --20-Port 100GBase-QSFP28 Integrated Line Processing Unit
              subbname8090DEVGPLI20CQE4(225950),       --20-Port 100GBase-QSFP28 Integrated Line Processing Unit
              subbname8090DEVGPLI36KQS1(225951),        --36-Port 400GBase-QSFP-DD Integrated Line Processing Unit
              subbname8090DEVGPLI18KQS1(225952),        --18-Port 400GBase-QSFP-DD Integrated Line Processing Unit
              subbname8090DEVDVSUVIRTUAL(225953),      --DVSUVIRTUAL
              subbname8090DEVCR5D0LFXFM71(225954),      --24-Port 10GBase LAN/WAN-SFP+ MACsec Flexible Card(P483-CM)
              subbname8090DEVCR5D0E2NBF73(225955),      --4-Port 50GBase/2-Port 100GBase-QSFP28 FlexE Flexible Card(P483-CM)
              subbname8090DEVCR5D0E2NBF74(225956),      --4-Port 50GBase/2-Port 100GBase-QSFP28 FlexE Flexible Card(P483-CM)
              subbname8090DEVCR58ERYFA0(225957),          --72-Port 25GE-SFP28/10GE-SFP+ Integrated Line Process Unit
              subbname8090DEVCR58ERYFAS0(225958),       --72-Port 25GE-SFP28/10GE-SFP+ Integrated Line Process Unit
              subbname8090DEVGPR8KQ56CQ(225959),         --8-Port 400GBase-QSFPDD + 56-Port 100GBase-QSFP28
              subbname8090DEVCR5D00E1ND74(225960),      --1-Port 100GBase-QSFP28 Flexible Card E(P240-E)
              subbname8090DEVME0D00E1ND74(225961),      --1-Port 100GBase-QSFP28 Flexible Card E(BP240-E)
              subbname8090DEVCGNVSU100A(225962),        --CGN Versatile Service Flexible Card (VSUP-100)
              subbname8090DEVANND1EM10F00(225963),      --10 Channels GE/FE Optical Interface Board
              subbname8090DEVCR8D00EAGFC4(225964),      --10-Port 100/1000Base-X-SFP  Physical Interface Card(PIC)
              subbname8090DEVCR8D00EAGFC3(225965),      --10-Port 100/1000Base-X-SFP  Physical Interface Card(PIC)
              subbname8090DEVCX6D0E8VFM10(225966),       --8-Port 50GBase-QSFP28 FlexE Flexible Card(S1T)
              subbname8090DEVCX6D0E4NFM10(225967),       --4-Port 100GBase-QSFP28 FlexE Flexible Card(S1T)
              subbname8090DEVCR8DE1NEKB11(225968),      --1-Port 400GBase-QSFP-DD Physical Interface Card CM(Enable 1*100G)(PIC)
              subbname8090DEVCR8D00E4XFC2(225969),      --4-Port 10GE-SFP+ FlexE Physical Interface Card(PIC)
              subbname8090DEVCR8D00E4XFC1(225970),      --4-Port 10GE-SFP+ FlexE Physical Interface Card(PIC)
              subbname8090DEVANRD001EH200(225971),      --2 Channel 100G/50G Base QSFP28 High Speed Interface Board
              subbname8090DEVCR8D00E1VBC1(225972),      --1-port 50G Base (QSFP28) Physical Interface Card(PIC)
              subbname8090DEVGPLI20CQE6(225973),        --20-Port 100GBase-QSFP28 MACsec Integrated Line Processing Unit
              subbname8090DEVGPLI20CQES5(225974),       --20-Port 100GBase-QSFP28 MACsec Integrated Line Processing Unit
              subbname8090DEVCR5D00EDNB65(225976),      --16-Port 100GBase QSFP28 Flexible Card CM(CP3T2-CM,Occupy 1 sub-slot)(8 port enable)
              subbname8090DEVCR5D00E4KB63(225977),       --4-Port 400GBase QSFP-DD  Flexible Card CM(CP3T2-CM,Occupy 1 sub-slot)(2 port enable)
			  subbname8090DEVCR59E4KBB(165000),         -- 4-Port 400GBase QSFP-DD
              subbname8090DEVCR59EDNBC(709793),         -- 16-Port 100GBase QSFP28
			  subbname8090DEVNetEngineA811M(225988),     --CARD NetEngine A811 M
			  subbname8090DEVCR57L8XEDG0(225993),        --8-Port GE-SFP/10GE-SFP+ and 16-Port GE-SFP Unflexible Card(P243)
              subbname8090DEVCR57LFXFJ4(225992),         --24-Port 10GBase LAN/WAN-SFP+ MACsec Unflexible Card(P483)
              subbname8090DEVCR8D00E1NBC2(225994),       --2-Port 50GBase/1-Port 100GBase-QSFP28 FlexE MACsec Physical Interface Card(PIC)
              subbname8090DEVCR8D000DE1C2(225995),        --16-Port E1 Physical Interface Card(PIC,75ohm/120ohm)
			  subbname8090DEVCR5D00LBXF73(561699),        --12-Port 10GBase LAN/WAN-SFP+ Flexible Card(P245)
              subbname8090DEVME0M0LEXFB72(561700),        --20-Port 10GBase LAN/WAN-SFP+ Flexible Card H(BP400-H)
              subbname8090DEVCR5D0LAXFH71(561701),        --10-Port 10GBase LAN/WAN-SFP+ Flexible Card H(P240A-H)
              subbname8090DEVCR5D0LAXFE72(561702),        --10-Port 10GBase LAN/WAN-SFP+ Flexible Card E(P245-E)
              subbname8090DEVCX6D0EFGFA13(561703),        --24-Port 100/1000Base-X-SFP Flexible Card A(S240A-A)
              subbname8090DEVCX6D0LBXFA13(561704),        --12-Port 10GBase LAN/WAN-SFP+ Flexible Card A(S240A-A)
              subbname8090DEVANND16E10000(225996),        --16 Channels E1 Interface Board(PIC,75ohm/120ohm)
              subbname8090DEVANND00EX4S04(225997),        --4 Channels 10GE FlexE Optical Interface Board(SFP+)
              subbname8090DEVCR5D00E2NF74(203899),      -- 2-Port 50GBase/2-Port 100GBase-QSFP28 Flexible Card A(P485-A)
              subbname8090DEVCR5DE2VE1N73(986205),   -- 2-Port 50GBase/1-Port 100GBase-QSFP28 FlexE Flexible Card (P245)
              subbname8090DEVCX6DE2VE1N11(177058),   -- 2-Port 50GBase/1-Port 100GBase-QSFP28 FlexE Flexible Card (S240A-A)
              subbname8090DEVME0D00L1NB72(689388),   -- 2-Port 50GBase/1-Port 100GBase-QSFP28 Flexible Card(BP245)
              subbname8090DEVCR5D0EFGFH71(729209),   -- 24-Port 1000Base-X-SFP Flexible Card H(P51A-H)
              subbname8090DEVCR5D0EFGFA72(204664),   -- 24-Port 100/1000Base-X-SFP Flexible Card(P55)
              subbname8090DEVCR5D0EFGFE72(257371),   -- 24-Port 1000Base-X-SFP Flexible Card E(P245-E)
              subbname8090DEVCR5D00E1ND76(231975),   -- 1-Port 100GBase-QSFP28 Flexible Card A(P240A-A)
              subbname8090DEVCR5D00E1ND78(905397),   -- 1-Port 100GBase-QSFP28 Flexible Card A(P245-A)
              subbname8090DEVCX6D0E1NBA11(632384),   -- 1-Port 100GBase-QSFP28 Flexible Card A(S240A-A)
              subbname8090DEVME0D0EFGFH7I(260956),   -- 24-Port 1000Base-X-SFP Flexible Card H(BP51A-H)
              subbname8090DEVME0D0EFGFE7F(913970),   -- 24-Port 1000Base-X-SFP Flexible Card E(BP245-E)
              subbname8090DEVME0D0LBXXB7J(160367),   -- 12-Port 10GBase LAN/WAN-SFP+ Flexible Card(BP245-E)
              subbname8090DEVME0D0E1NDB73(535050),   -- 1-Port 100GBase-QSFP28 Flexible Card(BP240A)
              subbname8090DEVME0D0E1NDB72(519111),   -- 1-Port 100GBase-QSFP28 Flexible Card(BP245)
              subbname8090DEVME0M0LEXFB74(941707),   -- 20-Port 10GBase LAN/WAN-SFP+ Flexible Card(BP485)
              subbname8090DEVME0D0LAXFH7I(632930),   -- 10-Port 10GBase LAN/WAN-SFP+ Flexible Card H(BP240A-H)
              subbname8090DEVME0D0LAXFB7I(601206),   -- 10-Port 10GBase LAN/WAN-SFP+ Flexible Card E(BP245-E)
              subbname8090DEVCR5D00LFXF77(971370),   -- 24-Port 10GBase LAN/WAN-SFP+ Flexible Card A(P485-A)
              subbname8090DEVCR5D0LBXFE7F(976431),   -- 12-Port 10GBase LAN/WAN-SFP+ Flexible Card E(P245-E)
              subbname8090DEVCR5DE2VE1N72(576762),   -- 2-Port 50GBase/1-Port 100GBase-QSFP28 FlexE Flexible Card (P245-E)
              subbname8090DEVME0D00L1NB71(864407),   -- 2-Port 50GBase/1-Port 100GBase-QSFP28 Flexible Card(BP245-E)
              subbname8090DEVCR5D00E1ND75(469730),   -- 1-Port 100GBase-QSFP28 Flexible Card(P245)
              subbname8090DEVCR5D00E1ND77(145911),   -- 1-Port 100GBase-QSFP28 Flexible Card E(P245-E)
              subbname8090DEVME0D00E1ND75(239749),   -- 1-Port 100GBase-QSFP28 Flexible Card E(BP245-E)
              subbname8090DEVCR5D0EFGFA74(673606),   -- 24-Port 100/1000Base-X-SFP Flexible Card A(P245-A)
              subbname8090DEVME0D0EFGFB7J(209459),   -- 24-Port 100/1000Base-X-SFP Flexible Card(BP245)
              subbname8090DEVCR5D00LBXF74(872589),   -- 12-Port 10GBase LAN/WAN-SFP+ Flexible Card A(P245-A)
              subbname8090DEVME0D0LBXXB7I(987604),   -- 12-Port 10GBase LAN/WAN-SFP+ Flexible Card(BP245)
			  subbname8090DEVCX6D0E2NBA12(983715),   -- 2-Port 100GBase-QSFP28 Flexible Card A(S480-A)
              subbname8090DEVME0M0E2NFB72(700917),   -- 2-Port 100GBase-QSFP28 Flexible Card H(BP400-H)
              subbname8090DEVME0M0E2NFB73(975301),   -- 2-Port 50GBase/2-Port 100GBase-QSFP28 Flexible Card(BP485)
              subbname8090DEVCR57E1NBG3(704702),   -- 1-Port 100GBase-QSFP28 Fixed Card
              subbname8090DEVCR57LBXFL2(644732),   -- 12-port 10GBase LAN/WAN-SFP+ Fixed Card
              subbname8090DEVCR57LFXFM2(774065),   -- 24-Port 10GBase LAN/WAN-SFP+ Fixed Card
              subbname8090DEVCR57E2NBE4(275411),   -- 2-Port 100GBase-QSFP28 Fixed Card A
			  subbname8090DEVIG2D00LFXF74(275412),   -- 24-Port 10GBase LAN/WAN-SFP+ Flexible Card A(P480-A)
              subbname8090DEVIG2D00E2NF70(275413),   -- 2-Port 100GBase-QSFP28 Flexible Card A(P480-A)
              subbname8090DEVCR57LBXFG2(774067),   -- 12-Port 10GBase LAN/WAN-SFP+ Fixed Card
              subbname8090DEVME0M0LEXFB75(774068),   -- 20-Port 10GBase LAN/WAN-SFP+ Flexible Card(BP485-E)
              subbname8090DEVME0M0E2NFB74(774069),   -- 2-Port 50GBase/2-Port 100GBase-QSFP28 Flexible Card(BP485-E)
			  subbname8090DEVCR57LAXECG0(774070),   -- 10-Port GE-SFP/10GE-SFP+ and 14-Port GE-SFP Fixed Card
              subbname8090DEVGPLI20CQES9(729921),   -- 20-Port 100GBase QSFP28 Integrated Line Process Unit
              subbname8090DEVGPLI20CQE10(208306),   -- 20-Port 100GBase QSFP28 Integrated Line Process Unit
              subbname8090DEVGPLI40CQES7(172719),   -- 40-Port 100GBase QSFP28 Integrated Line Process Unit
			  subbname8090DEVGPLI40CQE8(172720),    -- 40-Port 100GBase QSFP28 Integrated Line Process Unit
			  subbname8090DEVGPLI4KQ24CQE2(733887), -- 4-Port 400GBase QSFPDD 24-Port 100GBase QSFP28 Integrated Line Process Unit
              subbname8090DEVGPLI32CQE4(964151),   -- 32-Port 100GBase QSFP28 Integrated Line Process Unit
              subbname8090DEVCR59E8NBD(165996),   -- 8-Port 100GBase QSFP28 Fixed card
              subbname8090DEVCR59LJXFA(859868),   -- 36-Port 10GBase LAN/WAN-SFP+ Fixed card
              subbname8090DEVGPLI4KQ24CQES1(733886),   -- 4-Port 400GBase QSFPDD 24-Port 100GBase QSFP28 Integrated Line Process Unit
			  subbname8090DEVCR8D00E1NBC4(225912),      --1-Port 100GBase-QSFP28 Physical Interface Card(PIC)
			  subbname8090DEVCR8D00E2NBC4(295996),        --2-Port 50GBase/1-Port 100GBase-QSFP28 FlexE MACsec Physical Interface Card(PIC)
              subbname8090DEVCR8D00E4XFC3(920246),      --4-Port 10GE(SFP+)/GE(SFP) MACsec Physical Interface Card(PIC)
              subbname8090DEVCR8D00E4YFC0(742487),      --4-Port 25GE(SFP28)/10GE(SFP+) MACsec Physical Interface Card (PIC)
              subbname8090DEVCR8D00EAGFCA(998794),      --10-port 100/1000Base-X-SFP MACsec Physical Interface Card(PIC)
              subbname8090DEVCR8D00EAXFC1(607802),      --10-Port 10GE/GE LAN/WAN-SFP+ MACsec Physical Interface Card(PIC)
              subbname8090DEVCR8D00EEGFXA(817470),      --20-Port 100/1000Base-X-CSFP/10-Port 100/1000Base-X-SFP Physical Interface Card(PIC)
              subbname8090DEVCX6D0EFGFA14(913971),   -- 24-Port 100/1000Base-X-SFP Flexible Card A(S480-A)
              subbname8090DEVCR8D00E8GEB2(226873),        --8-Port 100/1000Base-RJ45 Physical Interface Card(PIC)
              subbname8090DEVCR8D00E1NCC1(295791),      --1-Port 100GBase-CFP2 Physical Interface Card(PIC)
              subbname8090DEVCR57LFXFN4(295992),         --24-Port 10GBase LAN/WAN-SFP+ MACsec Unflexible Card(P483)
              subbname8090DEVCR58EKNBC1(270655),   -- 40-Port 100GE/50GE-QSFP28 Integrated Line Process Unit
              subbname8090DEVCR58EKNBCS1(808683),   -- 40-Port 100GE/50GE-QSFP28 Integrated Line Process Unit
              subbname8090DEVCR58E8KE8ND1(125263),   -- 8-Port 400GE-QSFP-DD + 8-Port 100GE-QSFP28 Integrated Line Process Unit
              subbname8090DEVCR58E8KE8NDS1(245954),   -- 8-Port 400GE-QSFP-DD + 8-Port 100GE-QSFP28 Integrated Line Process Unit
              subbname8090DEVCR58EENBJS1(470120),   -- 20-Port 100GE/50GE-QSFP28 Integrated Line Process Unit
              subbname8090DEVCR58EENBJ1(669469),   -- 20-Port 100GE/50GE-QSFP28 Integrated Line Process Unit
              subbname8090DEVGPR8CQ20YSC(295722),         --8-Port 100GBase-QSFP28 + 48-Port 25GBase-Y-SFP+  
			  subbname8090DEVNetEngineA811(225989),      --CARD NetEngine A811
              subbname8090DEVNetEngineA821(225990),      --CARD NetEngine A821
              subbname8090DEVNetEngineA821E(225998),     --CARD NetEngine A821 E
              subbname8090DEVANND001EV105(225999),       --1 Channel 50G Base QSFP28 High Speed Interface Board
              subbname8090DEVANND001EV106(226000),       --1 Channel 50G Base QSFP28 High Speed Interface Board
              subbname8090DEVCR8DLPUTK0C0(226051),        --Trunk Line Processing Unit(LPUT-800-CM, 400G Enabled by Default)
              subbname8090DEVCR8D00LAXFD0(226052),        --10-Port 10GE/GE LAN/WAN-SFP+ MACsec Physical Interface Card(PIC)
              subbname8090DEVCR8DE2V1NBD0(226053),        --2-Port 50GBase/1-Port 100GBase-QSFP28 FlexE MACsec Physical Interface Card(PIC)
              subbname8090DEVCR8D00EAGFD5(226054),        --10-port 100/1000Base-X-SFP MACsec Physical Interface Card(PIC)
              subbname8090DEVCR8D00CDE1D0(226055),        --16-Port E1 Physical Interface Card(PIC,75ohm/120ohm)
              subbname8090DEVCR8D00C4CFD0(226056),        --4-Port OC-3c/STM-1c POS-SFP Flexible Interface Card(PIC)
              subbname8090DEVCR8D00E8GED0(226057),        --8-Port 100/1000Base-RJ45 Physical Interface Card(PIC)
              subbname8090DEVCR8D00P8CFD0(226058),        --8-Port STM-1c/8-Port STM-4c POS Card (PIC)(Default Enable 4*STM-1c)
              subbname8090DEVME0D00LFGF70(225979),      --24-Port 100/1000Base-X-SFP Flexible Card(BP243)
              subbname8090DEVME0D00LFXF71(225980),      --24-Port 10GBase LAN/WAN-SFP+ Flexible Card(BP483)
              subbname8090DEVME0D00L4NB70(225981),      --4-Port 50GBase/2-Port 100GBase-QSFP28 Flexible Card(BP483)
              subbname8090DEVME0D00LBXF71(225982),      --12-Port 10GBase LAN/WAN-SFP+ Flexible Card(BP243)
              subbname8090DEVME0D00L1NB70(225983),      --2-Port 50GBase/1-Port 100GBase-QSFP28 Flexible Card(BP243)
              subbname8090DEVCR5D00E1KB72(225984),      --1-Port 400GBase-QSFP-DD + 2-Port QSFP28 OA Flexible Card(P1T)
              subbname8090DEVCR5D00E1KB73(225985),      --1-Port 400GBase-QSFP-DD + 2-Port QSFP28 OA Flexible Card(P1T-CM, 100G Enabled by Default)
              subbname8090DEVNetEngineA810(225986),      --CARD NetEngine A810
              subbname8090DEVCARDNetEngineA817(333110),     --CARD NetEngine A817
              subbname8090DEVCARD2NetEngineA817(333109), --CARD NetEngine A817,4E1
			  subbname8090DEVCR5D08CWDM70(564529),      --8-Channel CWDM Multiplexing &amp; Demultiplexing (1471/1491/1511/1531/1551/1571/1591/1611nm) Physical Interface Card(PIC)
              subbname8090DEVCARDATN910CF(333111),      --CARD ATN910C F
              subbname8090DEVCARDETN500F(225669),       --CARD ETN500 F
              subbname8090DEVCARDATN905(225666),        --CARD ATN 905
              subbname8090DEVCARDATN910CE(333112),     --CARD ATN 910C E
              subbname8090DEVCARDATN910E-A(225659),     --CARD ATN910E-A
              subbname8090DEVCARDNetEngine8000EM1E-B(225671), -- CARD NetEngine8000E M1E-B
              subbname8090DEVCARDNE05ESR(225670),      --CARD NE05E SR
             subbname8090DEVCR5D04OTU290(537488),    -- 4-Port 10G OTU2-XFP Physical Interface Card(PIC)
             subbname8090DEVCR9D00N2NC80(537489),    -- 2-Port 100G OTN/ETH-CFP2 Flexible Card
             subbname8090DEVCR5D00E2NC77(537490),    -- 2-Port 100GBase-CFP2 Flexible Card A(P480-A)
             subbname8090DEVCR5D00LAXF90(561523),     -- 10-Port 10GBase-X-SFP+ Physical Interface Card(PIC)
             subbname8090DEVCR5D00E1NC99(561524),     -- 1-Port 100GBase-CFP2 Physical Interface Card(PIC)
             subbname8090DEVCR5D00E2NB91(561525),     -- 2-Port 100GBase-QSFP28 Physical Interface Card(PIC)
             subbname8090DEVANKD01EXAS00(561526),    -- Finished Board Unit,ATN 950C,ANK1EXAS0,10 Channels 10GE Optical Interface Board(SFP+)
             subbname8090DEVANKD001EH100(561527),    -- Finished Board Unit,ATN 950C,ANK1EH1,1 Channel 100GE Optical Interface Board(CFP2)
             subbname8090DEVCR5D00P4XX60(561528),    -- 4-Port OC-192c/STM-64c POS-XFP Flexible Card(CP400,Occupy 1 sub-slot)
             subbname8090DEVCR58EANBB0(561529),        -- 10-Port 100GBase-QSFP28 Integrated Card
             subbname8090DEVCX6D0E2NCA11(537491),    -- 2-Port 100GBase-CFP2 Flexible Card A(S480-A)
             subbname8090DEVME0M0E2NCB72(537492),    -- 2-Port 100GBase-CFP2 Flexible Card(BP480)
             subbname8090DEVCR2D04OTU210(561735),    -- 4-Port 10G OTU2-XFP Physical Interface Card(PIC)
             subbname8090DEVCR2D0E5XMF10(561736),    -- 2-Port 50GBase/1-Port 100GBase-QSFP28 Physical Interface Card(PIC)
             subbname8090DEVCR2D00LAXF11(561737),    -- 10-Port 10GBase-X-SFP+ Physical Interface Card(PIC)
             subbname8090DEVCR2D00E1NC11(561738),    -- 1-Port 100GBase-CFP2 Physical Interface Card(PIC)
             subbname8090DEVCR2D00E2NF10(561739),    -- 2-Port 100GBase-QSFP28 Physical Interface Card(PIC)
             subbname8090DEVCX6D0E2NBA10(561740),      -- 2-Port 100GBase-QSFP28 Flexible Card A(S480-A)
             subbname8090DEVME0M0E2NFB70(561741),      -- 2-Port 100GBase-QSFP28 Flexible Card H(BP400-H)
             subbname8090DEVME0M0E2NFB71(561742),      -- 2-Port 100GBase-QSFP28 Flexible Card(BP480)
            subbname8090DEVCX6DE2VE1N10(561743),      -- 2-Port 50GBase/1-Port 100GBase-QSFP28 FlexE Flexible Card (S120)
             subbname8090DEVNEDD00EX4S00(225564),    --Finished Board Unit,NE08E-S6E,NED1EX4S0,4 Channels 10GE Optical Interface Board(SFP+)
             subbname8090DEVANKD001EV100(225622),       --1 Channel 50G Base QSFP28 High Speed Interface Board
             subbname8090DEVCR5D00E1NC7D(537713),       --1-Port 100GBase-CFP2 Flexible Card A(P240-A)
             subbname8090DEVCX68E2NLHXF0(537426),       --2-Port 100GBase-QSFP28 + 30-Port 10GBase-X-SFP+
             subbname8090DEVCR5D00E4XF20(537427),       --4-Port 10GBase-SFP+MACsec Interface Card
             subbname8090DEVCR5D00E1NB20(537428),       --1-Port 100GBase-QSFP28+MACsec Interface Card
             subbname8090DEVCR5DE2NE4X10(537429),       --2-Port 100GBase-QSFP28/1-Port100GBase-QSFP28+4-Port 10GBase-SFP+MACsec Interface Card
             subbname8090DEVAND1EM8F(537430),    -- ATN 950B,AND1EM8F0,8 Channels GE/FE Optical Interface Board
             subbname8090DEVAND1EM8T(537431),    -- ATN 950B,AND1EM8T0,8 Channels GE/FE Electric Interface Board
             subbname8090DEVAND1EM4F(537432),    -- ATN 950B,AND1EM4F0,4 Channels GE/FE Optical Interface Board
             subbname8090DEVAND1EM4T(537433),    -- ATN 950B,AND1EM4T0,4 Channels GE/FE Electric Interface Board
             subbname8090DEVAND1EX1(537434),                -- 1 Channel 10 GE Optical Interface board
             subbname8090DEVAND2EM8M(537435),           -- 4 Channels GE/FE Optical Interface and 4 Channels GE/FE Electric Interface Board
             subbnameATNAND3MD1(537436),              -- 32 Channels E1 Interface Board
             subbnameATNNEDD001EM600(537437),            --6 Channels E&M Interface Board
             subbnameATNNED3MD1(537438),                       -- 32 Channels E1 Interface Board
             subbname8090DEVCR2D000EM890(537439),       --6 Channels E&M Interface Board
             subbname8090DEVCR57E1NBA2(537735),         -- 1-Port 100GBase-QSFP28 Fixed Card
             subbname8090DEVCR5D00T1NC70(537440),       --03032PCD,  1-Port 100G OTN/ETH-CFP2 Flexible Card(P240)
             subbname8090DEVCR9D00EANB81(537441),       --10-Port 100GBase-QSFP28 MacSec Flexible Card
             subbname8090DEVCR9D00EANB80(537442),       --10-Port 100GBase-QSFP28 Flexible Card
             subbname8090DEVCR2D0EM4TP10(537443),       --4 Port 100/100Base -RJ45 with PoE Physical Interface Card
             subbname8090DEVCR58EANBA(537444),          --10-Port 100GBase QSFP28 MACsec fixed Card
             subbname8090DEVCR2D0L4XFM10(537445),       --4-Port 10GBase-SFP+MACsec Interface Card
             subbname8090DEVNEDD0EX4SM00(537446),       --4 Channel 10GE Optical Interface Board with MACSec (SFP+)
             subbname8090DEVNEDD0EM4TP00(537447),       --4 Port 100/1000Base-RJ45 with PoE Physical Interface Card
             subbname8090DEVCR58EANBA1(537448),       --10-Port 100GBase QSFP28 MACsec fixed Card
             subbname8090DEVCR9D00LFXF81(537449),    --24-Port 1000M/10GBase LAN/WAN-SFP+ Flexible Card-C
               subbnameATNANKD001EY401(225650),   --4 Channels 25G (SFP28)/4 Channels 10G (SFP+) High Speed Interface Board
               subbnameATNANKD001EV102(225651),   --1 Channel 50G Base QSFP28 High Speed Interface Board CM(30GE enable by default)
               subbnameATNANKD001EV201(225653),   --2 Channels 50G/1 Channel 100G Base QSFP28 High Speed Interface Board(50GE enable by default)
               subbnameATNANKD01EXAS01(225654),   --10 Channels 10GE Optical Interface Board(SFP+)
               subbnameATNANKD001EY201(225655),   --2 Channels 25G (SFP28)/2 Channels 10G (SFP+) High Speed Interface Board
               subbnameATNANKD001EY101(225656),   --1 Channels 25G (SFP28)/2 Channels 10G (SFP+) High Speed Interface Board
               subbnameNEDD00EV1Q00(225657),        --1 Channel 50GE Optical Interface Board(QSFP28)
			    subbname8090DEVCR5D0E5XMF91(225700),       --2-Port 50GBase/1-Port 100GBase-QSFP28 FlexE MACsec Physical Interface Card CM(PIC)(Default Enable 1*50GE)
              subbname8090DEVCR5D00E4XM25(225701),       --4-Port 25GE(SFP28)/10GE(SFP+) MACsec Physical Interface Card (PIC)
              subbname8090DEVCR5D00E8XM25(225702),       --8-Port 25GE(SFP28)/10GE(SFP+) MACsec Physical Interface Card (PIC)
			  subbname8090DEVCR8D00L8YFC1(723821),       --8-Port 25GE(SFP28)/10GE(SFP+) MACsec Physical Interface Card (PIC)
              subbname8090DEVCR5D00LAXF91(225703),       --10-Port 10GBase LAN/WAN-SFP+ MACsec Physical Interface Card(PIC)
              subbname8090DEVCX6D0E5XMF91(225704),       --2-Port 50GBase/1-Port 100GBase-QSFP28 FlexE MACsec Physical Interface Card CM(PIC)(Default Enable 1*50GE)
              subbname8090DEVCX6D00E4XF91(225705),       --4-Port 25GE(SFP28)/10GE(SFP+) MACsec Interface Card (PIC)
              subbname8090DEVCX6D00E8XF91(225706),       --8-Port 25GE(SFP28)/10GE(SFP+) MACsec Interface Card (PIC)
              subbname8090DEVCX6D00LAXF91(225707),       --10-Port 10GBase LAN/WAN-SFP+ MACsec Interface Card(PIC)
              subbname8090DEVCR5DE4VE2N70(225708),       --4-Port 50GBase/2-Port 100GBase-QSFP28 FlexE/MACsec Flexible Card (P480)
              subbname8090DEVCR57E4VBE1(225709),       --8-Port 50GBase/4-Port 100GBase-QSFP28 FlexE/MACsec Integrated Line Processing Unit CM(LPUI-480-CM)
              subbname8090DEVCR57E8VBA1(225710),       --16-Port 50GBase/8-Port 100GBase-QSFP28 FlexE/MACsec Integrated Line Processing Unit (LPUI-1T)
			  subbname8090DEVCR57E8VBF2(226010),       --16-Port 50GBase/8-Port 100GBase-QSFP28 FlexE/MACsec Integrated Line Processing Unit (LPUI-1T)
              subbname8090DEVCR57EDYFA1(225712),       --32-Port 25GBase-QSFP28 MACsec Integrated Line Processing Unit (LPUI-1T)
              subbname8090DEVCR57EENBC0(225714),       --20-Port 100GBase-QSFP28 FlexE/MACsec Integrated Line Processing Unit (LPUI-2T)
              subbname8090DEVCX6DE4VE2N10(225716),       --4-Port 50GBase/2-Port 100GBase-QSFP28 FlexE/MACsec Flexible Card (S400)
              subbname8090DEVCR9D00LJXF80(225717),       --36-Port GE/10GE LAN/WAN-SFP+ MACSec Flexible Card CM
              subbname8090DEVCR9D00EANB82(225718),       --10-Port 100GE/50GE-QSFP28 MACSec/FlexE Flexible Card CM
              subbname8090DEVCR9D00E5NB80(225720),       --5-Port 100GE/10-Port 50GE-QSFP28 MACSec/FlexE Flexible Card CM
              subbname8090DEVCR9D00EDYF80(225721),       --16-Port 25GE-SFP28 MACSec Flexible Card CM
              subbname8090DEVGPR8CQ20YS(225722),         --NE40E-F1A-8H20Q
			  subbname8090DEVCR57EBGFD0(225723),         --12-Port 100/1000Base-X-SFP Fixed Card A(P51-A)
			  subbname8090DEVCR58EANBC1(225724),         --10-Port 100GBase-QSFP28 Flexible Card
               subbname8090DEVANKD001EY200(225623),   --2 Channels 25G (SFP28)/2 Channels 10G (SFP+) High Speed Interface Board
               subbname8090DEVCR5D00E4XF25(225624),   --4-Port 25GBase-SFP28 Physical Interface Card(PIC)
               subbname8090DEVCR5D00LJXF60(225640),       --36-Port 10GBase LAN/WAN-SFP+ Flexible Card CM(CP1T6,Occupy 1 sub-slot)
               subbname8090DEVCR5D00LFXF76(537450),    --24-Port 10GBase LAN/WAN-SFP+ Flexible Card A(P481-A)
               subbname8090DEVCR5D00LFXF75(537451),    --24-Port 10GBase LAN/WAN-SFP+ Flexible Card A(P481-E)
               subbname8090DEVCX6D00LFXF10(537452),    --24-Port 10GBase LAN/WAN-SFP+ Flexible Card A(S481-A)
               subbname8090DEVME0D00LFXF70(537453),    --24-Port 10GBase LAN/WAN-SFP+ Flexible Card(BP481)
               subbname8090DEVCR5D00E2NC78(537454),    --2-Port 100GBase-CFP2 Flexible Card A(P481-E)
               subbname8090DEVCR5D00E2NC79(537464),    --2-Port 100GBase-CFP2 Flexible Card A(P481-A)
               subbname8090DEVCX6D00E2NC10(537472),    --2-Port 100GBase-CFP2 Flexible Card A(S481-A)
               subbname8090DEVME0D00E2NC78(537473),    --2-Port 100GBase-CFP2 Flexible Card(BP481)
               subbname8090DEVCR5D00E2NF71(537474),    --2-Port 100GBase-QSFP28 Flexible Card A(P481-E)
               subbname8090DEVCR5D00E2NF72(537475),    --2-Port 100GBase-QSFP28 Flexible Card A(P481-A)
               subbname8090DEVCX6D00E2NF10(537476),    --2-Port 100GBase-QSFP28 Flexible Card A(S481-A)
               subbname8090DEVME0D00E2NF71(537477),    --2-Port 100GBase-QSFP28 Flexible Card(BP481)
               subbname8090DEVCR5D00E8NC64(537500),    -- 8-Port 100G CFP2 Flexible Card CM(CP1T6,Occupy 1 sub-slot)
               subbname8090DEVCR5D00E8NB61(537501),    -- 8-Port 100G QSFP28 Flexible Card CM(CP1T6,Occupy 1 sub-slot)
               subbname8090DEVCR5D00E2KC60(537502),    -- 2-Port 400G CFP8 Flexible Card CM(CP1T6,Occupy 1 sub-slot)
               subbname8090DEVCX6D0LEXFA12(562730),      -- 20-Port 10GBase LAN/WAN-SFP+ Flexible Card A(S480-A)
               subbname8090DEVCX68EENEFYFA(562731),   -- 20-Port 100GBase-QSFP28 + 24-Port 25GBase-Y-SFP+ A
               subbname8090DEVCR58E4K4NA0(562732),   -- 4-Port 400GBase CFP8 + 4-Port 100GBase QSFP28 Fixed Card
               subbname8090DEVCX6D0E2NCA12(562733),      -- 2-Port 100GBase-CFP2 Flexible Card A(S401-A)
               subbname8090DEVCR5D0E2NFH70(562734),      -- 2-Port 100GBase-QSFP28 Flexible Card H(P400-H)
               subbname8090DEVCR56LEXF3(561777),       -- 20-Port 10GBase LAN/WAN-SFP+ Flexible Card(CP400,Occupy 1 sub-slot)
               subbname8090DEVCR5D00LEXF74(561778),
               subbname8090DEVCR5D00LEXF73(561779),
               subbname8090DEVCX6D00LEXF10(561780),
               subbname8090DEVME0D00LEXF70(561781),
               subbname8090DEVCR56E2NCC3(561782), -- NE40E X16B,CR56E2NCC3 , 2-Port 100GBase-CFP2 Flexible Card(CP400,Occupy 1 sub-slot)

               subbname8090DEVCR53P4HF0(677001),	-- 4-port OC-12c/STM-4c POS-SFP Flexible Card
               subbname8090DEVCR5D00E8NB63(537503),    -- 8-Port 100G QSFP28 Flexible Card(CP1T6,Occupy 1 sub-slot)
               subbname8090DEVCR5D00E2KC61(537504),    -- 2-Port 400G CFP8 Flexible Card(CP1T6,Occupy 1 sub-slot)
               subbname8090DEVCR5D00E8NC65(537505),    -- 8-Port 100G CFP2 Flexible Card(CP1T6,Occupy 1 sub-slot)
               subbname8090DEVCR5D00LJXF61(537506),    -- 36-Port 10GBase LAN/WAN-SFP+ Flexible Card(CP1T6,Occupy 1 sub-slot)
               subbname8090DEVCR5D00E4NB63(537507),    -- 4-Port 100GBase QSFP28 Flexible Card CM(CP1T,Occupy 1 sub-slot)
               subbname8090DEVCR5D00LFXF63(537508),    -- 24-Port 10GBase LAN/WAN SFP+ Flexible Card CM(CP1T,Occupy 1 sub-slot)
               subbname8090DEVCR5D00E2NC63(537509),    -- 2-Port 100GBase-CFP2 Flexible Card CM(CP400,Occupy 1 sub-slot)
               subbname8090DEVCR5D00LEXF65(537510),    -- 20-Port 10GBase LAN/WAN-SFP+ Flexible Card CM(CP400,Occupy 1 sub-slot)

               subbname8090DEVCX6D00NBXFA0(580901),    -- V8R11C00 for CX6D00NBXFA0(SBOM) 12-Port 10G OTN/ETH-SFP+ Flexible Card
               subbname8090DEVCX6D00N2NCA0(580902),    -- V8R11C00 for CX6D00N2NCA0(SBOM) 2-Port 100G OTN/ETH-CFP2 Flexible Card

               subbname8090DEVCR53C2CF0(567890),    -- 2-Port Channelized OC-3c/STM-1c POS-SFP Flexible Card
                subbname8090DEVCR2D00MPAA90(561651),       --4-Channel FXS/FXO+2-Channel E&M+2-Channel RS232+2-Channel RS485 Board
                subbname8090DEVCR2D000SA890(561652),       --8-Channel V.35/X.21/V.24 Board
                subbname8090DEVCR2D00MP8A90(561653),       --4 Channels C37.94 Optical Interface and 4 Channels CoDir64K Electric Interface Board
            -- for NE5000E V800R005C01 Card SBOM
            subbname8090DEVCR5D00E2NC61(561407),   -- 2-Port 100GEBase-CXP Flexible Card(CP400,1 sub-slot)
            subbname8090DEVCR5D00E6MF61(561408),   -- 6-Port 40GBase-QSFP+ Flexible Card(CP400,1 sub-slot)
            subbname8090DEVCR5D0OLEXF61(561409),   -- 20-Port 10GBase LAN-SFP+ Flexible Card(CP400,1 sub-slot)
            subbname8090DEVCR5D00E1NC61(561410),   -- 1-Port 100GBase-CFP Flexible Card(CP400,1 sub-slots)
                subbname8090DEVCR5D00L5XF60(561411),   -- 5-Port 10GBase LAN/WAN-SFP+ Flexible Card B(CP100,2 sub-slots)
        subbname8090DEVCR5D00N2NC61(561416),   -- 2-Port 100G OTN/ETH-CFP2 Flexible Card(CP400,Occupy 1 sub-slot)
        subbname8090DEVCR5D00E1NC62(561417),   -- 1-Port 100GBase-CFP Flexible Card(CP400,Occupy 1 sub-slot)

                -- for NE5000E V800R008C00 Card SBOM
                subbname8090DEVCR5D00L2NC63(561418),   -- Finished Board,NE5000E,CR56E2NCC2,2-Port 100GBase-CFP2 Flexible Card(CP400,Occupy 1 sub-slot)
                subbname8090DEVCR5D00LEXF63(561419),   -- Finished Board,NE5000E,CR56LEXF2,20-Port 10GBase LAN/WAN-SFP+ Flexible Card(CP400,Occupy 1 sub-slot)

                --for CX600 V8R5  OC and NE40E  (561500 ~)
                subbname8090DEVCR5D00L2XF70(561500),   -- CX68L2XFB, 2-Port 10GBase LAN/WAN-SFP+  Physical Interface Card(PIC)
                subbname8090DEVCR5D00E8GF71(561501),   -- CX68E8GFC, 8-Port 100/1000Base-X-SFP  Physical Interface Card(PIC)
                subbname8090DEVCR5D00E8GE70(561502),   -- CX68E8GEB, 8-Port 10/100/1000Base-RJ45 Physical Interface Card(PIC)
                subbname8090DEVCR5D00L1XE8GF70(561503), -- 1-Port 10GBase LAN/WAN-SFP+  8-Port 100/1000Base-X-SFP Physical Interface Card(PIC)
                subbname8090DEVCR5D00C4CF71(561504),   -- CX68C4CF ,    4-Port Channelized STM-1c POS-SFP  Physical Interface Card(PIC)
                subbname8090DEVCR5D000IE170(561505),   -- CX68MIE1 ,    32-Port E1 Physical Interface Card(PIC,75ohm)
                subbname8090DEVCR5D000IE171(561506),   -- CX68MIE1B ,   32-Port E1 Physical Interface Card(PIC,120ohm)
                subbname8090DEVCR5D000DE170(561507),   -- CX68MDE1A ,   16-Port E1 Physical Interface Card(PIC,75ohm)
                subbname8090DEVCR5D000DE171(561508),   -- CX68MDE1B ,   16-Port E1 Physical Interface Card(PIC,120ohm)
                subbname8090DEVCR5D00L4XF70(561509),   -- CX68L4XF, 4-Port 10GBase-X-SFP+High-speed Interface Card(PIC)
                subbname8090DEVCR5D00P4CF70(561510),   -- CX67P4CFA, 4-Port OC-3c/STM-1c POS-SFP Flexible Interface Card(PIC)
                subbname8090DEVCR5D00AUXQ10(561511),   -- CX67AUXQ, Auxiliary  Flexible Interface Card with 4-Port 100Base-RJ45 (FIC,Supporting 1588v2)(PIC)
            subbname8090DEVCR5D00C4T370(561512),   -- CX68C4T3, 4-Port Clear Channel E3/Channelized T3 Physical Interface Card (PIC)
            subbname8090DEVCR57E3MB2(561513),       -- V6R8C10,03030WGU,3-Port 40GBase-QSFP+ Fixed Card
            subbname600DEVCR57LAXFB(561514),       -- V6R8C10,03031AKC,10-Port 10GBase LAN/WAN-SFP+ Fixed Card
            subbname600DEVCR57EFGFH2(561515),       -- V6R9C20,03031XQL,24-Port 1000Base-X-SFP Fixed Card E
            subbname600DEVCR57L5XFI3(561516),       -- V6R9C20,03031XQC,5-Port 10GBase LAN/WAN-SFP+ Fixed Card E
            subbname600DEVCR57L2XFI2(561517),       -- V6R9C20,03031XQH,2-Port 10GBase LAN/WAN-SFP+ Fixed Card E
                subbname8090DEVCR5D00P8UF70(561530),      -- 8-Port OC-48c/STM-16c POS-SFP Flexible Card(P120)
                subbname8090DEVCR5D00LFXF74(561531),      -- CR57LFXFE, 24-Port 10GBase LAN/WAN-SFP+ Flexible Card A(P480-A)
                subbname8090DEVCR5D00E2NC72(561532),      -- CR57E2NCE, 2-Port 100GBase-CFP2 Flexible Card A(P480-A)
                subbname8090DEVCR57LFXFE1(561533),      -- 48-Port 10GBase LAN/WAN-SFP+ Integrated Line Processing Unit (LPUI-480)
                subbname8090DEVCR57E2NCE1(561534),      -- 2-Port 100GBase-CFP2 + 24-Port 10GBase LAN/WAN-SFP+ Integrated Line Processing Unit (LPUI-480)

                subbname8090DEVCR57E2NCE(561535),    -- 2-Port 100GBase-CFP2 Flexible Card A(P480-A)
                subbname8090DEVCR57LFXFE(561536),    -- 24-Port 10GBase LAN/WAN-SFP+ Flexible Card A(P480-A)
                subbname8090DEVCR57LEXFE(561537),    -- 20-Port 10GBase LAN/WAN-SFP+ Flexible Card
                subbname8090DEVCX6D00A2HF10(561538),    -- 2-Port OC-12c/STM-4c ATM-SFP Flexible Card(S10)
                subbname8090DEVCR5D0L2XFH71(561539),    -- CX68L2XFC, 2-Port 10GBase LAN/WAN-SFP+ Physical Interface Card H (PIC-H)
                subbname8090DEVCR5D0EAGFH70(561540),    -- CX68EAGFD, 10-Port 100/1000Base-X-SFP Physical Interface Card H (PIC-H)
                subbname8090DEVCR5D00EAGF70(561541),    -- CX68EAGFD, 10-Port 100/1000Base-X-SFP Physical Interface Card(PIC)
                subbname8090DEVCR5DL1XE8G71(561542),    -- CX68L1XE8GFB, 1-Port 10GBase LAN/WAN-SFP+ + 8-Port 100/1000Base-X-SFP Physical Interface Card(PIC)
                subbname8090DEVCR5DP4C2HF70(561543),    -- CX68P4CFC, 4-Port OC-3c/STM-1c (or 2-Port OC12c/STM-4c)  POS-SFP Physical Interface Card(PIC)
                subbname8090DEVCR5D00E8GE71(561544),    -- CX68E8GED, 8-Port 100/1000Base-RJ45 Physical Interface Card(PIC)
                subbname8090DEVCR5D00L4XF72(561545),    -- CX68L4XFD, 4-Port 10GBase LAN/WAN-SFP+ Physical Interface Card(PIC)
                subbname8090DEVCR5D00L2XF71(561546),    -- CX68L2XFC, 2-Port 10GBase LAN/WAN-SFP+ Physical Interface Card(PIC)
                subbname8090DEVCR5DP4C2HF7020(561547),  -- CX68P2HFC, 4-Port OC-3c/STM-1c (or 2-Port OC12c/STM-4c)  POS-SFP Physical Interface Card(PIC)

                subbname8090DEVCR5D0E3MFA70(564768), -- 3-Port 40GBase-QSFP+ Flexible Card(P240-A)
                subbname8090DEVCR5D00TBXF70(564769), -- 12-Port OTU2-SFP+ Flexible Card(P120)
                subbname8090DEVCR5D00T6XF70(564770), -- 6-Port OTU2-SFP+ Flexible Card(P120)
                subbname8090DEVCR5D00T1NV70(564771), -- 1-Port OTU4-80KM-LC Flexible Card A(P240-A)
                subbname8090DEVCR5D0LAXFE70(564773), -- 10-Port 10GBase LAN/WAN-SFP+ Flexible Card E(P240-E)
				subbname8090DEVCR5D0LBXFE7E(537479), -- 10-Port 10GBase LAN/WAN-SFP+ Flexible Card E(P240-E)
                subbname8090DEVCR5D00L1NC7E(537495), -- 1-Port 100GBase-CFP2 Flexible Card E(P241-E)
				subbname8090DEVME0D0LBXFE7E(537478), -- 10-Port 10GBase LAN/WAN-SFP+ Flexible Card E(P240-E)
				subbname8090DEVME0D0L6XXB7H(561499), --03032YUU,  6-Port 10GBase WAN/LAN-XFP Flexible Card(BP100)
				subbname8090DEVME0D00L1NC7E(537494), -- 1-Port 100GBase-CFP2 Flexible Card E(P241-E)

                subbname8090DEVME0D0LAXFE7H(561420), -- 10-Port 10GBase LAN/WAN-SFP+ Flexible Card E(BP240-E)
                subbname8090DEVCX6D0E2NCA10(561667),   --2-Port 100GBase-CFP2 Flexible Card A(S480-A)
                subbname8090DEVCX6D0LFXFA11(561668),   --24-Port 10GBase LAN/WAN-SFP+ Flexible Card A(S480-A)
                subbname8090DEVCR5D0L5XFH70(561430),   -- 5-Port 10GBase LAN/WAN-SFP+ Flexible Card H(P120-H)
        subbname8090DEVME0D0L5XFH7H(561431),   -- 5-Port 10GBase LAN/WAN-SFP+ Flexible Card H(BP100-H)
        subbname8090DEVCX6D0L5XFH10(561432),   -- 5-Port 10GBase LAN/WAN-SFP+ Flexible Card H(S102-H)
        subbname8090DEVCR5D0L2XFH70(561433),   -- 2-Port 10GBase LAN/WAN-SFP+ Flexible Card H(P51-H)
        subbname8090DEVME0D0L2XFH7H(561434),   -- 2-Port 10GBase LAN/WAN-SFP+ Flexible Card H(BP51-H)
        subbname8090DEVCR5D0L1XFA70(561435),   -- 1-Port 10GBase LAN/WAN-SFP+ Flexible Card A(P50-A)
        subbname8090DEVTNRD00MD8A70(561436),   -- 8-Channel CWDM Multiplexing & Demultiplexing Flexible Card
        subbname8090DEVCR5D00MD8A70(561437),   -- 8-Channel CWDM Multiplexing & Demultiplexing (1471/1491/1511/1531/1551/1571/1591/1611nm) Flexible Card(P50)
        subbname8090DEVBGWD0L5XFE70(561438),   -- 5-Port 10GBase LAN/WAN-SFP+ Flexible Card(BP100)
        subbname8090DEVBGWD0LAXFE70(561439),   -- 10-Port 10GBase LAN/WAN-SFP+ Flexible Card(BP200)
        subbname8090DEVME0D0LAXFH7H(561440),   -- 10-Port 10GBase LAN/WAN-SFP+ Flexible Card H(BP240-H)

        subbname8090DEVCR2D00E1NC10(561607), --1-Port 100GBase-CFP2 Physical Interface Card(PIC)
        subbname8090DEVCR2D00LAXF10(561608), --10-Port 10GBase LAN/WAN-SFP+ Physical Interface Card
        subbname8090DEVME0D0EAGFE70(561588), -- 10-Port 100/1000Base-X-SFP  Physical Interface Card E(PIC-E)
        subbname8090DEVME0D0L2XFE71(561589), -- 2-Port 10GBase LAN/WAN-SFP+  Physical Interface Card(PIC-E)
        subbname8090DEVCR5D00E1NC79(561594), -- 1-Port 100GBase LAN/WAN-CFP2  Physical Interface Card(PIC)
        subbname8090DEVCR5D00LAXF71(561595), -- 10-Port 10GBase LAN/WAN-SFP+  Physical Interface Card(PIC)
        subbname8090DEVCR5D0EFGFE71(561578), -- 24-Port 1000Base-X-SFP Flexible Card  E(P52-E)
        subbname8090DEVCR5D0L5XFE74(561579), -- 5-Port 10GBase LAN/WAN-SFP+ Flexible Card E(P52-E, Occupy two sub-slots)
        subbname8090DEVCR5D0L2XFE75(561580), -- 2-Port 10GBase LAN/WAN-SFP+ Flexible Card E(P52-E)
        subbname8090DEVCR5D0L5XFE76(561581), -- 5-Port 10GBase LAN/WAN-SFP+ Flexible Card E(P120-E)
        subbname8090DEVME0D0EFGFE7E(561582), -- 24-Port 1000Base-X-SFP Flexible Card E(BP52-E)
        subbname8090DEVME0D0L5XXE7E(561583), -- 5-Port 10GBase LAN/WAN-SFP+ Flexible Card E(BP52-E,occupy 2 sub-slot)
        subbname8090DEVME0D0L5XXE8E(561584), -- 5-Port 10GBase LAN/WAN-SFP+ Flexible Card E(BP120-E)
        subbname8090DEVME0D0L2XXE7E(561585), -- 2-Port 10GBase LAN/WAN-SFP+ Flexible Card E(BP5E-E)
        subbname8090DEVCR5D0LAXFH70(561586), -- 10-Port 10GBase LAN/WAN-SFP+ Flexible Card H(P240-H)
        subbname8090DEVCX6D0LAXFH10(561587),   -- 10-Port 10GBase LAN/WAN-SFP+ Flexible Card H(S200-H)
        subbname8090DEVCR5D0E2NCE70(561596), -- 2-Port 100GBase-CFP2 Flexible Card E(P480-E)
        subbname8090DEVCR5D0LEXFE70(561597), -- 20-Port 10GBase LAN/WAN-SFP+ Flexible Card E(P480-E)
        subbname8090DEVMEOM0LEXFB70(561598), -- 20-Port 10GBase LAN/WAN-SFP+ Flexible Card(BP480)
        subbname8090DEVMEOM0E2NCB70(561599), -- 2-Port 100GBase-CFP Flexible Card(BP480)
        subbname8090DEVCR57L5XFI3(561605), -- 5-Port 10GBase LAN/WAN-SFP+ Fixed Card E
        subbname8090DEVCR57L2XFI2(561606), -- 2-Port 10GBase LAN/WAN-SFP+ Fixed Card E
        subbname8090DEVCR57EFGFH2(561609), -- 24-Port 1000Base-X-SFP Fixed Card E
        subbname8090DEVCR5D0L2XFH72(561592),   -- 2-Port 10GBase LAN/WAN-SFP+  Physical Interface Card H (PIC-H)
        subbname8090DEVCR2D0L2XFH11(561590),   -- 8-Port 100/1000Base-X-SFP  Physical Interface Card H
        subbname8090DEVCR5D0E8GFH70(561593),   -- 2-Port 10GBase LAN/WAN-SFP+  Physical Interface Card H (PIC-H)
        subbname8090DEVCR2D0E8GFH10(561591),   -- 8-Port 100/1000Base-X-SFP  Physical Interface Card H
        subbname8090DEVCR58E8NBA(561622),   -- 8*100GBase QSFP28 Card
        subbname8090DEVCR58D8NCA(561624),   -- 8-Port 100GBase-CFP DWDM Card
        subbname8090DEVCR56E4NBA1(561623), -- 4-Port 100GBase QSFP28 Flexible Card(CP1T,Occupy 1 sub-slot)
        subbname8090DEVCR5D00E4NB60(561600), -- 4-Port 100GBase QSFP28 Flexible Card(CP1T,Occupy 1 sub-slot)
        subbname8090DEVCR5DE2NLEX60(561601), -- 2-Port 100GBase QSFP28+20-Port 10GBase LAN/WAN SFP+ Flexible Card(CP1T,Occupy 1 sub-slot)
        subbname8090DEVCR5D00LFXF60(561602), -- 24-Port 10GBase LAN/WAN SFP+ Flexible Card(CP1T,Occupy 1 sub-slot)
        subbname8090DEVCR5D00N4NC60(561603), -- 4-Port 100G OTN/ETH CFP4 Flexible Card(CP1T,Occupy 1 sub-slot)
        subbname8090DEVCR5D00LMXB60(561604), -- 48-Port 10GBase LAN/WAN QSFP+  Sharp Flexible Card(CP1T,Occupy 1 sub-slot)
        subbname8090DEVCR5DE2VE1N70(537466),      --03032MVX, CR5DE2VE1N70, 2-Port 50GBase/1-Port 100GBase-QSFP28 FlexE Flexible Card (P120)
        subbname8090DEVCR5D00E25F10(561640),       --03032QNG, CR5D00E25F10, 2 Port 50G Base QSFP28 High Speed Interface Card
        subbname8090DEVCR58EENBA0(537465),       --03032MYU, CR58EENBA0,20*100GBase QSFP28 flexible Dauhtger Card
        subbname8090DEVCR5D0E2NFE70(561730),        --03032LCN, CR5D0E2NFE70, 2-Port 100GBase-QSFP28 Flexible Card E(P480-E)
        subbname8090DEVCR58E4KCA0(537467),           --03032MYC, CR58E4KCA0, 4-Port 400GBase CFP8 Daughter Card
        subbname8090DEVCR58D8NCB0(537470),           --03032NAC, CR58D8NCB0, 8-Port 100G CFP2 flexible Dauhtger Card
        subbname8090DEVCR57EENBE0(537471),            --03032MWM, CR57EENBE0, 20-Port 100GBase QSFP28 Integrated Line Process Unit(NE40E LPUI-2T)
		subbname8090DEVCR59LJXFF(225644),             --36-Port 10GBase LAN/WAN SFP+ Fixed Card
        subbnameCARDATN910CG(333115),                 --ATN910C-G virtual card,16*10GE(o), 12*GE /GE/FE(o),4*GE/FE(e)
        subbnameCARDATN910CS(333113),                 --ATN910C-S virtual card,5*10GE(o), 3*10GE /GE/FE(o),4*GE/FE(e)
        subbname8090DEVCR9D00EANB83(225719),          --10-Port 100GE-QSFP28 Flexible Card CM
        subbnameCARDATN910CH(333114),                 --ATN910C-H virtual card,4*10GE(o), 4*10GE /GE/FE(o),4*GE/FE(e)
        subbname8090DEV910D-H(333118),                 --card ATN 910D-H
		subbname8090DEVNetEngine-8000-M1D-A(235929),  --CARD NetEngine 8000 M1D-A
        subbname8090DEVCR8DE4NB00M4(709872),   -- 4-Port 100GBase/50GBase-QSFP28 Physical Interface Card(PIC)
        subbname8090DEVCR8DE4NB00M5(709873),   -- 4-Port 100GBase/50GBase-QSFP28 Physical Interface Card CM(Enable 2*100GE by default)(PIC)
        subbname8090DEVCR8D0LJXXCCQ(513270),   -- 36-Port 10GBase LAN/WAN-SFP+ MACsec Flexible Card CM(P1T-CM)
        subbname8090DEVANNDE8EFFEC1(549699),   -- 8-Port 10GE-SFP+ FlexE High Speed Interface Board
        subbname8090DEVCR8DE4KBFECS(709847),   -- 4-Port 400GBase-QSFP-DD FlexE MACsec Flexible Card CM(P3T2-CM,400GE Port Enabled with 100GE by default)
        subbname8090DEVCR5D00LAXF92(709874),   -- 10-Port 10GE/GE LAN/WAN-SFP+ MACsec Physical Interface Card(PIC)
        subbname8090DEVCARDNetEngineXH821(235930),    --CARD NetEngine XH821
        subbname8090DEVCARDNetEngineXH821E(235931),   --CARD NetEngine XH821 E
        subbname8090DEVCARDNetEngineXH86(235932),     --CARD NetEngine XH861
        subbname8090DEVCARDNetEngineXH861E(235933),     --CARD NetEngine XH861E"
        subbname8090DEVCR59TDNBA1(709798),             --16xOTU4/16x100GE QSFP28 Fixed card
        subbname8090DEVCR8D800E8KC2(709869),           --8-Port 400GBase-QSFP-DD FlexE MACsec Flexible Card CM(P6T4-CM,400GE Port Enabled with 100GE by default)
        subbname8090DEVCR8DEFNBFCE1(709838),           --24-Port 100GBase-QSFP28 FlexE MACsec Flexible Card E CM(P6T4-E-CM)
        subbname8090DEVCR8DG80400C0(548792),           --4 Channels C37.94 and 4 Channels 64K Physical Interface Card
        subbname8090DEVCR59TDNBA0(709797),             --16xOTU4/16x100GE QSFP28 Fixed card
        subbname8090DEVCR8DE2NBMSF2(548700),           --2-Port 100GBase/50GBase-QSFP28 Interface Card(PIC)
        subbname8090DEVCR8DE2NBMSF3(548701),           --2-Port 100GBase/50GBase-QSFP28 Interface Card(PIC)
        subbname8090DEVXHMDE1KB01M0(548702),   -- 1-Port 400GBase-QSFP-DD Single-layer Physical Interface Card(PIC)
        subbname8090DEVXHMDE4NB01M0(548703),   -- 4-Port 100GBase/50GBase-QSFP28 Physical Interface Card(PIC)
        subbname8090DEVXHMDE4NB01M1(548704),   -- 4-Port 100GBase/50GBase-QSFP28 Physical Interface Card(PIC)(Enable 2*100GE by default)
        subbname8090DEVXHMDEAGMXF00(548705),   -- 10-Port 10GE/GE LAN/WAN-SFP+ MACsec Physical Interface Card(PIC)
        subbname8090DEVXHMDE4GMXF00(548706),   -- 4-Port 10GE-SFP+ FlexE MACsec Physical Interface Card(PIC)
        subbname8090DEVCR8DEDNBFECT(709857),           --2-Port 100GBase/50GBase-QSFP28 Interface Card(PIC)
        subbnameCARDATN910CS60G(333120),               --ATN910C-S-60G virtual card,6*10GE(o), 2*10GE /GE/FE(o),4*GE/FE(e)
              subbname8090DEV905-L(115928),            --CARD ATN 905-L
              subbname8090DEVNetEngine-A816(115929),   --CARD NetEngine A816
              subbname8090DEVNetEngine-A816-E(115930), --CARD NetEngine A816 E
              subbname8090DEVANNDE1NBFM01(548799),      --1-Port 100GBase/50GBase-QSFP28 FlexE MACsec+8-Port 10GE(SFP+)/GE(SFP) MACsec Physical Interface Card(PIC)
              subbname8090DEVIG2D0LJXX0CP(513269),   -- 36-Port 10GBase LAN/WAN-SFP Flexible Card(P1T)
              subbname8090DEVIG2D0E5NBCCP(513233),   -- 5-Port 100GBase-QSFP28 FlexE MACsec Flexible Card(P1T)
              subbname8090DEVANOD001EY401(225652),   -- 4 Channels 25G (SFP28)/4 Channels 10G (SFP+) High Speed Interface Board
              subbname8090DEVANOD001EY410(225658),   -- 4 Channels 25G (SFP28)/4 Channels 10G (SFP+) High Speed Interface Board
              subbname8090DEVCR8DE1KB00M5(709870),   -- 1-Port 400GBase-QSFP-DD Single-layer Physical Interface Card(PIC)
			  subbname8090DEVCR8DE1KB00M6(709871),   -- 1-Port 400GBase-QSFP-DD Single-layer Physical Interface Card CM(Enable 1*100G)(PIC)
			  subbname8090DEVANODE1KB00M1(709875),   -- 1-Port 400GBase-QSFP-DD Physical Interface Card(PIC)
			  subbname8090DEVANODE1KB00M2(709876),   -- 1-Port 400GBase-QSFP-DD Physical Interface Card CM(Enable 1*100G)(PIC)
			  subbname8090DEVANODE1KB00D1(709877),   -- 1-Port 400GBase-QSFP-DD Physical Interface Card(PIC)
			  subbname8090DEVANOD00EM8F01(709878),   -- 8 Channels GE/FE Electrical Interface Board
			  subbname8090DEVANOD00EM8FE0(709879),   -- 8 Channels GE/FE Electrical Interface Board
			  subbname8090DEVANOD0EM10F00(709880),   -- 10 Channels GE/FE Optical Interface Board
			  subbname8090DEVANOD0EM10GE0(709881),   -- 10 Channels GE/FE Optical Interface Board
			  subbname8090DEVANOD01EXAS01(709882),   -- 10 Channels 10GE Optical Interface Board(SFP+)
			  subbname8090DEVANOD01EXAS10(709883),   -- 10 Channels 10GE Optical Interface Board(SFP+)
			  subbname8090DEVANODE2NB00C2(709884),   -- 2-Port 100GBase/50GBase-QSFP28 Interface Card(PIC)
			  subbname8090DEVANODE2NB00D2(709885),   -- 2-Port 100GBase/50GBase-QSFP28 Interface Card(PIC)
			  subbname8090DEVANND000EM890(709886),   -- 6 Channes E&M Interface Board
              subbname8090DEVIG2D84KBFECP(709896),   -- 4-Port 400GBase-QSFP-DD FlexE MACsec Flexible Card(P3T2)
              subbname8090DEVIG2D8DNBFECQ(709897),   -- 16-Port 100GBase-QSFP28 FlexE MACsec Flexible Card(P3T2)
              subbname8090DEVXHMDE1KB00C0(709930),   -- 1-Port 400GBase-QSFP-DD Single-layer Physical Interface Card(PIC)
              subbname8090DEVXHMDE1KB00C1(709931),   -- 1-Port 400GBase-QSFP-DD Single-layer Physical Interface Card CM(Enable 1*100G)(PIC)
              subbname8090DEVXHMDE1KB00C2(709932),   -- 1-Port 400GBase-QSFP-DD Single-layer Physical Interface Card(PIC)
              subbname8090DEVXHMDE1KB00C3(709933),   -- 1-Port 400GBase-QSFP-DD Single-layer Physical Interface Card CM(Enable 1*100G)(PIC)
              subbname8090DEVXHMDE4NB00C0(709934),   -- 4-Port 100GBase/50GBase-QSFP28 Physical Interface Card(PIC)
              subbname8090DEVXHMDE4NB00C1(709935),   -- 4-Port 100GBase/50GBase-QSFP28 Physical Interface Card CM(Enable 2*100GE by default)(PIC)
              subbname8090DEVXHMDE4NB00C2(709936),   -- 4-Port 100GBase/50GBase-QSFP28 Physical Interface Card(PIC)
              subbname8090DEVXHMDLAXF00C0(709938),   -- 4-Port 100GBase/50GBase-QSFP28 Physical Interface Card CM(Enable 2*100GE by default)(PIC)
              subbname8090DEVXHMDLAXF00C1(709939),   -- 1-Port 400GBase-QSFP-DD Single-layer Physical Interface Card(PIC)
              subbname8090DEVXHMDE4NB00C3(709937),   -- 4-Port 100GBase/50GBase-QSFP28 Physical Interface Card CM(Enable 2*100GE by default)(PIC)

-- ME60:
                subbnameME60Unkown(159744),
                subbnameME60P1XZE0(159745),        --ME60P1XZE0 Module
                subbnameME60W1XQE0(159746),        --ME60W1XQE0 Module
                subbnameME60W1XSE0(159747),        --ME60W1XSE0 Module
                subbnameME60E1XQE0(159748),        --ME60E1XQE0 Module
                subbnameME60E1XSE0(159749),        --ME60E1XSE0 Module
                subbnameME60EAGFE0(159750),        --ME60EAGFE0 Module
                subbnameME60P4UFE0(159751),        --ME60P4UFE0 Module
                subbnameME60EAGFB0(159752),        --ME60EAGFB0 Module
                subbnameME60P1XQE0(159753),        --ME60P1XQE0 Module
                subbnameME60P1XVE0(159754),        --ME60P1XVE0 Module
                subbnameME60E1XSB0(159755),        --ME60E1XSB0 Module
                subbnameME60E1XQB0(159756),        --ME60E1XQB0 Module
                subbnameME60W1XSB0(159757),        --ME60W1XSB0 Module
                subbnameME60W1XQB0(159758),        --ME60W1XQB0 Module
                subbnameME60EFGEB0(159759),        --ME60EFGEB0 Module

                subbnameME60EFGFB0(159760),         --ME01EFGFB0 Module
                subbnameME60E2XXB0(159761),         --ME01E2XXB0 Module
                subbnameME60EAGFB1(159762),         --ME01EAGFB1 Module
                subbnameME60E5GFB0(159763),         --ME01E5GFB0 Module
                subbnameME60E1XXB0(159764),         --ME01E1XXB0 Module
                subbnameME60P2XXM0(159765),         --ME01P2XXM0 Module
                subbnameME60EFGFM0(159766),         --ME01EFGFM0 Module
                subbnameME60EAGFM0(159767),         --ME01EAGFM0 Module
                subbnameME60P8CFM0(159768),         --ME01P8CFM0 Module
                subbnameME60P4HFM0(159769),         --ME01P4HFM0 Module
                subbnameME60P4UFM0(159770),         --ME01P4UFM0 Module
                subbnameME60E1XXM0(159771),         --ME01E1XXM0 Module
                subbnameME60E2XXM0(159772),         --ME01E2XXM0 Module
                subbnameME60P1XXM0(159773),         --ME01P1XXM0 Module

                subbnameME60A4HFB0(159774),         --ME01A4HFB0 Module
                subbnameME60AGCFB0(159775),         --ME01AGCFB0 Module
                subbnameME60E4GFB0(159776),         --ME01E4GFB0 Module
                subbnameME60EWFEB0(159777),         --ME01EWFEB0 Module
                subbnameME60EGFFB0(159778),         --ME01EGFFB0 Module

                subbnameME60EMGFB0(159779),         --ME01EMGFB0 Module
                subbnameME60EMGFM0(159780),         --ME01EMGFM0 Module

                subbnameME60EFFFB1(159781),         --24*1000Base SFP Light/Electrical Interface BSU line control board
                subbnameME60EFFFM0(159782),          --24*1000Base SFP Light/Electrical Interface MSU line control board

                subbnameME60EAGFYB0(159783),         --10*1GE SFP Light/Electrical Interface with TM  -1*1

                subbnameME60A8CFB0(159784),         --ME60A8CFB0 Module
                subbnameME60P8CFM1(159785),         --ME60P8CFM1 Module

                subbnameME60E4XXB0(159786),         --ME60E4XXB0 Module
                subbnameME60E4XXM0(159787),          --ME60E4XXM0 Module
                subbnameME03EEGFE0(159792),         --LPUF-40/41 20*GE TM card, support BRAS HQOS
                subbnameME03L5XFA0(159793),         --LPUF-101 5*10GE SFP+ Optical card, 1/2 width, no 1588
                subbnameME03E1NC0(159794),          --LPUF-101 1*100GE, test only
                subbnameME03P1MZ0(159795),          --1-port 40G POS XFP  Flexible Pluggable Interface Daughter Card
                subbnameME03L2XXB0(159796),         --LPUF-40/41 2*10GE TM card, support BRAS HQOS
                subbnameME03L2XXB1(159797),         --LPUF-40/41 2*10GE DPI card
                subbnameME01A8CFB1(159799),         --ME01A8CFB1 Module
                subbnameME60VSUF80(159800),           --SPU2.0 Board Sub Card(VSUF80)
                subbnameME60VSUF160(159801),           --SPU2.0 Board Sub Card(VSUF160)

                --V6R7 card packing ME60
                subbnameME0D0EFGFB7H(159802),    --24-Port 100/1000Base-X-SFP Flexible Card(BP51)
                subbnameME0D0L5XXB7F(159803),    --5-Port 10GBase WAN/LAN-XFP Flexible Card(BP51)
                subbnameME0D0L2XXB7H(159804),    --2-Port 10GBase WAN/LAN-XFP Flexible Card(BP51)
                subbnameME0D0EFGFE7H(159805),    --24-Port 1000Base-X-SFP Flexible Card E(BP51-E)
                subbnameME0D0L5XXE7F(159806),    --5-Port 10GBase WAN/LAN-XFP Flexible Card E(BP51-E)
                subbnameME0D0L2XXE7H(159807),    --2-Port 10GBase WAN/LAN-XFP Flexible Card E(BP51-E)
                subbnameME0D0L6XXB7H(159808),    --6-Port 10GBase WAN/LAN-XFP Flexible Card(BP100)
                subbnameME0D0L5XXB7H(159809),    --5-Port 10GBase WAN/LAN-XFP Flexible Card(BP100)
                subbnameME0D0L5XXE7H(159810),    --5-Port 10GBase WAN/LAN-XFP Flexible Card E(BP100-E)
                subbnameME0D0L1NXB7H(159811),    --1-Port 100GBase WAN/LAN-XFP Flexible Card(BP100)
                subbnameME0D0LBXXB7H(159812),    --12-Port 10GBase WAN/LAN-XFP Flexible Card(BP240)
                subbnameME0D2L1NXB7H(159813),    --1-Port 100GBase WAN/LAN-XFP Flexible Card(BP240)
                --V6R8 card packing ME60
                subbnameME0D0LBXXE7H(564729),    --12-Port 10GBase LAN/WAN-SFP+ Flexible Card E(BP240-E)
                -- for V600R009C30,vsuf
                subbnameME0D00SP8072(159814),    --Versatile Service Daught Card(SP80-T)

                subbnameME0D00SP8071(159816),      --ME0D00SP8071 Versatile Service Unit Sub Card(SP80-M)
                subbnameME0D00SPD071(159815),      --ME0D00SPD071 Versatile Service Unit Sub Card(SP160-M)

-- S9300:       0x000A1000~0x000A1fff(659456~663551)
                subbnameLE01FSUA(659456),
                subbnameLE0D00CKMA00(659457),          --Clock Pinch Board-1588
                subbnameLE0MFSUA(659458),              --Flexible Service Unit
                subbnameLE02CKMB(659459),              --Clock Pinch Board-BITS/1588
                subbnameLE0D0VSTSA00(659460),
                subbnameLE02S4USE(659461),
                subbnameLE02TCAMA(659462),
                subbnameCR53P1UF(659463),              --1-Port OC-48c/STM-16C POS SFP Flexible Pluggable Interface Daughter Card
                subbnameCR53P4HF(659464),              --4-Port OC-12c/STM-4C POS SFP Flexible Card
                subbnameCR53P4CF(659465),              --4-Port OC-3c/STM-1C POS SFP Flexible Card
                subbnameCR53E8GF(659466),              --8-Port FE/GE SFP Flexible Pluggable Interface Daughter Card
                subnameLE2D2VS08000(659467),           --8-Port 10G Cluster Switching System Service Unit (SFP+)
                subbnameLE2D2SC86S00(659468),          --x86 Service Process Sub-card
                subbnameLE1D2VS04000(659469),          --4-Port 10G Cluster Switching System Service Unit (SFP+)

-- S7700:       0x000A2000~0x000A2fff(663552~667647)
                subbnameES0D00FSUA00(663552),          --Flexible Service Unit
                subbnameES1D2VS04000(663553),          --4-Port 10G Cluster Switching System Service Unit (SFP+)

-- S9700:       0x000A7000~0x000A7fff(684032~688127)
                subnameET1D2VS08000(684032), --8-Port 10G Cluster Switching System Service Unit (SFP+)

-- S12700:      0x000AB000~0x000ABfff(700416~704511)
                subbnameET1D2VQ06000(700416),           --6-Port 40GE Cluster Switching System Service Unit (QSFP+) for 12700 V2R11
                subbnameET1D2VQ02000(700417),           --2-Port 40GE Cluster Switching System Service Unit (QSFP+) for 12700 and 9700   V2R11

-- S7900:       0x000AE000~0x000AEfff(712704~716799)



-- SSP & NSE:
                subbnameNSESX11E8GF(231151),      --SX11E8GF1020
                subbnameNSESX11P4UF(231152),      --SX11P4UF1020
                subbnameNSESX11L1XX(231153),       --SX11L1XX2020
                subbnameNSESX11EBGF(231154),      --SX11EBGF2020
                subbnameNSESX11EBGE(231155),      --SX11EBGE2020
                subbnameNSESX11P1XX(231156),      --SX11P1XX2020
                virentSSP5000SX1D00P1MZ70(697000),     --virentSSP5000SX1D00P1MZ70
                virentSSP5000SX1D00P2XX70(697001),     --virentSSP5000SX1D00P2XX70
                virentSSP5000SX1D0L5XXA70(697002),     --virentSSP5000SX1D0L5XXA70
                virentSSP5000SX1DP8XE8X70(697003),     --virentSSP5000SX1DP8XE8X70
                virentSSP5000SX1DP2ME8X70(697004),     --virentSSP5000SX1DP2ME8X70
                virentSSP5000SX1D00P8UF70(697005),     --virentSSP5000SX1D00P8UF70

-- atn
                subbnameANTUnkown(225280),          --
                subbnameAND1ML1(225465),        -- 16 Channels E1 Interface Board(75ohm)
                subbnameAND1ML1A(225466),       -- 16 Channels E1 Interface Board(120ohm)
                subbnameAND1CD1(225283),        -- 1 Channelized OC-3c/STM-1c Optical Interface Board
                subbnameANE7E8GF(225284),       -- 8 Channels Gigabit Ethernet Optical/Electric High-speed Interface Board(HIB,No supporting 1588v2)
                subbnameANE7E8GFA(225285),      -- 8 Channels Gigabit Ethernet Optical/Electric High-speed Interface Board A(HIB)
                subbnameAND1EF8F(225286),       -- 8 Channels Fast Ethernet Optical Interface Board
                subbnameAND1EF8T(225287),       -- 8 Channels Fast Ethernet Electric Interface Board
                subbnameAND1AUXQ(225288),       -- Assistant Channel And 4 Channels FE Electric Interface Board
                subbnameANE7A4CF(225289),       -- 4 Channels OC-3c/STM-1c ATM Optical Interface Board

--ATN910&950, ATN950B
--card
               subbnameATNAND1EG2(225453),        --2x GE service interface board
               subbnameATNAND1EG4F(225454),       --4x GE service interface board
               subbnameATNAND2ML1A(225455),       --16x E1 service interface board (75 ohms)
               subbnameATNAND2ML1B(225456),       --16x E1 service interface board (120 ohms)
               subbnameATNAND1MD1A(225457),       --32x E1 service interface board (75 ohms)
               subbnameATNAND1MD1B(225458),       --32x E1 service interface board (120 ohms)
               subbnameATNAND1SHD4(225460),       --4x G.SHDSL service interface board
               subbnameATNAND1SHD4I(225461),      --4x IMA mode of G.SHDSL service interface board
               subbnameATNAND1AVD8A(225462),      --8x ADSL2+/VDSL2 service interface board
               subbnameATNAND1EG4T(225463),       --4x GE service interface board electric
               subbnameATNAND1MO1C(225464),       --8x T1 service interface board electric(100 ohms)
               subbnameATNVIRTUAL(225459),        --Virtual card
               subbnameATNVIRTUAL1(225467),       --Virtual card(CXPI)
               subbnameATNVIRTUAL2(225490),       --Virtual card(910I),with 4GE(o),4GE/FE(o),4GE/FE(e)
               subbnameATNVIRTUAL3(225491),       --Virtual card(910I),with 16E1,4GE(o),4GE/FE(o),4GE/FE(e)
               subbnameATNVIRTUAL4(225492),       --Virtual card(910I),with 16E1,4GE(o),4GE/FE(o),4GE/FE(e),4FE
               subbnameATNVIRTUAL5(225500),       --Virtual card(910I),with 16E1,2GE(o)+4GE/FE(o),4GE/FE(e)
               subbnameATNVIRTUAL6(225516),       --Virtual card(910I),with 4GE(o),4GE/FE(o),4GE/FE(e),poe
               subbnameATNVIRTUAL7(225517),       --Virtual card(905),with 2Combo,2GE(o),2GE/FE(e)
               subbnameATNVIRTUAL8(225518),       --Virtual card(905),with 4GE(o)
               subbnameATNVIRTUAL9(225519),       --Virtual card(905),with 4GE(o),poe
               subbnameATNAND1EX1(225468),        --1x 10GE service interface board fiber
               subbnameATNAND1EM8F(225469),       --8x GE service interface board fiber
               subbnameATNAND1EM4F(225470),       --4x GE service interface board fiber
               subbnameATNAND1EM8T(225471),       --8x GE service interface board electric
               subbnameATNAND1EM4T(225472),       --4x GE service interface board electric
               subbnameATNAND3ML1A(225479),       --16x E1 service interface board (75 ohms)
               subbnameATNAND3ML1B(225480),       --16x E1 service interface board (120 ohms)
               subbnameATNAND2MD1A(225481),       --32x E1 service interface board (75 ohms)
               subbnameATNAND2MD1B(225482),       --32x E1 service interface board (120 ohms)
               subbnameATNAND2CQ1B(225497),       --4-port channelized OC-3c/STM-1c POS-SFP Flexible Interface Board
               subbnameAND2EG2(225504),           --2 GE service interface board
               subbnameAND2EF8F(225505),          --8 Channels Fast Ethernet Optical Interface Board
               subbnameAND2EF8T(225506),          --8 Channels Fast Ethernet Electric Interface Board
               subbnameAND1EM4C(225507),          --4 Channels GE/FE Combo Board
               subbnameATNAND2PQ10(225520),       --4 Channels OC-3/STM-1 POS Optical Interface Board
               subbnameATNVIRTUAL10(225521),      --Virtual card(905),with 4GE(e),2VDSL
               subbnameATNVIRTUAL11(225522),      --Virtual card(910B),with 2XGE(o),8GE/FE(o),8GE/FE(e),16E1
               subbnameATNVIRTUAL12(225523),      --Virtual card(910B),with 2XGE(o),16GE/FE(o),8GE/FE(e)
               subbnameATNVIRTUAL13(225540),      --Virtual card(910I),with 2Combo,2GE/FE(o),2GE/FE(e)
               subbnameATNVIRTUAL14(225541),      --Virtual card(910I),with 4Combo,4GE(o),4GE/FE(e)
               subbnameATNVIRTUAL15(225542),      --Virtual card(910I), with 4Combo,4GE(o),4GE/FE(e),16E1,
               subbnameATNVIRTUAL16(225548),      --Virtual card(905),with with 2GE/FE(e),2Combo,2GE(o),VDSL
               subbnameATNVIRTUAL17(225549),      --Virtual card(905),with 2Combo,2GE/FE(o),2GE/FE(e)
               subbnameAND2EM4T(225551),          --4 Channels GE/FE Electrical Interface Board
               subbnameAND2EM4F(225552),          --4 Channels GE/FE Optical Interface Board
               subbnameAND2EM8T(225553),          --8 Channels GE/FE Electrical Interface Board
               subbnameAND2EM8F(225554),          --8 Channels GE/FE Optical Interface Board
               subbnameAND2EX1S(225555),          --1 Channel 10GE Optical Interface Board
               subbnameAND2EX2S(225556),          --2 Channels 10GE Optical Interface Board
               subbnameAND2EM8M(225557),          --4 Channels GE/FE Optical +4 Channels GE/FE Electric Interface Board
               subbnameATNAND1EX8F(225558),       -- 1 Channel 10GE (SFP+),8 Channels GE/FE Optical Interface Board
               subbnameATNCX68MD8A(225559),       -- 8-Channel CWDM Multiplexing & Demultiplexing (1471/1491/1511/1531/1551/1571/1591/1611nm) Flexible Card.
               subbnameATNVIRTUAL18(225560),      --Virtual card(910B-D/E),with 24GE/FE(o)+4XGE(o)
               subbnameATNVIRTUAL19(225561),      --Virtual card(905-E),with 2GE/FE(o)+2GE/FE(e)+4E1
               subbnameATNVIRTUAL20(225562),      --Virtual card(905A-D),with 5GE/FE(e)
               subbnameANJ1EXL1(225563),          --1 Channel 40GE Optical Interface Board
               subbnameAND2EX8F(225565),          -- 1 Channel 10GE (SFP+),8 Channels GE/FE Optical Interface Board
               subbnameAND3MD10(225566),          --32 Channels E1 Interface Board
               subbnameANDD00EM4F00(225575),      --ATN950C, 4 Channels GE/FE Optical Interface Board
               subbnameANDD00EM4T00(225576),      --ATN950C, 4 Channels GE/FE Electrical Interface Board
               subbnameANDD00EM8F00(225577),      --ATN950C, 8 Channels GE/FE Optical Interface Board
               subbnameANDD00EM8T00(225578),      --ATN950C, 8 Channels GE/FE Electrical Interface Board
               subbnameANDD00EX1S00(225579),      --ATN950C, 1 Channel 10 GE Optical Interface board(SFP+)
               subbnameANKD00EX2S00(225580),      --ATN950C, 2 Channel 10 GE Optical Interface board(SFP+)
               subbnameANDD16E17500(225581),      --ATN950C, 16 Channels E1 Interface Board(75ohm)
               subbnameANDD16E11200(225582),      --ATN950C, 16 Channels E1 Interface Board(120ohm)
               subbnameANDD32E17500(225583),      --ATN950C, 32 Channels E1 Interface Board(75ohm)
               subbnameANDD32E11200(225584),      --ATN950C, 32 Channels E1 Interface Board(120ohm)
               subbnameLNDD01XE8F00(225585),      --ATN980B, 1 Channel 10GE Optical(SFP+)+8 Channels GE/FE Optical Interface Board
               subnameCARDATN910CA(225586),       --ATN910C-A virtual card
               subnameCARDATN910CB(225587),       --ATN910C-B virtual card
               subbnameANKD00EX4S00(225588),      --ATN980B, 4 Channels 10GE Optical Interface Board
               subbnameANKD00EM20F0(225589),     --ATN980B, 20 Channels GE Optical Interface Board
               subbnameANKD0EM20F00(225747),     --ATN980B, 20 Channels GE Optical Interface Board
               subbnameCARD1ATN910CD(225590),   --ATN910C-D virtual card,4*10GE(o), 8*10GE /GE/FE(o),8*GE/FE(e)
               subbnameCARD2ATN910CD(225591),   --ATN910C-D virtual card,16E1

               subbnameATNANJ1EV2(564531),                     --03057706, ATNANJ1EV2, 2 Port 50GBase QSFP28 High Speed Interface Card
               subbnameATNNEDD01MPAA00(225597),       --4-Channel FXS/FXO+2-Channel E&M+2-Channel RS232+2-Channel RS485 Board
               subbnameATNNEDD001SA800(225598),       --8-Channel V.35/X.21/V.24 Board
               subbnameATNNEDD01MP8A00(225599),       --4 Channels C37.94 Optical Interface and 4 Channels CoDir64K Electric Interface Board

--etn :  0x000ad000~0x000adfff(708608~712703)
--card
              subnameETNVIRTUAL1(708608),                    -- Virtual card(ETN500-A),with 2GE/FE(O)+2GE/FE(E)+2GE/FE(Combo)
              subnameETNVIRTUAL2(708609),                    -- Virtual card(ETN500-B),with 2GE/FE(O)+2GE/FE(E)+2GE/FE(Combo)
              subnameETNVIRTUAL3(708610),                    -- Virtual card(ETN500-C),with GE/FE(O)+2GE/FE(E)+4E1
              subnameLND1ME8F(708612),                       -- 8 Channels Fast Ethernet Optical Interface Board
              subnameLND1ME8T(708613),                       -- 8x GE service interface board electric
              subnameLND1XE1S(708614),                       --1 Channel 10GE Optical Interface Board
              subnameLND1XE8F(708615),                       -- 1 Channel 10GE (SFP+),8 Channels GE/FE Optical Interface Board
              subnameLND1DM1A(708616),                       --32x E1 service interface board (75 ohms)
              subnameLND1DM1B(708617),                       --32x E1 service interface board (120 ohms)
              subnameLND2DM1(708618),                        --32 Channels E1 Interface Board
              subnameLND1QC1(708619),                        --4 Channels Channelized OC-3c/STM-1c POS Optical Interface Board
              subnameLND1QP1(708620),                        --4 Channels OC-3/STM-1 POS Optical Interface Board
              subnameLND1ME4F(708621),                         --4 Channels GE/FE Optical Interface Board
              subnameLND1ME4T(708622),                         --4 Channels GE/FE Electrical Interface Board
              subnameLND1EX8F(708623),                       -- 1 Channel 10GE (SFP+),8 Channels GE/FE Optical Interface Board



-- NE0508E:    0x000AC000~0x000Acfff (704512 ~ 708607)
--card
               subbnameNE08EEX1S(704512),             --1 Channel 10 GE Optical Interface board (SFP+)
               subnameNE08EEX2S(704513),              --2 Channel 10 GE Optical Interface board (SFP+)
               subnameNE08EEM8M(704514),              --4 Channels GE/FE Optical Interface and 4 Channels GE/FE Electric Interface Board
               subnameNE08EEM8F(704515),              --8 Channels GE/FE Optical Interface Board
               subnameNE08EEM4F(704516),              --4 Channels GE/FE Optical Interface Board
               subnameNE08EEM4T(704517),              --4 Channels GE/FE Electric Interface Board
               subnameNE08EEM8T(704518),              --8 Channels GE/FE Electric Interface Board
               subnameNE08ECQ1B(704519),              --4 Channels Channelized OC-3c/STM-1c POS Optical Interface Board
               subnameNE08EPQ10(704520),              --4 Channels OC-3/STM-1 POS Optical Interface Board
               subnameNE08ED3ML1A(704521),            --16 Channels E1 Interface Board(75ohm)
               subnameNE08ED3ML1B(704522),            --16 Channels E1 Interface Board(120ohm)
               subnameNE05EVIRTUAL1(704523),          -- Virtual card(NE05E-SE),with 2XGE(o)+16GE/FE(o)+8GE/FE(e)
               subnameNE05EVIRTUAL2(704524),          -- Virtual card(NE05E-SF),with 2XGE(o)+8GE/FE(o)+8GE/FE(e)+16E1
               subnameNE05EVIRTUAL3(704525),          -- Virtual card(NE05E-SG),with 4Combo+4GE(O)+4GE/FE(E)
               subnameNE05EVIRTUAL4(704526),          -- Virtual card(NE05E-SH),with 4Combo+4GE(O)+4GE/FE(E)+16E1
               subnameNE05EVIRTUAL5(704527),          -- Virtual card(NE05E-SI),with 4GE(O)+4GE/FE(O)+4GE/FE(E)
               subnameNE05EVIRTUAL6(704528),          -- Virtual card(NE05E-SJ),with 2Combo+2GE/FE(o)+2GE/FE(e)
               subnameNE05EVIRTUAL7(704529),          -- Virtual card(NE05E-SK),with 2Combo+2GE/FE(o)+2GE/FE(e)
               subnameNE05EVIRTUAL8(704530),          -- Virtual card(NE05E-SL),with 2Combo+2GE(o)+2GE/FE(o)
               subnameNE05EVIRTUAL9(704531),          -- Virtual card(NE05E-SM),with 1Combo+1GE/FE(o)+2GE/FE(e),POE+
               subnameNE05EEG2(704532),               --  2 Channels GE Optical Interface Board
               subnameNE05EEG4(704533),               --4 Channels FE/GE Adaptive Optical Interface Board
               subnameNE05EEF8F(704534),              --8 Channels Fast Ethernet Optical Interface Board
               subnameNE05EEG4T(704535),              --4 Channels FE/GE Adaptive Electronic Interface Board
               subnameNE05EF8T(704536),               --8 Channels Fast Ethernet Electric Interface Board
               subnameNE05ED2ML1A(704537),            --16 Channels E1 Interface Board(75ohm)
               subnameNE05ED2ML1B(704538),            --16 Channels E1 Interface Board(120ohm)
               subnameNE05ED1MD1A(704539),            --32 Channels E1 Interface Board(75ohm)
               subnameNE05ED1MD1B(704540),            --32 Channels E1 Interface Board(120ohm)
               subnameNE05EAVD8A(704541),             --8 Channels ADSL2+ Interface Board,with Bonding Function, Annex A&Annex M Mode
               subnameNE05EAVD8B(704542),             --8 Channels VDSL2 Interface Board,with Bonding Function, Annex A&Annex M Mode
               subnameNE05ESHD4(704543),              --4 Channels G.SHDSL Interface Board
               subnameNE05EMO1C(704544),              --8 Channels T1 Interface Board
               subnameNE05EVIRTUAL10(704545),         --Virtual card(NE05E-S2),with 4GE/FE(o)+4GE/FE(e)+2GE(o)
               subnameNE08ENED1MPAA(704546),          --4-Channel FXS/FXO+2-Channel E&M+2-Channel RS232+2-Channel RS485 Board
               subnameNE08ENED1SA8(704547),           --8-Channel V.35/X.21/V.24 Board
               subnameNE08EPWRPIC(704548),            --the pic of TNF1APIU
               subnameNE08ENED1MP8A(704549),          --4-Channel C37.94,4-Channel CoDir64K
               subnameNEDD00EM4F00(704560),           --NE08E, 4 Channels GE/FE Optical Interface Board
               subnameNEDD00EM4T00(704561),           --NE08E, 4 Channels GE/FE Electrical Interface Board
               subnameNEDD00EM8F00(704562),           --NE08E, 8 Channels GE/FE Optical Interface Board
               subnameNEDD00EM8T00(704563),           --NE08E, 8 Channels GE/FE Electrical Interface Board
               subnameNEDD00EX1S00(704564),           --NE08E, 1 Channel 10 GE Optical Interface board(SFP+)
               subnameNEDD00EX2S00(704565),           --NE08E, 2 Channel 10 GE Optical Interface board(SFP+)
               subnameNEDD16E17500(704566),           --NE08E, 16 Channels E1 Interface Board(75ohm)
               subnameNEDD16E11200(704567),           --NE08E, 16 Channels E1 Interface Board(120ohm)
               subnameNEDD32E17500(704568),           --NE08E, 32 Channels E1 Interface Board(75ohm)
               subnameNEDD32E11200(704569),           --NE08E, 32 Channels E1 Interface Board(120ohm)
               subnameCARDNE05ESQ(704570),            --NE05E virtual card

-- PTN:        0x38000 ~ 0x38FFF   229376 ~ 233471
               subbnameTN91EG20(229376),         --20-Port 100/1000Base-X-SFP Flexible Card(Supporting 1588v2)
               subbnameTN91EX2(229377),          --2-Port 10GBase LAN/WAN-XFP Flexible Card(Supporting 1588v2)
               subbnameTN91ET20B(229378),        --20-Port 10/100/1000Base-RJ45 Flexible Card
               subbnameTN91EG8(229379),          --8-Port 100/1000Base-X-SFP Flexible Card(Supporting 1588v2)
               subbnameTN91CD1(229380),          --2-Port Channelized OC-3c/STM-1c POS-SFP Flexible Card
               subbnameTN91MT1(229381),          --24-Port Channelized E1/T1-DB100 Flexible Card

               subbnameTNR1EG8(229382),          --8 Ports FE/GE (Optical) Ethernet Processing Flexible Card (Supporting 1588V2)
               subbnameTNR1CD1(229383),          --2 Ports Channelized OC-3C/STM-1C SFP Flexible Card
               subbnameTNR1MT1(229384),          --24 Ports Channelized E1/T1-DB100 Flexible Card
               subbnameTNR1EX2(229385),          --2 Ports 10 Gigabit Ethernet Processing Flexible Card (Supporting 1588V2)
               subbnameTNR1EG20(229386),         --20 Ports FE/GE (Optical) Ethernet Processing Flexible Card (Supporting 1588V2)
               subbnameTNR1ET20B(229387),        --20 Ports FE/GE (Electric) Ethernet Processing Flexible Card

               --for V6R6 CH-PTN card packing
               subbnameTNRD00EFF800(229405),     --8 Ports FE (Optical) Ethernet Processing Flexible Card (Supporting 1588v2)
               subbnameTNRD000EX201(229406),     --2 Ports 10 Gigabit Ethernet Processing Flexible Card (Supporting 1588v2)
               subbnameTNRD000EX500(229408),     --5 Ports 10 Gigabit Ethernet Processing Flexible Card (Supporting 1588v2)
               subbnameTNRD00EXL100(229500),     --1 Ports 40 Gigabit Ethernet Processing Flexible Card (Supporting 1588v2)
               subbnameTNRD000CO101(229501),     --8 Ports Channelized OC-3C/STM-1C SFP Flexible Card

               --for V6R6 PTN6900 chinamobile JICAI
               subbnameTNRD000CO100(229600),     --8 Ports Channelized OC-3C/STM-1C SFP Flexible Card
               subbnameTNRD000SO100(229602),     --8 Ports OC-3/STM-1 CFP Flexible Card

               --for V6R7 PTN6900 card packing
               subbnameTNRD000EX600(229700),     --6 Ports 10 Gigabit Ethernet Processing Flexible Card (Supporting 1588v2)
               subbnameTNRD000EH101(229702),     --1 Port 100 Gigabit Ethernet Processing Flexible Card (Supporting 1588v2)
               subbnameTNRD00EX1200(229703),     --12 Ports 10 Gigabit Ethernet Processing Flexible Card (Supporting 1588v2)
               subbnameTNRD00EXL300(229704),    --3 Ports 40GBase-CFP Ethernet Processing Board (Supporting 1588v2)

               -- V8R5 PTN packaging
               subbnameTNRD00MPUK70(229450),     --for V8R5C01 TNRD00MPUK70(SBOM),Main Processing Unit K
               subbnamePTN990TPJD00EXL100(229451),        --TPJD00EXL100,1-Port 40GBase-CFP Physical Interface Card(PIC)
               subbnamePTN990TNDD00EX1S00(229452),        --TNDD00EX1S00,1 Channel 10 GE Optical Interface board(SFP+)
               subbnamePTN990TNDD00EX2S00(229453),        --TNDD00EX2S00,2 Channel 10 GE Optical Interface board(SFP+)
               subbnamePTN990TNDD00EM4T01(229454),        --TNDD00EM4T01,4 Channels GE/FE Electrical Interface Board
               subbnamePTN990TNDD00EM8T01(229455),        --TNDD00EM8T01,8 Channels GE/FE Electrical Interface Board
               subbnamePTN990TNDD00EM4F02(229456),        --TNDD00EM4F02,4 Channels GE/FE Optical Interface Board
               subbnamePTN990TNDD00EM8F02(229457),        --TNDD00EM8F02,8 Channels GE/FE Optical Interface Board
               subbnamePTN990TPJD000AUX00(229458),        --TPJD000AUX00,Auxiliary  Flexible Interface Card
               subbnamePTN990TNDD000SQ100(229459),        --TNDD000SQ100,4 Channels STM-1 Optical Interface Board
               subbnamePTN990TNDD00MD1A00(229460),        --TNDD00MD1A00,32 Channels E1 Interface Board(75ohm)
               subbnamePTN990TNDD00MD1B00(229461),        --TNDD00MD1B00,32 Channels E1 Interface Board(120ohm)
               subbnamePTN990TNDD00ML1A00(229462),        --TNDD00ML1A00,16 Channels E1 Interface Board(75ohm)
               subbnamePTN990TNDD00ML1B00(229463),        --TNDD00ML1B00,16 Channels E1 Interface Board(120ohm)
               subbnamePTN990J1EM16DP1(229464),        --J1EM16D-P1,16 Channel 1 GE Optical Interface board
               subbnamePTN990J1EM16DP2(229465),        --J1EM16D-P2,16 Channel 1 GE Optical Interface board
               subbnamePTN990TPJ1EF8F(229466),        --TPJ1EF8F,8 Channel 1 GE Optical Interface board
               subbnamePTN990TPJ1EX4S(229467),        --TPJ1EX4S,4 Channel 10 GE Optical Interface board(SFP+)

               subbnameTPKD000SQ100(229468),       --TPK1SQ1, 4 Channels STM-1 Optical Interface Board
               subbnameTPKD00EX2S00(229469),       --TPK1EX2S, 2 Channel 10 GE Optical Interface board(SFP+)
               subbnameTPKD00EX1S00(229470),       --TPK1EX1S, 1 Channel 10 GE Optical Interface board(SFP+)
               subbnameTPKD00EM8F00(229471),      --TPK1EM8F, 8 Channels GE/FE Optical Interface Board
               subbnameTPKD00EM8T00(229472),      --TPK1EM8T, 8 Channels GE/FE Electrical Interface Board
               subbnameTPKD00EXL100(229473),       --TPK1EXL1, 1-Port 40GBase-CFP Physical Interface Card(PIC)
               subbnameTPKD00MD1A00(229474),      --TPK1MD1A, 32 Channels E1 Interface Board(75ohm)
               subbnameTPKD00MD1B00(229475),      --TPK1MD1B, 32 Channels E1 Interface Board(120ohm)
               subbnameTPKD00ML1A00(229476),       --TPK1ML1A, 16 Channels E1 Interface Board(75ohm)
               subbnameTPKD00ML1B00(229477),       --TPK1ML1B, 16 Channels E1 Interface Board(120ohm)
               subbnameTPK2EY2(229551),         --2 Channel 25/10/1 GE Optical Interface Board
               subbnameTND1EY1(229552),         --2 Channel 25/1 Channel 10/1 GE Optical Interface Board
               subbnameTPK2FV1(229553),         --1 Channel 50 GE  FlexE Service Optical Interface Board
               subbnameTND2FV1(229554),         --1 Channel 50 GE  FlexE Service Optical Interface Board
               subbnamePTN980TND1EX1(229650),         --1 Channel 10 GE Optical Interface board
               subbnamePTN980TND1EM4F(229651),        --4 Channels GE/FE Optical Interface Board
               subbnamePTN980TND1EM4T(229652),        --4 Channels GE/FE Electrical Interface Board
               subbnamePTN980TND1EM8T(229653),        --8 Channels GE/FE Electrical Interface Board
               subbnamePTN980TND1EM8F(229654),        --8 Channels GE/FE Optical Interface Board
               subbnameTPN1EY4(229545),          --Finished Board Unit,OptiX PTN 980,TPN1EY4,4 Channel 25/10/1 GE Optical Interface Board
               subbnameTPN1EY2(229546),          --Finished Board Unit,OptiX PTN 980,TPN1EY2,2 Channel 25/10/1 GE Optical Interface Board
               subbnameTPN1EM8F(229570),         --8 Channels GE/FE Optical Interface Board
               subbnameTPN1EX1S(229571),         --1 Channel 10GE Optical Interface Board(SFP+)
               subbnameTPN1MD1(229572),          --32 Channels E1 Interface Board
               subbnameTPN1FH1(229655),          --1 Channel 100 GE FlexE Optical Interface Board
               subbnameTPN1FV2(229656),          --2 Channels 50 GE FlexE Optical Interface Board
               subbnameTPN1FV1(229657),          --1 Channel 50 GE FlexE Optical Interface Board
               subbnameTPN2MD1(229286),          --32 Channels E1 Interface Board
               subbnameTPN2EX10P(229285),        --10 Channels 10 GE Optical Interface Board(physical board, with 8 port enabled by default) (SFP+)
               subbnameTPT1FV2P(229287),         --2 Channels 50 GE FlexE Optical Interface Board(physical board, with 1 port enabled by default)


--PTN990 V1R9C00

               subbnamePTN990TPJ1EH1(229510),           --TPJ1EH1,1 Channel 100 GE Optical Interface Board
               subbnamePTN990TPL1EM4F(229511),        --Finished Board Unit,Optix PTN 930,TPL1EM4F0,4 Channels GE/FE Electrical Interface Board
               subbnamePTN990TPL1EM4T(229512),        --Finished Board Unit,Optix PTN 930,TPL1EM4T0,4 Channels GE/FE Electrical Interface Board
               subbnamePTN990TPL1ML1A(229513),        --Finished Board Unit,OptiX PTN 930,TPL1ML1A,16 Channels E1 Interface Board(75ohm)
               subbnamePTN990TPJ1EV2(229506),                      --03057714,TPJ1EV2 , 2 Port 50G Base-Qsfp28 High-Speed Interface Card



-- AR:          0x000A3000~0x000A3fff(667648~671743)
                subbnameAR01DD016A(667648),       --16 Channel DSP module
                subbnameAR01DD032A(667649),       --32 Channel DSP module
                subbnameAR01DD064A(667650),       --64 Channel DSP module
                subbnameAR01DD128A(667651),       --128 Channel DSP module
                subbnameAR01WiFi(667652),         --WiFi module
                subbnameAR013G(667653),           --3G module
                subbnameAR01FAN(667654),            --FAN module for AR1220
-- NE20E-X6:
               subbnameCR2D00P1XX11(675840),     --1-Port OC-192c/STM-64c POS-XFP Flexible Card(HIC20)
               subbnameCR2D00L1XX10(675841),     --1-Port 10GBase LAN/WAN-XFP Flexible Card(HIC20)
               subbnameCR2D00EBGF10(675842),     --12-Port 100/1000Base-X-SFP Flexible Card(HIC20)
               subbnameCR2D00EBGE10(675843),     --12-Port 10/100/1000Base-RJ45 Flexible Card(HIC20)

               subbnameCR2D00EKGF10(675844) ,    --40-Port 100/1000Base-SFP Flexible Card(HIC20,Occupy two sub-slots)
               subbnameCR2D00EKGE10(675845) ,    --40-Port 10/100/1000Base-RJ45 Flexible Card(HIC20,Occupy two sub-slots)
               subbnameCR2D00L4XX10(675846),     --4-Port 10GBase WAN/LAN-XFP Flexible Card(HIC20,Occupy two sub-slots)
               subbnameCR2D00EMFE10(675847) ,    --48-Port 10/100Base Delander Flexible Card(HIC20)
               subbnameCR2D00P1XX10(675848) ,    --1-Port OC-192c/STM-64c POS-XFP Flexible Interface Card(Occupy two FIC slots)
               subbnameCR2D00E8GF10(675849) ,      --8 100/1000Base-X-SFP A(P10-A,1588v2)
               subbnameCR2D00A4CF10(675850) ,    --4-Port OC-3c/STM-1c ATM-SFP Flexible Interface Card(FIC)
               subbnameCR2D00P1UF10(675851) ,    --1-Port OC-48c/STM-16c POS-SFP Flexible Interface Card(FIC)
               subbnameCR2D00P2UF10(675852) ,    --2-Port OC-48c/STM-16c POS-SFP Flexible Interface Card(FIC)
               subbnameCR2D00P4HF10(675853) ,    --4-Port OC-12c/STM-4c POS-SFP Flexible Interface Card(FIC)
               subbnameCR2D00P4CF10(675854),     --4-Port OC-3c/STM-1c POS-SFP Flexible Interface Card(FIC)
               subbnameCR2D00P8CF10(675855) ,    --8-Port OC-3c/STM-1c POS-SFP Flexible Interface Card(FIC)
               subbnameCR2D00C2CF10(675856) ,    --2-Port Channelized OC-3c/STM-1c POS-SFP Flexible Interface Card(FIC)
               subbnameCR2D00CFE110(675857),     --24-Port Channelized E1/T1-DB100 Flexible Interface Card(FIC)
               subbnameCR2DL2XEEG10(675858),      --2-Port 10GBase LAN/WAN-XFP+20-Port 100/1000Base-X-SFP Flexible Card(HIC20,Occupy two sub-slots)
               -- FOr cx600 V8R5  NE20E
               subbnameCR2D00L2XF11(675870),       --2-Port 10GBase LAN/WAN-SFP+  Physical Interface Card
               subbnameCR2D00E8GF11(675871),       --8-Port 100/1000Base-X-SFP Physical Interface Card
               subbnameCR2D00E8GE11(675872),       --8-Port 10/100/1000Base-RJ45 Physical Interface Card
               subbnameCR2DL1XE8G10(675873),       -- CX68L1XE8GF, 1-Port 10GBase LAN/WAN-SFP+  8-Port 100/1000Base-X-SFP Physical Interface Card
               subbnameCR2D00C4CF11(675874),       --CX68C4CF    4-Port Channelized STM-1c POS-SFP  Physical Interface Card
               subbnameCR2D000IE110(675875),       --CX68MIE1    32-Port E1 Physical Interface Card(75ohm)
               subbnameCR2D000IE111(675876),       --CX68MIE1B   32-Port E1 Physical Interface Card(120ohm)
               subbnameCR2D000DE110(675877),       --CX68MDE1A   16-Port E1 Physical Interface Card(75ohm)
               subbnameCR2D000DE111(675878),       --CX68MDE1B   16-Port E1 Physical Interface Card(120ohm)
               subbnameCR2D00L4XF10(675879),       -- CX68L4XF, 4-Port 10GBase-X-SFP+High-speed Interface Card
               subbnameCR2D00P4CF11(675880),       -- CX67P4CFA, 4-Port OC-3c/STM-1c POS-SFP Flexible Interface Car

               subbnameCR2D00EAGF10(675882),        -- CX68EAGFD, 10-Port 100/1000Base-X-SFP Physical Interface Card
               subbnameCR2DL1XE8G11(675883),        -- CX68L1XE8GFB, 1-Port 10GBase LAN/WAN-SFP+ + 8-Port 100/1000Base-X-SFP Physical Interface Card
               subbnameCR2DP4C2HF11(675884),        -- CX68P4CFC, 4-Port OC-3c/STM-1c (or 2-Port OC12c/STM-4c)  POS-SFP  Physical Interface Card
               subbnameCR2DP2C1HF11(675885),        -- CX68P2CFC, 2-Port OC-3c/STM-1c (or 1-Port OC12c/STM-4C) POS-SFP  Physical Interface Card
               subbnameCR2D0L2XFH10(675886),        -- CX68L2XFC, 2-Port 10GBase LAN/WAN-SFP+ Physical Interface Card H
               subbnameCR2D0EAGFH10(675887),        -- CX68EAGFD, 10-Port 100/1000Base-X-SFP Physical Interface Card H
               subbnameCR2D00E8GE12(675888),        -- CX68E8GED, 8-Port 100/1000Base-RJ45 Physical Interface Card
               subbnameCR2D00E1MF10(675889),        -- CX68E1MC,  1-Port 40GBase-CFP Physical Interface Card
               subbnameCR2D00L4XF11(675890),        -- CX68L4XFD, 4-Port 10GBase LAN/WAN-SFP+ Physical Interface Card
               subbnameCR2D00L2XF12(675891),        -- CX68L2XFC, 2-Port 10GBase LAN/WAN-SFP+ Physical Interface Card
               subbnameCR5DP2C1HF70(675895),        -- CX68P2CFC, 2-Port OC-3c/STM-1c (or 1-Port OC12c/STM-4C) POS-SFP  Physical Interface Card(PIC)
               subbnameCR2DP4C2HF1120(675894),      -- CX68P2HFC, 4-Port OC-3c/STM-1c (or 2-Port OC12c/STM-4c)  POS-SFP  Physical Interface Card
               subbnameCR2DP2C1HF1120(675893),      -- CX68P1HFC, 2-Port OC-3c/STM-1c (or 1-Port OC12c/STM-4C) POS-SFP  Physical Interface Card
               subbnameCR5DP2C1HF7020(675892),      -- CX68P2CFC, 2-Port OC-3c/STM-1c (or 1-Port OC12c/STM-4C) POS-SFP  Physical Interface Card(PIC)
-- CloudEngine: 0x000A8000~0x000A8fff(688128~692223)
               subbnameDE51DFCMA(688128),        -- CloudEngine TOR CE6800 CE5800 FAN Control Card
               subbnameDE51DCTLA(688129),        -- CloudEngine TOR CE6800 CE5800 Extend Interface Card
               subbnamePAC150WA(688130),         -- CloudEngine TOR CE6800 CE5800 150W AC Power Module
               subbnamePAC350WA(688131),         -- CloudEngine TOR CE6800 CE5800 350W AC Power Module,Front to Back
               subbnamePAC350WAB(688132),        -- CloudEngine TOR CE6800 CE5800 350W AC Power Module,Back to Front
               subbnameFAN40SA(688133),          -- CloudEngine TOR CE6800 CE5800 Fan box,Front to Back
               subbnameFAN40SAB(688134),         -- CloudEngine TOR CE6800 CE5800 Fan box,Back to Front
               subbnameFAN40EA(688135),          -- CloudEngine TOR CE6800 CE5800 Extend Fan box,Front to Back
               subbnameFAN40EAB(688136),         -- CloudEngine TOR CE6800 CE5800 Extend Fan box,Back to Front
               subbnameCED24S2CQ(688137),        -- Manufactured Board,CloudEngine 8800,CE88-D24S2CQ,CE8860:24-Port-10G(SFP+),2-Port-100G(QSFP28) Interface Card,1*1
               subbnameCED24T2CQ(688138),        -- Manufactured Board,CloudEngine 8800,CE88-D24T2CQ,CE8860:24-Port 10GBASE-T(RJ45),2-Port-100G(QSFP28) Interface Card,1*1
               subbnameCED16Q(688139),           -- Manufactured Board,CloudEngine 8800,CE88-D16Q,CE8860:16-Port-40G Interface Card(QSFP+),1*1
               subbnameCED8CQ(688140),           -- Manufactured Board,CloudEngine 8800,CE88-D8CQ,CE8860:8-Port-100G Interface Card(QSFP28),1*1
               subbnameCED24S2CQU(688141),       -- Manufactured Board,CloudEngine 8800,CE88-D24S2CQ-U,CE8860:24-Port-25GE/32G FC(SFP28),2-Port-100GE(QSFP28) Interface Card,1*1
               subbnameCED24S2CQ1(688142),       -- Manufactured Board,CloudEngine 8800,CE88-D24S2CQ1,CE88:24-port 25GE SFP28 and 2-port 100GE QSFP28 interface card (supporting MACsec),1*1
               subbnameCED32CQ(688143),          -- Manufactured Board,CloudEngine 9800,CE98-D32CQ,CE9860X:32 Port 100GE QSFP28 Interface Card,1*1
               subbnameCED8DQ(688144),           -- Manufactured Board,CloudEngine 9800,CE98-D8DQ,CE98:8 Port 400GE QSFPDD Interface Card
               subbnameCE98D8DQ(688145),         -- Manufactured Board,CE98D8DQ
               subbnameCE98D32CQA(688146),
               subbnamePAC1K2S12PF(688147),
               subbnamePDC1K2S12PB(688148),
               subbnamePAC600S12P(688149),
               subbnameCE88D8YS4DQH(688150),         -- CE V3R23C10
               subbnameCE88D10CQH(688151),
               subbnameCE88D16CQH(688152),
               subbnameCE88D24YS2CQH(688153),
               subbnameCE88D24T2CQH(688154),
               subbnamePAC2KS12PB(688155),
               subbnamePAC1K8S12PF(688156),
               subbnamePHD2KS12PB(688157),
               subbnamePDC2K2S12PB(688158),
               subbnamePDC2K2S12PF(688159),
               subbnameCE88SAND16CQH(688160),
               subbnameCE88SAND26FH(688161),
			   subbnameCE98D32CQF(688164),
			   subbnameCE98D8DQF(688165),
			   subbnamePDC400S12CF(688166),
			   subbnameXH90D32CQF(688167),
               subbnameCE88SAND12FH(688168),
			  
--Adapter Mount Card for iODN products: range: 0x000B0000~0x000BFFFF  720,896~786,431
                subbnameAF11AMCX1(753921),                --AF11AMCX1
                subbnameAF11AMCB1(753922),                --AF11AMCB1
                subbnameAF11AMCC1(753923),                --AF11AMCC1
                subbnameAF11AMCD1(753924),                --AF11AMCD1
                subbnameAF11AMCX2(753925),                --AF11AMCX2
                subbnameAF11AMCB2(753926),                --AF11AMCB2
                subbnameAF11AMCC2(753927),                --AF11AMCC2
                subbnameAF11AMCD2(753928),                --AF11AMCD2


--Security Product's TC-MIB value scope :       16711680 ~ 16777215  or Hex format:0x00ff0000 ~ 0x00ffffff  (Both 16711680 and 16777215 are included)

--USG2000/Eudemon200E
                subbnameE180(16719885),             -- Wireless Data sub Card,E180,HSUPA/HSDPA/UMTS/EDGE/GPRS/GSM USB STICK,White,HUAWEI Standard
                subbnameET128(16719886),                -- Wireless Data sub Card,ET128,HSDPA/TD-SCDMA/EDGE/GPRS/GSM USB STICK,HUAWEI Standard Version
                subbnameEC169(16719887),                -- Wireless Data sub Card,EC169,CDMA2000 EV-DO Rev.A Rotatable USB Stick,White,Chinese Universal,RoHS



--Security Product's TC-MIB value scope :       16711680 ~ 16777215  or Hex format:0x00ff0000 ~ 0x00ffffff  (Both 16711680 and 16777215 are included)
--SVN Serie's TC-MIB vlaue scope:                   16740352 ~ 16744447  or Hex format:0x00ff7000~0x00ff7fff    (Both 16740352 and 16744447 are included)
--SVN
                subbnameSVN3000CN1510(16740352),          -- High-rate encrypted board (CN1510)  SVN3000
        subbnameSVN5500CN1620(16740353),          -- SVN5500,SE41HSVA,High Speed SSL VPN Card,with HS General Security Platform Software,1*1

--Security Product's TC-MIB value scope :       16711680 ~ 16777215  or Hex format:0x00ff0000 ~ 0x00ffffff  (Both 16711680 and 16777215 are included)
--SIG9800 Serie's TC-MIB vlaue scope:                   16732160 ~ 16736255  or Hex format:0x00ff5000 ~ 0x00ff5fff  (Both 16732160 and 16736255 are included)
--SIG9800
                subbnameSIG9800SPCA(16732160),                 --SPUA sub card
                subbnameSIG9800BypassCard(16732161),           --Bypass sub card
        subbnameSUP34SFPCard(16732162),                --SUP,SUP34SFP,4-port GE Optical Interface Board(SFP),1*2
        subbnameSIG9800IG2D00E5XX00(16732163),         --SIG9800-X,IG21L5XXA0,5-Port 10GBase LAN/WAN-XFP Flexible Card A(P100-A,Supporting 1588v2,Occupy two sub-slots)
        subbnameSIG9800IG2D00P2XS00(16732164),         --SIG9800-X,IG21P2XXA0,2-Port OC-192c/STM-64c POS-XFP Flexible Card(P100,Occupy one sub-slot)
        subbnameSIG9800IG2D00P1MS00(16732165),         --SIG9800-X,IG21P1MZ0,1-Port OC-768c/STM-256c POS-2KM-LC Flexible Card(P100,Occupy two sub-slots)
        subbnameSIG9800IG2D00E4XF00(16732166),         --SIG9800-X,IG21E4XFA0,4-Port 10GBase LAN-SFP+ Flexible Card(P100,Occupy one sub-slots)
        subbnameSIG9800IG2D00EFGF01(16732167),         --SIG9800-X,IG21EFGFA0,24-Port 100/1000Base-X-SFP Flexible Card(P100,Occupy two sub-slots)
        subbnameSIG9800IG2D00EFGF02(16732168),         --SIG9800-X,IG21EFGFB1,24-Port 100/1000Base-X-SFP Flexible Card A(P101-A)
        subbnameSIG9800IG2D00E5XF00(16732169),         --SIG9800-X,IG21L5XFB1,5-Port 10GBase LAN/WAN-SFP+ Flexible Card A(P101-A)
        subbnameSIG9800IG2D00E1MS00(16732170),         --SIG9800-X,IG21E1MCB1,1-Port 40GBase LAN-CFP Flexible Card A(P101-A)
        subbnameSIG9800SUP5SPCA(16732171),             --SUP,SUP5SPCA,Service Processing Card,1*1
        subbnameSIG9800IG21L6XF0(16732172),            --SIG9800-X,IG21L6XF0,6-Port 10GBase LAN/WAN-SFP+ Flexible Card (P120)
        subbnameSIG9800IG21LBXF1(16732173),            --SIG9800-X,IG21LBXF1,12-Port 10GBase LAN/WAN-SFP+ Flexible Card (P240)
        subbnameSIG9800IG21E1NCB1(16732174),           --SIG9800-X,IG21E1NCB1,1-Port 100GBase-CFP Flexible Card (P240)

--Security Product's TC-MIB value scope :       16711680 ~ 16777215  or Hex format:0x00ff0000 ~ 0x00ffffff  (Both 16711680 and 16777215 are included)
--Eudemon8000E/USG9000 Serie's TC-MIB vlaue scope:  16748544 ~ 16752639  or Hex format:0x00ff9000 ~ 0x00ff9fff  (Both 16748544 and 16752639 are included)
--Eudemon8000E/USG9000 Board/Card :
                subbnameEudemon8000ECR52E1XXT0(16748544), --CR52E1XX0,1*10GBase LAN-XFP Optical Interface LPU A
                subbnameEudemon8000ECR52W1XXT0(16748545), --CR52W1XX0,1*10GBase WAN-XFP Optical Interface LPU A
                subbnameEudemon8000ECR52P1XXT0(16748546), --CR52P1XX0,1*OC-192c/STM-64c POS-XFP Optical Interface LPU A
                subbnameEudemon8000ECR52R1XF(16748547),   --CR52R1XX0,1*OC-192c/STM-64c RPR-XFP Optical Interface LPU A
                subbnameEudemon8000ECR52E5GF(16748548),   --CR52E5GF,5-port GbE SFP Optical Interface LPU G
                subbnameEudemon8000ECR52C8E10(16748549),  --CR52C8E10,8-Port Channelized E1-RJ45 Flexible Service Interface Card
                subbnameEudemon8000ECR52C8T10(16748550),  --CR52C8T10,8-Port Channelized T1-RJ45 Flexible Service Interface Card
                subbnameEudemon8000ECR52C1CF1(16748551),  --CR52C1CF1,1 port Channelized OC-3/STM-1 Flexible Service Interface Card
                subbnameEudemon8000ECR52L1XX0(16748552),  --1-port 10GBase WAN/LAN XFP Flexible Interface Daughter Card
                subbnameEudemon8000ECR52EBGF0(16748553),  --12-port 100/1000Base-X SFP Flexible Interface Daughter Card
                subbnameEudemon8000ECR52EBGE0(16748554),  --12-port 10/100/1000Base-TX RJ45 Flexible Interface Daughter Card
                subbnameEudemon8000ECR52P1XXBZ0(16748555),--1 port OC-192c/STM-64c POS-XFP Flexible Card
        subbnameEudemon8000ESU91L4XX00(16748556),      --SU91L4XX00 4 Port 10G Base WAN/LAN-XFP
      subbnameEudemon8000ESU91L4XX01(16748557),    --SU91L4XX01 4 Port 10G Base LAN/LAN-XFP
      subbnameEudemon8000ESU91SPCB02(16748558),    --Eudemon8000E-X,SU91SPCB02,20G Firewall Performance Expansion Card(oversea),with HS General Security Platform Software
      subbnameEudemon8000ESU91SPCC01(16748559),    --Eudemon8000E-X,SU91SPCC01,40G Firewall Processing Card,with HS General Security Platform Software
      subbnameEudemon8000ESU91SPCB01(16748560),    --Eudemon8000E-X,SU91SPCB01,80G Firewall Processing card,with HS General Security Platform Software
	  subbnameSPCA-HM(16728078),    --Firewall Service Processing Card A (0x00ff400e)
	  subbnameSPCA-20-O-HM(16728079),    --20 Expansion Card (oversea) (0x00ff400f)
	  subbnameFW-20X1G-RJ45(16728080),    --20-Port 100/1000Base-RJ45 Flexible Card (0x00ff4010)
	  subbnameFW-3X40G-QSFP(16728081),    --3-Port 40GBase-QSFP+ Flexible Card (P240-A)(0x00ff4011)
	  subbnameSPCB-NAT-E8KE(16728068),    --X8&X16 NAT Service Processing Card B(0x00ff4004)


-- NIP6800
	  subbnameNIP-SAC-A(16728082),    --NIP6800 Service Processing Acceleration card-A (P240-A)(0x00ff4012)
	  subbnameNIP-12X10G-SFP (16728083),    --NIP6800 12-Port 10G Base LAN/WAN-SFP+ Flexible Card A((1/2wide,Occupy one sub-slots) (P240-A)(0x00ff4013)
	  subbnameNIP-6X10G-SFP (16728084),    --NIP6800 6-Port 10G Base LAN/WAN-SFP+ Flexible Card A(1/2wide,Occupy one sub-slots) (P240-A)(0x00ff4014)
	  subbnameNIP-3X40GE-QSFP(16728085),    --NIP6800 3-Port 40GBase-QSFP+ Flexible Card(0x00ff4015)
	  subbnameNIP-1X100G-CFP(16728086),    --NIP6800 1-Port 100GBase-CFP Flexible Card A(0x00ff4016)
	  subbnameNIP-24XGE-SFP (16728087),    --NIP6800 24-Port 100/1000Base-X-SFP Flexible Card(1/2wide,Occupy one sub-slots)(0x00ff4017)
	  subbnameNIP-IPS-B (16728088),    --NIP6800 IPS Service Processing Card(0x00ff4018)
	  subnameNIP-IPS-E-ASP(16728114),	            --Finished Board Unit,NIP6800,NIP-IPS-E-A,NIP6800 Enhanced IPS Service Processing Card A
	  subnameNIP-IPS-E-BSP(16728115),	            --Finished Board Unit,NIP6800,NIP-IPS-E-B,NIP6800 Enhanced IPS Service Processing Card B
	  subnameNIP-2X10G-SFP(16728123),	            --Finished Board Unit,NIP6800,NIP-2X10G-SFP+,2-Port 10G Base LAN/WAN-SFP+ Flexible Card A
	  subnameNIP-SAC-BSP(16728124),	            	--Finished Board Unit,NIP6800,NIP-SAC-B,NIP6800 Enhanced Service Processing Acceleration Card B


-- AntiDDoS8000 :
		subnameADS-SPC-60-01SP(16728108),	        	--Finished Board Unit,AntiDDoS8000,ADS-SPC-60-01,Enhanced DDoS Protection Service Card(with 1 CPU)
		subnameADS-SPC-60-00SP(16728109),	        	--Finished Board Unit,AntiDDoS8000,ADS-SPC-60-00,DDoS Protection Service Card IV(with 1 CPU)
		subnameADS-SPC-120-00SP(16728110),	        --Finished Board Unit,AntiDDoS8000,ADS-SPC-120-00,DDoS Protection Service Card V(with 2 CPU)
		subnameADS-SPC-120-01SP(16728111),	        --Finished Board Unit,AntiDDoS8000,ADS-SPC-120-01,Enhanced DDoS Protection Service Card(with 2 CPUs)
		sunnameADS-SPC-IV(16728121),	                --Finished Board Unit,AntiDDoS8000,ADS-SPC-IV,DDoS Protection Service Card IV
		subnameADS-SPC-V(16728122),	            		--Finished Board Unit,AntiDDoS8000,ADS-SPC-V,DDoS Protection Service Card V
		subnameADS-SPC-20-00SP(16748598),	        	--Finished Board Unit,AntiDDoS8000,ADS-SPC-20-00,DDoS Protection Service Card with 20G Performance
		subnameADS-SPC-40-00SP(16748599),	        	--Finished Board Unit,AntiDDoS8000,ADS-SPC-40-00,DDoS Protection Service Card with 40G Performance
		subnameADS-SPC-80-00SP(16748600),	            --Finished Board Unit,AntiDDoS8000,ADS-SPC-80-00,DDoS Protection Service Card with 80G Performance
		subnameADS-SPC-40-01SP(16748601),	        	--Finished Board Unit,AntiDDoS8000,ADS-SPC-40-01,DDoS Protection Service Card(with 1 CPU)
		subnameADS-SPC-80-01SP(16748602),	            --Finished Board Unit,AntiDDoS8000,ADS-SPC-80-01,DDoS Protection Service Card(with 2 CPUs)

-- Eudemon :
		subnameSPCD-D-E8KESP(16728117),	            --Finished Board Unit,Eudemon,SPCD-D-E8KE,Firewall Processing card D
		subnameSPCC-S-E8KESP(16728118),	            --Finished Board Unit,Eudemon,SPCC-S-E8KE,Firewall Processing card C

-- Eudemon8000E-X :
		subnameSPCB-APPSEC-E8KESP(16728116),	        --Finished Board Unit,Eudemon8000E-X,SPCB-APPSEC-E8KE,Enhanced Application Security Service Processing Card B
		subnameE8KE-X-1X100G-QSFP28(16728125),	    --Finished Board Unit,Eudemon8000E-X,E8KE-X-1X100G-QSFP28,1-Port 100GBase-QSFP28 Daughter Card
		subnameE8KE-X-6X10G-SFP-SP(16748608),	    	--Finished Board Unit,Eudemon8000E-X,E8KE-X-6X10G-SFP+,6-Port 10G Base LAN/WAN-SFP+ Flexible Card A
		subnameE8KE-X-1X100G-CFPSP(16748609),	    	--Finished Board Unit,Eudemon8000E-X,E8KE-X-1X100G-CFP,1-Port 100GBase-CFP Flexible Card A
		subnameE8KE-X-12X10G-SFP(16748610),	        --Finished Board Unit,Eudemon8000E-X,E8KE-X-12X10G-SFP+,12-Port 10G Base LAN/WAN-SFP+ Flexible Card
		subnameSPC-APPSEC-E8KESP(16748611),	        --Finished Board Unit,Eudemon8000E-X,SPC-APPSEC-E8KE,Application Security Service Processing Card

-- Eudemon8000E-X8 :
		subnameE8KE-X-2X10G-SFP-SP(16728120),	        --Finished Board Unit,Eudemon8000E-X8,E8KE-X-2X10G-SFP+,2-Port 10G Base LAN/WAN-SFP+ Flexible Card A

-- SeMG9811 :
		subnameSEMG-5X10GE-SFP-SP(16728103),	        --Finished Board Unit,SeMG9811,SEMG-5X10GE-SFP+,5-Port 10GBase LAN/WAN-SFP+ Flexible Card A(P101,1/2wide,Occupy two sub-slots)
		subnameSEMG-24XGE-SFPSP(16728104),	        --Finished Board Unit,SeMG9811,SEMG-24XGE-SFP,24-Port 100/1000Base-X-SFP Flexible Card(P101,1/2wide,Occupy two sub-slots)
		subnameSEMG-SPC-S-40SP(16728105),	        	--Finished Board Unit,SeMG9811,SEMG-SPC-S-40,40G Protectioin X3 Service Processing Card
		subnameSEMG-SPC-D-80SP(16728106),	       		--Finished Board Unit,SeMG9811,SEMG-SPC-D-80,80G Protection X8&X16 Service Processing Card
		subnameSEMG-5X10GE-BUN(16728107),	        	--Function Module,SeMG9811,SEMG-5X10GE-BUN,5-Port 10GBase LAN/WAN-SFP+ Flexible Card Assemblies(include Flexible Card,5*SFP+ 10km Optical Transceiver,10*LC 10m SM)

-- USG9500 :
		subnameFWCD00L1XX01(16728094), 				--Finished Board Unit,USG9500,FWC2L1XX02,1-Port 10GBase WAN/LAN XFP Flexible Interface Daughter Card
		subnameFWCD00EBGF01(16728095),				--Finished Board Unit,USG9500,FWC2EBGF02,12-Port 100/1000Base-X SFP Flexible Interface Daughter Card
		subnameFWCD00L2XX01(16728096),	            --Finished Board Unit,USG9500,SU91L2XX04,2-Port 10GBase LAN/WAN-XFP Flexible Card(P40)
		subnameFWCD00EFGF01(16728097),	            --Finished Board Unit,USG9500,SU91EEGF05,20-Port 100/1000Base-X-SFP Flexible Card(P40)
		subnameE8KE-X-101-1X40GE-CFP(16728098),	    --Finished Board Unit,USG9500,SU91E1MCB5,1-Port 40GBase LAN CFP Flexible Card(P101,1/2wide,Occupy two sub-slots)
		subnameE8KE-X-101-5X10GE-SFP(16728099),	    --Finished Board Unit,USG9500,SU91L5XFB5,5-Port 10GBase LAN/WAN-SFP+ Flexible Card A(P101,1/2wide,Occupy two sub-slots)
		subnameE8KE-X-101-24XGE-SFP(16728100),	    --Finished Board Unit,USG9500,SU91EFGFB5,24-Port 100/1000Base-X-SFP Flexible Card(P101,1/2wide,Occupy two sub-slots)
		subnameSPC-20-O-E8KE(16728101),	            --Finished Board Unit,USG9500,SU91SPCB06,20G Firewall Performance Expansion Card(oversea)
		subnameSPC-IPS-20(16728102),	                --Finished Board Unit,USG9500,SU91IPSC02,IPS Service Processing Card
		subnameSPCA-APPSEC-FWSP(16728112),	        --Finished Board Unit,USG9500,SPCA-APPSEC-FW,Enhanced Application Security Service Processing Card A
		subnameSPCB-APPSEC-FWSP(16728113),	        --Finished Board Unit,USG9500,SPCB-APPSEC-FW,Enhanced Application Security Service Processing Card B
		subnameFW-2X10G-SFP(16728119),	                --Finished Board Unit,USG9500,FW-2X10G-SFP+,2-Port 10G Base LAN/WAN-SFP+ Flexible Card A
		subnameFW-1X100G-QSFP28(16728126),	        --Finished Board Unit,USG9500,FW-1X100G-QSFP28,1*100GE QSFP28 Daughter Card
		subnameFW-6X10G-SFP-SP(16748594),	        	--Finished Board Unit,USG9500,FW-6X10G-SFP+,6*10GE SFP+ Daughter Card
		subnameFW-1X100G-CFPSP(16748595),	        	--Finished Board Unit,USG9500,FW-1X100G-CFP,1*100GE CFP Daughter Card
		subnameFW-12X10G-SFP-SP(16748596),	        --Finished Board Unit,USG9500,FW-12X10G-SFP+,12*10GE SFP+ Daughter Card
		subnameSPC-APPSEC-FW(16748597),	            	--Finished Board Unit,USG9500,SPC-APPSEC-FW,Application Security Service Processing Card



-- USG9100 SubCard :
                subbnameUSG9100SU61E8GF(16748564),      -- 8-port GE SubCard
                subbnameUSG9100SU61P4UF(16748565),      -- 4-port 2.5G POS SubCard
                subbnameUSG9100SU61E1XX(16748566),      -- 1-port 10G SubCard
                subbnameUSG9100SU61W1XX(16748567),      -- 1-port 10G SubCard
                subbnameUSG9100SU61P1XX(16748568),      -- 1-port 10G SubCard
                subbnameUSG9100SU61X2G16(16748569),   -- 2-port 10G LAN SFP+ Optical Interface and 16-port GE Optical Interface Card(SFP) ,with HS General Security Platform Software
                subbnameUSG9100E2XS(16748570),        -- 2*SFP+ Interface Broad,with HS General Security Platform Software
                subbnameUSG9100E16GF(16748571),       -- 16*SFP Interface Board,with HS General Security Platform Software
                --add by jiaoningfei wx299524 20160413
                --firewall product subcard scope 16728064~16732159 or Hex format: 0x00ff4000~0x00ff4fff
      subbnameSPCB-D-E8KE(16748631),     -- Firewall Processing card B(0x00ff9057)
      subbnameSPCA-S-E8KE(16748632),     -- Firewall Processing card A (0x00ff9058)
      subbnameSPC-20-B-E8KE(16748637),     -- 20G Firewall Performance Expansion Card B(oversea)(0x00ff905d)
      subbnameSPC-20-A-E8KE(16748638),     -- 20G Firewall Performance Expansion Card A(oversea)(0x00ff905e)
      subbnameE8KE-X-20X1G-RJ45(16728066),     -- Finished Board Unit,Eudemon8000E-X,E8KE-X-20X1G-RJ45,20-Port 10/100/1000Base-RJ45 Flexible Card(0x00ff4002)
      subbnameE8KE-X-3X40GE-QSFP(16728067),     -- Finished Board Unit,Eudemon8000E-X,E8KE-X-3X40GE-QSFP+,3-Port 40GBase-QSFP+ Flexible Card(P240-A)(0x00ff4003)

      --added by usg usg subFrame from  0x00ff4000 to  0x00ff4fff
          subbnameSPU5SPC(16728064),	        --0x00ff4000
          subbnameSUP5SPCH(16728065),	        --0x00ff4001
          subbnameSPCA-NAT-E8KE(16728069),      --0x00ff4005
          subbnameSPC-NAT-X8X16-E8KE(16728070),	--0x00ff4006
          subbnameSPU5SPCE(16728071),	        --0x00ff4007
          subbnameADS-SPC-III(16728075),	--0x00ff400b
          subbnameADS-SPC-II(16728076),	        --0x00ff400c
          subbnameADS-SPC-I(16728077),	        --0x00ff400d
          subbnameSPCB-HM(16728089),	        --0x00ff4019
          subbnameSPCB-20-O-HM(16728090),	--0x00ff401a
          subbnameNIP-24XG-SFP(16728091),	--0x00ff401b
          subbnameNIP-SAC-A-2CPU(16728092),     --0x00ff401c
          subbnameNIP-IPS-A(16728093),	        --0x00ff401d
      --end added by usg usg subFrame from   0x00ff4000 to  0x00ff4fff
-- USG12000 SubCard :
subbnameSPCA-ADS-01    (16728127),    --0xff403f
subbnameSPCA-ADS-02    (16728128),    --0xff4040
subbnameSPCA-USG-01    (16728129),    --0xff4041
subbnameSPCA-USG-02    (16728130),    --0xff4042
subbnameSPCA-USG-TP-01 (16728131),    --0xff4043
subbnameSPCA-USG-TP-02 (16728132),    --0xff4044
subbnameSPCA-E9KE-01   (16728133),    --0xff4045
subbnameSPCA-E9KE-02   (16728134),    --0xff4046
subbnameSPCA-E9KE-TP-01(16728135),    --0xff4047
subbnameSPCA-E9KE-TP-02(16728136),    --0xff4048
subbnameSPCA-IPS-01(16728137),    --0xff4049
subbnameSPCA-IPS-02(16728138),    --0xff404a
subbnameHI1620CPU(16728139),   --0xff404b
subbnameSPCB-USG-01       (16728140),      --0xff404c
subbnameSPCB-USG-02       (16728141),      --0xff404d
subbnameSPCB-USG-TP-01       (16728142),      --0xff404e
subbnameSPCB-USG-TP-02       (16728143),      --0xff404f
subbnameSPCB-E9KE-01       (16728144),      --0xff4050
subbnameSPCB-E9KE-02       (16728145),      --0xff4051
subbnameSPCB-E9KE-TP-01       (16728146),      --0xff4052
subbnameSPCB-E9KE-TP-02       (16728147),      --0xff4053
subbnameSPCB-IPS-01       (16728148),      --0xff4054
subbnameSPCB-IPS-02       (16728149),      --0xff4055
subbnameSPCB-ADS-01       (16728150),      --0xff4056
subbnameSPCB-ADS-02       (16728151),      --0xff4057
subbnameSPCB-E9KE-02-L       (16728152),      --0xff4058
subbnameSPCC-E9KE-01       (16728155),      --0xff405b

subnameSPCD-E9KE-02       (16748612),    --00FF9044
subnameSPCD-ADS-02       (16748613),    --00FF9045
subnameSPCD-IPS-02       (16748614),    --00FF9046
subnameSPCD-USG-TP-02       (16748615),    --00FF9047
subnameSPCD-E9KE-TP-02       (16748616),    --00FF9048

subnameSPCD-USG-04       (16748618),    --00FF904A
subnameSPCD-E9KE-04       (16748619),    --00FF904B
subnameSPCD-ADS-04       (16748620),    --00FF904C
subnameSPCD-IPS-04       (16748621),    --00FF904D
subnameSPCD-USG-TP-04       (16748622),    --00FF904E
subnameSPCD-E9KE-TP-04       (16748623),    --00FF904F

subnameSPCD-USG-02       (16748625),    --00FF9051


-- FutureMatrix: 0x000AF000~0x000AFFFF(716800~720895)
               subbnameFMFAN(716800),
               subbnameFMD8CQ(716801),
               subbnameFMD16Q(716802),
			   subbnameFMD24S2CQ(716803),
			   subbnameFMD24T2CQ(716804),
			   subbnameFMD32CQ(716805),
			   subbnameFM98D8DQ(716806),
                

-- LINGQU: 0x000B0000~0x000B0FFF(720896~724991)
     subbnamePICL1HROH                    (720896),
     subbnamePICL1HUB                       (720897),
     subbnamePICL1ROH                       (720898),
     subbnamePICL2ROH                       (720899),
     subbnamePICL2UB                          (720900),
     subbnamePICL2HCCS                     (720901),
     subbnamePICL3ROH                       (720902),
     subbnamePICL3UB                          (720903),
     subbnamePICL4ROH                       (720904),
     subbnamePICL4UB                          (720905),
     subbnamePICTGL2ROH                  (720906),
     subbnamePICTGL2HCCS                (720907),
     subbnamePICGGXC511L1A1          (720908),
     subbnamePICGGXC511L1A2          (720909),
     subbnamePICGGXC511L1B1          (720910),
     subbnamePICGGXC511L1B2          (720911),
     subbnamePICBUX510HCCS           (720912),
     subbnamePICBUX510UB                (720913),
     subbnamePICEVBROH                   (720914),
     subbnamePICEVBHCCS                 (720915),
     subbnamePICEVBUB                      (720916),
     subbnamePICL1HCCS                   (720917),
     subbnamePIC620V1ROH                 (720918),
     subbnamePICGGXC511L1C1              (720919),
	 subbnamePICGGXC511L1C2              (720920),
subbnameEnd(2147483647)
           }

        HWPortType ::= TEXTUAL-CONVENTION
            STATUS current
            DESCRIPTION
                "This data type is used as the syntax of the ifType
                object in the (updated) definition of MIB-II's
                ifTable.

                The definition of this textual convention with the
                addition of newly assigned values is published
                periodically by the IANA, in either the Assigned
                Numbers RFC, or some derivative of it specific to
                Internet Network Management number assignments.  (The
                latest arrangements can be obtained by contacting the
                IANA.)

                Requests for new values should be made to IANA via
                email (iana@iana.org).

                The relationship between the assignment of ifType
                values and of OIDs to particular media-specific MIBs
                is solely the purview of IANA and is subject to change
                without notice.  Quite often, a media-specific MIB's
                OID-subtree assignment within MIB-II's 'transmission'
                subtree will be the same as its ifType value.
                However, in some circumstances this will not be the
                case, and implementors must not pre-assume any
                specific relationship between ifType values and
                transmission subtree OIDs.

                "
            SYNTAX INTEGER
                {
                other(1),                       -- none of the following
                regular1822(2),
                hdh1822(3),
                ddnX25(4),
                rfc877x25(5),
                ethernetCsmacd(6),
                iso88023Csmacd(7),
                iso88024TokenBus(8),
                iso88025TokenRing(9),
                iso88026Man(10),
                starLan(11),
                proteon10Mbit(12),
                proteon80Mbit(13),
                hyperchannel(14),
                fddi(15),
                lapb(16),
                sdlc(17),
                ds1(18),                        -- DS1-MIB
                e1(19),                         -- Obsolete see DS1-MIB
                basicISDN(20),
                primaryISDN(21),
                propPointToPointSerial(22),     -- proprietary serial
                ppp(23),
                softwareLoopback(24),
                eon(25),                        -- CLNP over IP
                ethernet3Mbit(26),
                nsip(27),                       -- XNS over IP
                slip(28),                       -- generic SLIP
                ultra(29),                      -- ULTRA technologies
                ds3(30),                        -- DS3-MIB
                sip(31),                        -- SMDS, coffee
                frameRelay(32),                 -- DTE only.
                rs232(33),
                para(34),                       -- parallel-port
                arcnet(35),                     -- arcnet
                arcnetPlus(36),                 -- arcnet plus
                atm(37),                        -- ATM cells
                miox25(38),
                sonet(39),                      -- SONET or SDH
                x25ple(40),
                iso88022llc(41),
                localTalk(42),
                smdsDxi(43),
                frameRelayService(44),          -- FRNETSERV-MIB
                v35(45),
                hssi(46),
                hippi(47),
                modem(48),                      -- Generic modem
                aal5(49),                       -- AAL5 over ATM
                sonetPath(50),
                sonetVT(51),
                smdsIcip(52),                   -- SMDS InterCarrier Interface
                propVirtual(53),                -- proprietary virtual/internal
                propMultiplexor(54),            -- proprietary multiplexing
                ieee80212(55),                  -- 100BaseVG
                fibreChannel(56),               -- Fibre Channel
                hippiInterface(57),             -- HIPPI interfaces
                frameRelayInterconnect(58),     -- Obsolete use either [frameRelay(32)] or [frameRelayService(44)].
                aflane8023(59),                 -- ATM Emulated LAN for 802.3
                aflane8025(60),                 -- ATM Emulated LAN for 802.5
                cctEmul(61),                    -- ATM Emulated circuit
                fastEther(62),                  -- Fast Ethernet (100BaseT)
                isdn(63),                       -- ISDN and X.25
                v11(64),                        -- CCITT V.11/X.21
                v36(65),                        -- CCITT V.36
                g703at64k(66),                  -- CCITT G703 at 64Kbps
                g703at2mb(67),                  -- Obsolete see DS1-MIB
                qllc(68),                       -- SNA QLLC
                fastEtherFX(69),                -- Fast Ethernet (100BaseFX)
                channel(70),                    -- channel
                ieee80211(71),                  -- radio spread spectrum
                ibm370parChan(72),              -- IBM System 360/370 OEMI Channel
                escon(73),                      -- IBM Enterprise Systems Connection
                dlsw(74),                       -- Data Link Switching
                isdns(75),                      -- ISDN S/T interface
                isdnu(76),                      -- ISDN U interface
                lapd(77),                       -- Link Access Protocol D
                ipSwitch(78),                   -- IP Switching Objects
                rsrb(79),                       -- Remote Source Route Bridging
                atmLogical(80),                 -- ATM Logical Port
                ds0(81),                        -- Digital Signal Level 0
                ds0Bundle(82),                  -- group of ds0s on the same ds1
                bsc(83),                        -- Bisynchronous Protocol
                async(84),                      -- Asynchronous Protocol
                cnr(85),                        -- Combat Net Radio
                iso88025Dtr(86),                -- ISO 802.5r DTR
                eplrs(87),                      -- Ext Pos Loc Report Sys
                arap(88),                       -- Appletalk Remote Access Protocol
                propCnls(89),                   -- Proprietary Connectionless Protocol
                hostPad(90),                    -- CCITT-ITU X.29 PAD Protocol
                termPad(91),                    -- CCITT-ITU X.3 PAD Facility
                frameRelayMPI(92),              -- Multiproto Interconnect over FR
                x213(93),                       -- CCITT-ITU X213
                adsl(94),                       -- Asymmetric Digital Subscriber Loop
                radsl(95),                      -- Rate-Adapt. Digital Subscriber Loop
                sdsl(96),                       -- Symmetric Digital Subscriber Loop
                vdsl(97),                       -- Very H-Speed Digital Subscrib. Loop
                iso88025CRFPInt(98),            -- ISO 802.5 CRFP
                myrinet(99),                    -- Myricom Myrinet
                voiceEM(100),                   -- voice recEive and transMit
                voiceFXO(101),                  -- voice Foreign Exchange Office
                voiceFXS(102),                  -- voice Foreign Exchange Station
                voiceEncap(103),                -- voice encapsulation
                voiceOverIp(104),               -- voice over IP encapsulation
                atmDxi(105),                    -- ATM DXI
                atmFuni(106),                   -- ATM FUNI
                atmIma (107),                   -- ATM IMA
                pppMultilinkBundle(108),        -- PPP Multilink Bundle
                ipOverCdlc (109),               -- IBM ipOverCdlc
                ipOverClaw (110),               -- IBM Common Link Access to Workstn
                stackToStack (111),             -- IBM stackToStack
                virtualIpAddress (112),         -- IBM VIPA
                mpc (113),                      -- IBM multi-protocol channel support
                ipOverAtm (114),                -- IBM ipOverAtm
                iso88025Fiber (115),            -- ISO 802.5j Fiber Token Ring
                tdlc (116),                     -- IBM twinaxial data link control
                gigabitEthernet (117),          -- Gigabit Ethernet
                hdlc (118),                     -- HDLC
                lapf (119),                     -- LAP F
                v37 (120),                      -- V.37
                x25mlp (121),                   -- Multi-Link Protocol
                x25huntGroup (122),             -- X25 Hunt Group
                trasnpHdlc (123),               -- Transp HDLC
                interleave (124),               -- Interleave channel
                fast (125),                     -- Fast channel
                ip (126),                       -- IP (for APPN HPR in IP networks)
                docsCableMaclayer (127),        -- CATV Mac Layer
                docsCableDownstream (128),      -- CATV Downstream interface
                docsCableUpstream (129),        -- CATV Upstream interface
                a12MppSwitch (130),             -- Avalon Parallel Processor
                tunnel (131),                   -- Encapsulation interface
                coffee (132),                   -- coffee pot
                ces (133),                      -- Circuit Emulation Service
                atmSubInterface (134),          -- ATM Sub Interface
                l2vlan (135),                   -- Layer 2 Virtual LAN using 802.1Q
                l3ipvlan (136),                 -- Layer 3 Virtual LAN using IP
                l3ipxvlan (137),                -- Layer 3 Virtual LAN using IPX
                digitalPowerline (138),         -- IP over Power Lines
                mediaMailOverIp (139),          -- Multimedia Mail over IP
                dtm (140),                      -- Dynamic syncronous Transfer Mode
                dcn (141),                      -- Data Communications Network
                ipForward (142),                -- IP Forwarding Interface
                msdsl (143),                    -- Multi-rate Symmetric DSL
                ieee1394 (144),                 -- IEEE1394 High Performance Serial Bus
                if-gsn (145),                   -- HIPPI-6400
                dvbRccMacLayer (146),           -- DVB-RCC MAC Layer
                dvbRccDownstream (147),         -- DVB-RCC Downstream Channel
                dvbRccUpstream (148),           -- DVB-RCC Upstream Channel
                atmVirtual (149),               -- ATM Virtual Interface
                mplsTunnel (150),               -- MPLS Tunnel Virtual Interface
                srp (151),                      -- Spatial Reuse Protocol
                voiceOverAtm (152),             -- Voice Over ATM
                voiceOverFrameRelay (153),      -- Voice Over Frame Relay
                idsl (154),                     -- Digital Subscriber Loop over ISDN
                compositeLink (155),            -- Avici Composite Link Interface
                ss7SigLink (156),               -- SS7 Signaling Link
                propWirelessP2P (157),          -- Prop. P2P wireless interface
                frForward (158),                -- Frame Forward Interface
                rfc1483 (159),                  -- Multiprotocol over ATM AAL5
                usb (160),                      -- USB Interface
                ieee8023adLag (161),            -- IEEE 802.3ad Link Aggregate
                bgppolicyaccounting (162),      -- BGP Policy Accounting
                frf16MfrBundle (163),           -- FRF .16 Multilink Frame Relay
                h323Gatekeeper (164),           -- H323 Gatekeeper
                h323Proxy (165),                -- H323 Voice and Video Proxy
                mpls (166),                     -- MPLS
                mfSigLink (167),                -- Multi-frequency signaling link
                hdsl2 (168),                    -- High Bit-Rate DSL - 2nd generation
                shdsl (169),                    -- Multirate HDSL2
                ds1FDL (170),                   -- Facility Data Link 4Kbps on a DS1
                pos (171),                      -- Packet over SONET/SDH Interface
                dvbAsiIn (172),                 -- DVB-ASI Input
                dvbAsiOut (173),                -- DVB-ASI Output
                plc (174),                      -- Power Line Communtications
                nfas (175),                     -- Non Facility Associated Signaling
                tr008 (176),                    -- TR008
                gr303RDT (177),                 -- Remote Digital Terminal
                gr303IDT (178),                 -- Integrated Digital Terminal
                isup (179),                     -- ISUP
                propDocsWirelessMaclayer (180), -- prop/Maclayer
                propDocsWirelessDownstream (181),   -- prop/Downstream
                propDocsWirelessUpstream (182), -- prop/Upstream
                hiperlan2 (183),                -- HIPERLAN Type 2 Radio Interface
                propBWAp2Mp (184),              -- PropBroadbandWirelessAccesspt2multipt
                sonetOverheadChannel (185),     -- SONET Overhead Channel
                digitalWrapperOverheadChannel (186),    -- Digital Wrapper
                aal2 (187),                     -- ATM adaptation layer 2
                radioMAC (188),                 -- MAC layer over radio links
                atmRadio (189),                 -- ATM over radio links
                imt (190),                      -- Inter Machine Trunks
                mvl (191),                      -- Multiple Virtual Lines DSL
                reachDSL (192),                 -- Long Reach DSL
                frDlciEndPt (193),              -- Frame Relay DLCI End Point
                atmVciEndPt (194),              -- ATM VCI End Point
                opticalChannel (195),           -- Optical Channel
                opticalTransport (196),         -- Optical Transport
                propAtm (197),                  -- Proprietary ATM
                voiceOverCable (198),           -- Voice Over Cable Interface
                infiniband (199),               -- Infiniband
                teLink (200),                   -- TE Link
                q2931 (201),                    -- Q.2931
                virtualTg (202),                -- Virtual Trunk Group
                sipTg (203),                    -- SIP Trunk Group
                sipSig (204),                   -- SIP Signaling
                docsCableUpstreamChannel (205), -- CATV Upstream Channel
                econet (206),                   -- Acorn Econet
                pon155 (207),                   -- FSAN 155Mb Symetrical PON interface
                pon622 (208),                   -- FSAN622Mb Symetrical PON interface
                bridge (209),                   -- Transparent bridge interface
                linegroup (210),                -- Interface common to multiple lines
                voiceEMFGD (211),               -- voice E&M Feature Group D
                voiceFGDEANA (212),             -- voice FGD Exchange Access North American
                voiceDID (213),                 -- voice Direct Inward Dialing
                mpegTransport (214),            -- MPEG transport interface
                sixToFour (215),                -- 6to4 interface
                gtp (216),                      -- GTP (GPRS Tunneling Protocol)
                pdnEtherLoop1 (217),            -- Paradyne EtherLoop 1
                pdnEtherLoop2 (218),            -- Paradyne EtherLoop 2
                opticalChannelGroup (219),      -- Optical Channel Group
                homepna (220),                  -- HomePNA ITU-T G.989
                gfp (221),                      -- Generic Framing Procedure (GFP)
                ciscoISLvlan (222),             -- Layer 2 Virtual LAN using Cisco ISL
                fcipLink (224),                 -- FCIP Link
                rpr (225),                      -- Resilient Packet Ring Interface Type
                qam (226),                      -- RF Qam Interface
                lmp (227),                      -- Link Management Protocol
                cblVectaStar (228),             -- Cambridge Broadband Limited VectaStar
                docsCableMCmtsDownstream (229), -- CATV Modular CMTS Downstream Interface
                adsl2 (230),                    -- Asymmetric Digital Subscriber Loop Version 2
                macSecControlledIF (231),       -- MACSecControlled
                macSecUncontrolledIF (232),     -- MACSecUncontrolled

-- huawei expanding
                aponOltPort(501),               -- Apon olt port
                aponOltSubport(502),            -- Apon olt sub port
                aponOntPort(503),               -- Apon ont port
                atmPort(504),                   -- atm port
                atmSubport(505),                -- atm sub port
                adslPort(506),                  -- Already defined in RFC
                lanPort(507),                   -- lan port
                cescPort(508),                  -- E1 port of CESC board
                cesdPort(509),                  -- V35 port of CESD board
                frcPort(510),                   -- E1 port FR board
                fpcSubport(511),                -- fpc sub port
                sepPort(512),                   -- sep port
                vpringPort(513),                -- STM-4 VPRING port
                eimPort(514),                   -- FE port of BAS board
                geimPort(515),                  -- GE port of BAS board
                basMainport(516),               -- ATM port of BAS board used to create connection
                apruCes(517),                   -- Apon CES port
                apruLan(518),                   -- Apon LAN port
                asxSoftSar(519),                -- soft sar port of ASX board
                asxHardSar(520),                -- hard sar port of ASX board
                cesE1Port(521),                 -- E1 port of CES board, for TDM use
                e1Port(522),                    -- E1 port of CES
                t1Port(523),                    -- T1 port of CES
                pstnPort(524),                  -- pstn port
                braPort(525),                   -- pstn port
                praPort(536),                   -- bra port
                cdiPort(539),                   -- vfb port
                vfbPort(540),                   -- pstn port
                atiPort(541),                   -- ati port
                mlcE1Port(542),                 -- mlcE1 port
                v5TkPort(543),                  -- v5Tk port
                comPort(544),                   -- com port
                v35Port(545),                   -- v35 port
                mmxIwe8Port(546),               -- CES port on MMXC board
                frPortE1(547),                  -- E1 port of FR board
                frPortT1(548),                  -- T1 port of FR board
                frPortV35(549),                 -- V35 port of FR board
                aiuAtmPort(550),                -- ATM port on AIU board
                imaPort(551),                   -- IMA port
                e3Port(552),                    -- E3 port
                mmxImaPort(554),                -- IMA port on MMX board
                nullPort(555),                  -- null port
                shdslPort(556),                 -- G.SHDSL  port
                iadMainport(557),               -- iad main port
                iadPort(558),                   -- ida port
                cesSDTVPort(559),               -- CES SDT virtual port
                vlanVPort(560),                 -- VLAN virtual port of LAN board
                frVCCIndexVPort(561),           -- FR VCC virtual port
                frStreamVPort(562),             -- FR stream virtual port
                imaGroupVPort(563),             -- IMA group virtual port
                adslInterleaveVPort(564),       -- Interleavet virtual port of ADSL board
                adslFastVPort(565),             -- Fast virtual port of ADSL board
                lanTrunkVPort(566),             -- Trunk virtual port of LAN board
                sepsmxAtmPort(568),             -- Used to configure the SEPL or SMXL port feature
                dehaUdtPort(569),               -- UDT Port of DEHA board
                t1TdmPort(570),                -- T1 port of TDM
                cposT1ccPort(571),             -- CPOS port of T1CC
                lanswitchPort(572),             -- port of the board for lanswitch between chassises
                vsrPort(573),                   -- VSR port of OFCA board or SFEA
                sfpClusterPort(574),            -- SFP port of the board for lanswitch between chassises
-- OFA5920
                bitsPort(575),                  -- BITS port
                gponOnuPort(576),               -- GPON upstream port
                eponOnuPort(577),               -- EPON upstream port
                hwPort(578),                    -- HW port of PVM
        gponOltPor(579),                -- GPON OLT port
-- MA5200
                debugserial(580),               -- debug serial port
                debugnet(581),                  -- debug net port
-- MA5800
                xponOltPort(597),               -- XPON OLT port
-- MA5600
                nativeTDME1Port(589),           -- Native TDM E1 port
                nativeTDMT1Port(590),           -- Native TDM T1 port
                tengeOptPort(591),              -- 10GE optical port
                eponOltPort(592),               -- EPON OLT port
                stm-1Port(593),                 -- STM-1 port of H801O2CE subboard
		hundredgeOptPort(594),          -- 100GE optical port
                fortyOptPort(595),              -- 40GE optical port
-- MA5200
                sdlFE1Port(600),                -- SDL FE1 port
                sdlShdslPort(601),              -- SDL G.SHDSL port
-- MA5635
                adslPstnPort(700),                -- adsl como port, especially for adsl como board
                vdslPstnPort(701),                -- vdsl como port, especially for vdsl como board
-- SD5103
                serialSrvPort(799),               -- serial service port
                autoAdptPort(800),                -- auto adpt port
                catvPort(801),                    -- CATV port

-- SRG
                fxoport(802),                    -- FXO port
-- MA5631
                eocport(803),                    -- EoC master RF port
-- MA5633
                docsisport(804),                 -- docsis port of board HS33CDAA,the board has only one port(docsisPort).
-- MA5616
                veiPort(805),                    -- Vei port of board NLV.
-- MA5694S
               vdslNNIPort(806),                 -- VDSL upstream port.
-- MA5811S
               gfast-port(807),                  --G.FAST PORT.

               rfIpReturnPort(808),             -- IP return RF port
-- MA5800
               lanVPort(809),                   -- LAN virtual port of bord.
               otnPort(810),                    -- physical port of otn board.
-- T8010
               portnameGNSS(811),
               portnameCLOCK(812),
               portname1PPSTOD(813),                -- The port with RJ45 type
               portnameClockType(814),               -- 8 clock port group type
-- 8010
                dsp(65536),                      -- dsp port
                bits(65537),                     -- bits port
                clk(65538),                      -- clk port
                mon(65539),                      -- mon port
                aux(65540),                      -- aux port
                sdho(65541),                     -- sdho port
                sdhe(65542),                     -- sdhe port

-- hwRPS
               fanPort(786932),                   --Fan module fan port
               dcoutputPort(786933),              --Up converter module DC output port
               dcinputPort(786694),               --Down converter module DC input port
-- MA5200 add definition of port type 0x21000(135168) ~ 0x21FFF(139263)
                portnameH521ATMOC3S(135168),
                portnameH521ATMOC3M(135169),
                portnameH521ATMOC12S(135170),
                portnameH521ATMOC12M(135171),
                portnameH521CPOSOC3S(135172),
                portnameH521CPOSOC3M(135173),
                portnameH521CPOSOC48S(135174),
                portnameH521CPOSOC48M(135175),
                portnameH521FEE(135176),
                portnameH521FEOSSFP(135177),
                portnameH521FEOMSFP(135178),
                portnameH521GEESFP(135179),
                portnameH521GEOSSFP(135180),
                portnameH521GEOMSFP(135181),
                portnameH521POSOC3S(135182),
                portnameH521POSOC3M(135183),
                portnameH521POSOC12S(135184),
                portnameH521POSOC12M(135185),
                portnameH521POSOC48S(135186),
                portnameH521POSOC48M(135187),
                portnameH521E1(135188),
                portnameH521T1(135189),
                portnameH521E3(135190),
                portnameH521T3(135191),
                portnameH521CE1(135192),
                portnameH521CT1(135193),
                portnameH521CPOSOC3(135194),
                portnameH521GEEGBIC(135195),
                portnameH521GEOMGBIC(135196),
                portnameH521GEOSGBIC(135197),
                portnameH521GEOMMTRJ(135198),
                portnameH521GEOSMTRJ(135199),
                portnameH521GEOSLC(135200),
                portnameH521GEOMLC(135201),
                portnameH521GEOSSC(135202),
                portnameH521GEOMSC(135203),
                portnameH521FEOSMTRJ(135204),
                portnameH521FEOMMTRJ(135205),
                portnameH521FEOSSC(135206),
                portnameH521FEOMSC(135207),
                portnameH521FEOSLC(135208),
                portnameH521FEOMLC(135209),
                portnameH522GERPR(135210),
                portnameH523POS10G(135211),
                portnameH523GE10GLAN(135212),
                portnameH523GE10GWAN(135213),
                portnameH521ATMOC3(135214),
                portnameH521ATMOC12(135215),
                portnameH521CPOSOC48S2(135216),
                portnameH521FEOSFP(135217),
                portnameH521POSOC3(135218),
                portnameH521POSOC12(135219),
                portnameH521POSOC48(135220),
                portnameH521GEOGBIC(135221),
                portnameH521GEOLC(135222),
                portnameH521GEOSC(135223),
                portnameH521GEOSFP(135224),
                portnameH521FEOLC(135225),
                portnameH521FEOSC(135226),
                portnameH523POS10GS(135227),
                portnameH523POS10GM(135228),
                portnameH523GE10GLANS(135229),
                portnameH523GE10GLANM(135230),
                portnameH523GE10GWANS(135231),
                portnameH523GE10GWANM(135232),
                portnameH521SMUFE(135233),
                portnameH523SMUGGE(135234),
-- WA5700:
                bwaTdmPort(155648),               -- TDM port of the BWA

-- 8031:        S23&33&53&CX200D porttype definition

                portnameS233353SFP(536576),    -- The port when SFP transceiver plugged in
                portnameS233353ESFP(536577),   -- The port when ESFP transceiver plugged in
                portnameS233353RJ45(536578),   -- The port with RJ45 type
                portnameS233353FIBER(536579),  -- The port with fiber type without transceiver
                portnameS233353COMBOFIBER(536580),  -- The port with combo fiber type
                portnameS233353COMBOCOPPER(536581), -- The port with combo copper type

-- S9300:       0x000A1000~0x000A1fff(659456~663551)
                portnameLE01SFP(659456),
                portnameLE01ESFP(659457),
                portnameLE01RJ45(659458),
                portnameLE01ERJ45(659459),
                portnameLE01RJ45POE(659460),
                portnameLE01XFP(659461),
                portnameLE01EXFP(659462),
                portnameLE01COMBO(659463),
                portnameLE02EPON(659464),
                portnameLE02VXFP(659465),
                portnameLE02POS(659466),
                portnameLE024XFP(659467),
                portnameLE02XRJ45(659468),
                portnameLE0210XFP(659469),
                portnameLE0225FP(659470),

-- AR:          0x000A3000~0x000A3fff(667648~671743)
                portnameAR01FELANRJ45(667648),          -- The port with RJ45 type of FE LAN
                portnameAR01FELANFIBER(667649),         -- The port with fiber type of FE LAN
                portnameAR01FEWANRJ45(667650),          -- The port with RJ45 type of FE WAN
                portnameAR01FEWANFIBER(667651),         -- The port with fiber type of FE WAN
                portnameAR01GELANRJ45(667652),          -- The port with RJ45 type of GE LAN
                portnameAR01GELANFIBER(667653),         -- The port with fiber type of GE LAN
                portnameAR01GEWANRJ45(667654),          -- The port with RJ45 type of GE WAN
                portnameAR01GEWANFIBER(667655),         -- The port with fiber type of GE WAN
                portnameAR01COMBOFIBER(667656),         -- The port with combo fiber type
                portnameAR01COMBOCOPPER(667657),        -- The port with combo copper type
                portnameAR01E1DB9(667658),              -- The port with E1/CE1 type DB9 head
                portnameAR01T1DB9(667659),              -- The port with T1/CT1 type DB9 head
                portnameAR01SYNSERIAL(667660),          -- The port with Sync Serial type
                portnameAR01ASYNSERIAL(667661),         -- The port with Async Serial type
                portnameAR01ISDNVOICE(667662),          -- The port with ISDN voice type
                portnameAR01FXS(667663),                -- The port with FXS type
                portnameAR01FXO(667664),                -- The port with FXO type
                portnameAR01ADSL(667665),               -- The port with ADSL type
                portnameAR01VDSL(667666),               -- The port with VDSL type
                portnameGSGDSL(667667),                 -- The port with G.SHDSL type with Ethernet mode
                portnameAR01EPON(667668),               -- The port with EPON type
                portnameAR01GPON(667669),               -- The port with GPON type
                portnameAR013G(667670),                 -- The port with 3G type
                portnameAR01ISDNDATA(667671),           -- The port with ISDN data type
                portnameAR01E1FDB9(667672),             -- The port with E1-F type DB9 head
                portnameAR01T1FDB9(667673),             -- The port with T1-F type DB9 head
                portnameGSGDSLATM(667674),              -- The port with G.SHDSL type with ATM mode
                portnameCPOS(667675),                   -- The port with CPOS type
                portnameAR01E1RJ45(667676),             -- The port with E1/CE1 type RJ45 head
                portnameAR01T1RJ45(667677),             -- The port with T1/CT1 type RJ45 head
                portnameAR01E1FRJ45(667678),            -- The port with E1-F type RJ45 head
                portnameAR01T1FRJ45(667679),            -- The port with T1-F type RJ45 head
                portnameAR01EM(667680),                 -- The port with E&M type
                portnameAR01GEWANM12(667681),           -- The port with M12 type of GE WAN
                portnameAR01GELANM12(667682),           -- The port with M12 type of GE LAN
                portnameAR01OPENGE(667683),             -- The port with OPENGE type
                portnameAR01VGE(667684),                -- The port with VGE type

-- CloudEngine:    0x000A8000~0x000A8fff(688128~692223)
                portnameDCDE01SFP(688128),              -- The port with 10/100/1000BASE-T type
                portnameDCDE01QSFP(688129),             -- The port with 10G BASE-T type
                portnameDCDE01XFP(688130),              -- The port with 10G SFP type
                portnameDCDE01QXFP(688131),             -- The port with 40G SFP type
                portnameDCDE01VXFP(688132),             -- The port with 40G/4*10G SFP type
                portnameDCDE01RJ45(688133),             -- The port with RJ45 type
                portnameDCDE01CFP(688134),              -- The port with 100G CFP type
                portnameDCDE01CFP2(688135),             -- The port with 100G CFP2 type
                portnameDCDE01CXP(688136),              -- The port with 100G CXP type
                portnameDCDE01SFP2(688137),             -- The port with GE SFP type
                portnameDCDE01QSFP28(688138),           -- The port with 100G QSFP type
                portnameDCDE01SFP25G(688139),           -- The port with 25G SFP type
                portnameDCDE01CFP10G(688140),           -- The port with 10G type split from 100G CFP type
                portnameDCDE01CFP40G(688141),           -- The port with 40G type split from 100G CFP type
                portnameDCDE01CFP210G(688142),          -- The port with 10G type split from 100G CFP2 type
                portnameDCDE01CFP240G(688143),          -- The port with 40G type split from 100G CFP2 type
                portnameDCDE01CXP10G(688144),           -- The port with 10G type split from 100G CXP type
                portnameDCDE01CXP40G(688145),           -- The port with 40G type split from 100G CXP type
				portnameDCDE01QSFPDD(688146),           -- The port with 400G QSFP type
                portnameDCDE01QSFP56(688147),           -- The port with 200G QSFP type
                portnameDCDE01SFP56(688148),            -- The port with 50G SFP type
                portnameDCDE01RJ4525GE(688149),     -- The port with 25G BASE-T type
                portnameDCDE01SPE(688150),              --  The port with 10BASE-T1L type
                portnameDCDE01QSFPDD800G(688151),       -- The port with 800G QSFPDD type
                portnameDCDE01DSFP(688152),             -- The port with 100G DSFP type

-- LINGQU:    0x000A9000~0x000A9fff(692224~696319)
                portnameROHPORTF200G(692224),
                portnameROHPORTE200G(692225),
                portnameR2EPORTE200G(692226),
                portnameR2EPORTF200G(692227),
                portnameHCCSPORTF200G(692228),
                portnameHCCSPORTE200G(692229),
                portnameUBGPORTF200G(692230),
                portnameUBGPORTE200G(692231),
                portnameUBG2EPORTE200G(692232),
                portnameUBG2EPORTF200G(692233),

-- USG2200,USG2100
                wifi(16711680),                   -- WIFI card communicates with WIFI terminals as a wireless AP, and supports IEEE 802.11b/ 802.11g
                veport(16711681),                 -- The Virtual Ethernet (VE) is applied to the PPPoEoA and IPoEoA.
                                                  -- It functions on the interface board. Externally it features Ethernet attributes
                g3Port(16711682),                 -- 3G supports three wireless communication mode, including both WCDMA/CDMA2000/TD-SCDMA and corresponding 2G mode.
                serialPort(16711683),             -- The serial port is used for the exchange of information between computers or devices
                                                  -- one bit at a time over a single channel. Serial communications can be synchronous or asynchronous.
                                                  -- Both sender and receiver must use the same baud rate, parity, and control information.
                dialerPort(16711684),             -- The dialer interface is used as dialing interface of pppoe client ,supports pppoe protocol
                t1(16711685),
                electricityPort(16711686)         --electricity port
                }

        HWUnSupportNodeInteger ::= TEXTUAL-CONVENTION
            STATUS current
            DESCRIPTION
                "
                This object is not used any longer.To the nodes that don't supported in the MIB table ,the default value
                should be return for keeping the integrity of the OID in the MIB table ,
                and the type of the default value is INTEGER, and default value is 65535.

                "
            SYNTAX INTEGER { defaultValue(65535) }

        HWUnSupportNodeString ::= TEXTUAL-CONVENTION
            STATUS current
            DESCRIPTION
                "
                This object is not used any longer.To the nodes that don't supported in the MIB table ,the default value
                should be return for keeping the integrity of the OID in the MIB table,
                and the default string is the null string. "
            SYNTAX OCTET STRING (SIZE (0))

        HWUnSupportNodeIPAddress ::= TEXTUAL-CONVENTION
            STATUS current
            DESCRIPTION
                "This object is not used any longer.To the nodes that don't supported in the MIB table ,the default value
                should be return for keeping the integrity of the OID in the MIB table,
                and the default IP address is 0.0.0.0."
            SYNTAX IpAddress

        HWUnSupportNodeMacAddress ::= TEXTUAL-CONVENTION
            STATUS current
            DESCRIPTION
                "This object is not used any longer.To the nodes that don't supported in the MIB table ,the default value
                should be return for keeping the integrity of the OID in the MIB table,
                and the default string is '000000'. "

            SYNTAX MacAddress
        HWVirtualEntityType ::= TEXTUAL-CONVENTION
            STATUS current
            DESCRIPTION
                "This object is not used any longer.To show the relevant virtual entity type in vender type object.
                "
            SYNTAX INTEGER
                {
                other(1),                       -- none of the following
                -- Begin: V8R8C10 season 4
               virent8090DEVCR5D0MPUB571(564850),    -- V8R8C10 season 4 for CR5D0MPUB571(SBOM), Main Processing Unit B5(16G Memory)
               virent8090DEVCX6D0MPUB571(564851),    -- V8R8C10 season 4 for CX6D0MPUB571(SBOM), Main Processing Unit B5(16G Memory)
               virentPTN6900DEVTNRD0MPUB571(229479), -- V8R8C10 season 4 for TNRD0MPUB571(SBOM), Main Processing Unit B5(16G Memory)
                   virentME60DEVME0D0MPUB571(159764),    -- V8R8C10 season 4 for ME0D0MPUB571(SBOM), Main Processing Unit B5(16G Memory)

                   virent8090DEVCR5D0MPUD471(564852),    --V8R8C10 season 4 for CR5D0MPUD471(SBOM),Main Processing Unit D4(16G Memory)
                   virent8090DEVCX6D0MPUD471(564853),    --V8R8C10 season 4 for CX6D0MPUD471(SBOM),Main Processing Unit D4(16G Memory)
                   virentPTN6900DEVTNRD0MPUD471(229480), --V8R8C10 season 4 for TNRD0MPUD471(SBOM),Main Processing Unit D4(16G Memory)

                   virent8090DEVCR5D0SRUA871(564854),    -- V8R8C10 season 4 for CR5D0SRUA871(SBOM), Switch and Route Processing Unit A8(16G Memory)
                   virent8090DEVCX6D0SRUA871(564855),    -- V8R8C10 season 4 for CX6D0SRUA871(SBOM), Switch and Route Processing Unit A8(16G Memory)
                   virentPTN6900DEVTNRD0SRUA871(229482), -- V8R8C10 season 4 for TNRD0SRUA871(SBOM), Switch and Route Processing Unit A8(16G Memory)
                   virentME60DEVME0D0SRUA871(159765),    -- V8R8C10 season 4 for ME0D0SRUA871(SBOM), Switch and Route Processing Unit A8(16G Memory)

                   virent8090DEVCR5D0SRUA971(564856),    -- V8R8C10 season 4 for CR5D0SRUA971(SBOM), Switch and Route Processing Unit A9(16G Memory)
                   virent8090DEVCX6D0SRUA971(564857),    -- V8R8C10 season 4 for CX6D0SRUA971(SBOM), Switch and Route Processing Unit A9(16G Memory)
                   virentPTN6900DEVTNRD0SRUA971(229483), -- V8R8C10 season 4 for TNRD0SRUA971(SBOM), Switch and Route Processing Unit A9(16G Memory)
                   virentME60DEVME0D0SRUA971(159766),    -- V8R8C10 season 4 for ME0D0SRUA971(SBOM), Switch and Route Processing Unit A9(16G Memory)
                -- end: V8R8C10 season 4

     -- from 536577 to 561150 is for 8031 Whole BOARD
 -- 8031:
                -- from 536577 to 536999 is for 8031 MPU Whole board
                virentCX61DEVCR52SRUA(536577),   -- the old whole board of SRUA saled before V3R7 version in CX600(whithout SBOM information)
                virentCX61DEVCR52MPUA(536578),   -- the old whole board of MPUA saled before V3R7 version in CX600(whithout SBOM information)
                virentCX61DEVCR52MPUB(536579),   -- the old whole board of MPUB saled before V3R7 version in CX600(whithout SBOM information)
                virentCX61DEVCR55MPUD(536580),   -- the old whole board of CR55MPUD saled before V3R7 version in CX600(whithout SBOM information)
                virentCX61DEVCR52MPUD(536581),   -- the old whole board of CR52MPUD saled before V3R7 version in CX600(whithout SBOM information)
                virentCX61DEVCR52SRUC(536582),   -- the old whole board of SRUC saled before V3R7 version in CX600(whithout SBOM information)
                virentCX61DEVCR52MPUC(536583),   -- the old whole board of MPUC saled before V3R7 version in CX600(whithout SBOM information)

                virentCX61DEVCX6D0SRUA410(536584), -- V6R1 for CX6D0SRUA410(SBOM),Switch and Route Processing Unit A4(Including 1*2G Memory and 1*1G CF Card)
                virentCX61DEVCX6D0MPUB410(536585), -- V6R1 for CX6D0MPUB410(SBOM),Main Processing Unit B4(Including 1*2G Memory and 1*1G CF Card)
                virentCX67DEVCX67MPUG(536586),     -- V6R2 for CX67MPUG,Main Processing Unit G
                virentCX61DEVCR57MPUH(536587),     -- the new whole board of CR57MPUH V6R5 version in CX600(whithout SBOM information)
                virent8090DEVCX6D00MPUK10(536588), -- V8R5 for SBOM, CX6D00MPUK10, Main Processing Unit K  ,in -country


                -- from 537000 to 537799 is for 8031 SFU Whole board
                virentCX61DEVCR52SFUA(537000),       -- the old whole board of SFUA saled before V3R7 version in CX600(whithout SBOM information)
                virentCX61DEVCR52SFUC(537001),       -- the old whole board of SFUC saled before V3R7 version in CX600(whithout SBOM information)
                virentCX61DEVCR52SFUD(537002),       -- the old whole board of SFUD saled before V3R7 version in CX600(whithout SBOM information)
                virentCX61DEVCR52SFUF(537003),       -- the old whole board of SFUF saled before V3R7 version in CX600(whithout SBOM information)
                virentCX61DEVCR52SFUG(537004),       -- the old whole board of SFUG saled before V3R7 version in CX600(whithout SBOM information)
                virentCX61DEVCR52SFUI(537005),       -- the old whole board of SFUI saled before V3R7 version in CX600(whithout SBOM information)
                virentCX61DEVCR52SFEA(537006),       -- the old whole board of SFEA saled before V3R7 version in CX600(whithout SBOM information)
                virentCX61DEVCR52SFEB(537007),       -- the old whole board of SFEB saled before V3R7 version in CX600(whithout SBOM information)
                virentCX61DEVCR57SFU40A(537008),     -- the old whole board of SFU40A saled before V3R7 version in CX600(whithout SBOM information)
                virentCX61DEVCR57SFU40B(537009),     -- the old whole board of SFU40B saled before V3R7 version in CX600(whithout SBOM information)

                virentCX61DEVCX6DSFUI401B(537010),    -- V6R1 for CX6DSFUI401B(SBOM), 40Gbps Switch Fabric Unit B
                virentCX61DEVCX6DSFUI401C(537011),    -- V6R1 for CX6DSFUI401C(SBOM), 40Gbps Switch Fabric Unit C
                virentCX61DEVCX61SFUG40GBPS(537012),  -- V6R1 for CX61-SFUG-40Gbps(SBOM), Switch Fabric Unit G

                virentCX61DEVCR57SFU100C(537013),     -- Two piece 8890, X8 100G SFU
                virentCX61DEVCR57SFU200B(537014),     -- Two piece 5802, X16 100G-200G SFU
                virentCX61DEVCR57SFU200C(537015),     -- Two piece 5802, X8 100G-200G SFU

                virentCX61DEVCR57SRU100A(537016),     -- Two piece 8890, 100G SFU, used with X8 SRUA100A MPU
                virentCX61DEVCX6D0SRUA510(537017),     -- Two piece 5802, 200G SFU, used with X8 SRUA200A MPU

                virentCX61DEVCR57LPUF41A(537018),     -- LPUF41A 40G LPU,SD58X2 Solution ,MIPS CPU
                virentCX61DEVCR57LPUF101A(537019),    -- Double LPUF41A, 100G LPU

                -- from 537800 to 540671 is for 8031 LPU Whole board and other board
                virentCX67DEVCX67NPUI20A(537800),    -- V6R2 for CX67NPUI20A, Flexible Card Line Processing Unit
                virent8090DEVCX6D0NSU5010(537801),   -- V8R5 for SBOM ,CX6D0NSU5010, Network Switch Unit (NSU-50)  in -country
                virent8090DEVCX6D00L2XF10(537802),      -- CX6D00L2XF10, 2-Port 10GBase LAN/WAN-SFP+ Service Interface Card(SIC)
                virent8090DEVCX6D00E8GF10(537803),   -- CX6D00E8GF10, 8-Port 100/1000Base-X-SFP Service Interface Card(SIC)
                virent8090DEVCX6D00E8GE10(537804),   -- CX6D00E8GE10, 8-Port 10/100/1000Base-RJ45 Service Interface Card(SIC)

                virent8090DEVCX6X0PWRDC70(537805),   -- V8R5 for SBOM ,  CX600-X2 DC/DC Power Module
                virent8090DEVCX6M001FBX71(537806),   -- V8R5 for SBOM ,  CX600-X1 FAN Module
                virent8090DEVCX6M002FBX72(537807),   -- V8R5 for SBOM ,  CX600-X2 FAN Module

                virent8090DEVCX6B0BKP0271(537808),   -- V8R5 for SBOM ,  CX600-X2 BACK Plane
                virent8090DEVCX6B0BKP0171(537809),
                virent8090DEVCX6D000IE170(537810),   -- V8R5 for SBOM ,  32E1 interface card, 75 ohm

                virent8090DEVCX6D000IE171(537811),   -- V8R5 for SBOM ,  32E1 interface card,120 ohm

                virent8090DEVCX6D00P4CF70(537812),   -- V8R5 for SBOM ,  4*155M CPOS interface card

                virent8090DEVCX6DNSU12010(537813),   -- V8R5 for SBOM ,CX6D0NSU12010, Network Switch Unit (NSU-120)  in -country
                virent8090DEVCX6D000DE110(537814),   -- V8R5 for SBOM ,  16E1 interface card, 75 ohm
                virent8090DEVCX6D000DE111(537815),   -- V8R5 for SBOM ,  16E1 interface card, 120 ohm

                virentCX67DEVCX6D000FBX70(540670),    -- V6R2 for ****, CX600-X1/X2 Fan Unit
                virentCX67DEVCX6D00PSUD70(540671),    -- V6R2 for CX6D00PSUD70, CX600-X1/X2 DC Power Supply Unit
                -- from 538000 to 538010
                virentCX62DEVCX67MPUG0(538000),       -- for CX600-DO Main Processing Unit G (Including 1*1G CF Card)
                virentCX62DEVCX67NPUI20(538001),      -- for CX600-DO Integrated Network Processing Unit with 2-Port 10GBase LAN/WAN-XFP(NPUI-20)
                virentCX62DEVCX67NPU20B0(538002),     -- for CX600-DO Integrated Network Processing Unit(NPUI-20-B)
                virentCX62DEVCX6D0MPUB411(538003),       -- for CX600-DO Main Processing Unit B4(Including 1*2G Memory and 1*1G CF Card)
                virentCX62DEVCR52SFU40B0(538004),     -- for CX600-DO 40Gbps Switch Fabric Unit B
                virentCX62DEVCR52SRU40A4(538005),     -- for CX600-DO Switch and Route Processing Unit A4(Including 1*2G Memory and 1*1G CF Card)
                virentCX62DEVCR52SFU40C0(538006),     -- for CX600-DO 40Gbps Switch Fabric Unit C
                virentCX62DEVCR52MPUD0(538007),       -- for CX600-DO Main Processing Unit D(Including 1*2G Memory and 1*1G CF Card)
                virentCX62DEVCR52ISUF10(538008),      -- for CX600-DO Flexible Card Integrated Service Unit(ISUF-10,four sub-slots)
                virentCX62DEVCR52ISUF20(538009),      -- for CX600-DO Flexible Card Integrated Service Unit(ISUF-20,two sub-slots)
                virentCX62DEVCR52ISUF40(538010),      -- for CX600-DO Flexible Card Integrated Service Unit(ISUF-40,two sub-slots)
                virent8090DEVCX6D0L4XXA10(538011),    -- for CX600-DO, CX6D0L4XXA10,4-Port 10GBase LAN/WAN-XFP Integrated Line Processing Unit (ISUI-41,Supporting 1588v2)
                virent8090DEVCX6D0EKGFA10(538012),    -- for CX600-DO, CX6D0EKGFA10,40-Port 100/1000Base-X-SFP Integrated Line Processing Unit (ISUI-41,Supporting 1588v2)
                virent8090DEVCX6DL2XEEG1A(538013),    -- for CX600-DO, CX6DL2XEEG1A,2-Port 10GBase LAN/WAN-XFP+20-Port 100/1000Base-X-SFP Integrated Line Processing Unit (ISUI-41,Supporting 1588v2)
                virent8090DEVCX6DISUF5010(538014),    -- Flexible Card Integrated Service Unit(ISUF-50,4 sub-slots)
                virent8090DEVCX6D00L4XX10(538015),    -- for V600R005C00 CX600, CX6D00L4XX10,4-Port 10GBase LAN/WAN-XFP Integrated Integrated Service Unit (ISUI-41)
                virent8090DEVCX6D00EMGF10(538016),    -- for V600R005C00 CX600, CX6D00EMGF10,48-Port 100/1000Base-X-SFP Integrated Integrated Service Unit (ISUI-41)
                virent8090DEVCX6DL2XEFG10(538017),    -- for V600R005C00 CX600, CX6DL2XEFG10,2-Port 10GBase LAN/WAN-XFP+24-Port 100/1000Base-X-SFP Integrated Integrated Service Unit (ISUI-41)
                virentCX62DEVCR57MPUH(538018),        -- for CX600-DO Main Processing Unit H(Including 2G Memory )
                virentCX61DEVCR57SFU100D(538019),     -- one piece 5802, X8 100G SFU
                virentCX61DEVCR57SRU100D(538020),     -- one piece 5802, 100G SFU, used with X8 SRUA100A MPU
                virent8090DEVCX6D00MPUK70(538021),    --V8R5 for SBOM,   CX6D00MPUK70, Main Processing Unit K , overseas
    -- from 561152 to 159743 is for 8090 Whole BOARD
 -- 8090:
                virent8090DEVLPU(561152),        -- The whole IO board, include all entities on the slot
                virent8090DEVMPU(561153),        -- Whole MPU Board, include all entities on the slot, virtual entity
                virent8090DEVSRU(561154),        -- Whole SRU Board, include all entities on the slot, virtual entity
                virent8090DEVSFU(561155),        -- Switch Fabric Unit for Full Capacity System, include all entities on the slot,virtual entity
                virent8090DEVSRUSFU(561156),     -- Switch Fabric Unit for Half & Halflow Frame System, include all entities on the slot,virtual entity
                virent8090DEVICU(561157),        -- Whole ICU Board, include all entities on the slot, virtual entity
                virent8090DEVECU(561158),        -- Whole ECU Board, include all entities on the slot, virtual entity


                -- from 561159 to 561999 is for 8090 MPU Whole board
                virent8090DEVCR52SRUA(561159),   -- the old whole board of SRUA saled before V3R7 version in 8090(whithout SBOM information)
                virent8090DEVCR52MPUA(561160),   -- the old whole board of MPUA saled before V3R7 version in 8090(whithout SBOM information)
                virent8090DEVCR52MPUB(561161),   -- the old whole board of MPUB saled before V3R7 version in 8090(whithout SBOM information)
                virent8090DEVCR55MPUD(561162),   -- the old whole board of CR55MPUD saled before V3R7 version in 8090(whithout SBOM information)
                virent8090DEVCR52MPUD(561163),   -- the old whole board of CR52MPUD saled before V3R7 version in 8090(whithout SBOM information)
                virent8090DEVCR52SRUC(561164),   -- the old whole board of SRUC saled before V3R7 version in 8090(whithout SBOM information)
                virent8090DEVCR52MPUC(561165),   -- the old whole board of MPUC saled before V3R7 version in 8090(whithout SBOM information)

                virent8090DEVCR5D0SRUA470(561166),   -- V6R1 for CR5D0SRUA470(SBOM), Switch and Route Processing Unit A4(Including 1*2G Memory and 1*1G CF Card)
                virent8090DEVCR5D0MPUB460(561167),   -- V6R1 for CR5D0MPUB460(SBOM), Main Processing Unit B4(Including 1*2G Memory and 1*1G CF Card)
                virent8090DEVCR5D00MPUG70(561168),   -- V6R2 for CR5D00MPUG70(SBOM), Main Processing Unit G0(Including 1*1G CF Card)

                virent8090DEVCR57SRU100A(561169),     -- Two piece 8890, 100G SFU, used with X8 SRUA100A MPU
                virent8090DEVCR5D0SRUA570(561170),     -- Two piece 5802, 200G SFU, used with X8 SRUA200A MPU

                virent8090DEVCR57MPUH(561171),        -- the new whole board of MPUH for V6R5 version in 8090(whithout SBOM information)
                virent8090DEVCR57SRU100D(561172),     -- One piece 5802, 100G SFU, used with X8 SRUA100A MPU
                virent8090DEVCR5D00MPUK70(561173),    -- V8R5 for SBOM,   CR5D00MPUK70, Main Processing Unit K, NE40E
                virent8090DEVCR5D0MPUB570(561174),    -- V8R6C10 for CR5D0MPUB570(SBOM), Main Processing Unit B5

                -- from 562000 to 562999 is for 8090 SFU Whole board
                virent8090DEVCR52SFUA(562000),       -- the old whole board of SFUA saled before V3R7 version in 8090(whithout SBOM information)
                virent8090DEVCR52SFUC(562001),       -- the old whole board of SFUC saled before V3R7 version in 8090(whithout SBOM information)
                virent8090DEVCR52SFUD(562002),       -- the old whole board of SFUD saled before V3R7 version in 8090(whithout SBOM information)
                virent8090DEVCR52SFUF(562003),       -- the old whole board of SFUF saled before V3R7 version in 8090(whithout SBOM information)
                virent8090DEVCR52SFUG(562004),       -- the old whole board of SFUG saled before V3R7 version in 8090(whithout SBOM information)
                virent8090DEVCR52SFUI(562005),       -- the old whole board of SFUI saled before V3R7 version in 8090(whithout SBOM information)
                virent8090DEVCR52K-SFEA(562006),     -- V8R5 for CR52K-SFEA(SBOM), Switch Fabric Extended Unit A
                virent8090DEVCR52SFEB(562007),       -- the old whole board of SFEB saled before V3R7 version in 8090(whithout SBOM information)
                virent8090DEVCR57SFU40A(562008),     -- the old whole board of SFU40A saled before V3R7 version in 8090(whithout SBOM information)
                virent8090DEVCR57SFU40B(562009),     -- the old whole board of SFU40B saled before V3R7 version in 8090(whithout SBOM information)

                virent8090DEVCR5DSFUI407B(562010),     -- V6R1 for CR5DSFUI407B(SBOM), 40Gbps Switch Fabric Unit B
                virent8090DEVCR5DSFUI407C(562011),     -- V6R1 for CR5DSFUI407C(SBOM), 40Gbps Switch Fabric Unit C
                virent8090DEVCR5DSFUG40GBPS(562012),   -- V6R1 for CR52-SFUG-40Gbps(SBOM), Switch Fabric Unit G

                virent8090DEVCR57SFU100C(562013),     -- Two piece 8890, X8 100G SFU
                virent8090DEVCR57SFU200B(562014),     -- Two piece 5802, X16 100G-200G SFU
                virent8090DEVCR57SFU200C(562015),     -- Two piece 5802, X8 100G-200G SFU
                virent8090DEVCR57SFU100D(562016),     -- One piece 5802, X8 100G SFU
                virent8090DEVCR5DSFUFA06C(562017),    -- V8R5 for CR5DSFUFA06C(SBOM), 100G Switch Fabric Unit B(SFUF-100-C)
                virent8090DEVCR5DSFUIK06A(562018),    -- V8R5 for CR5DSFUIK06A(SBOM), 400G Switch Fabric Unit A for Single Chassis(SFUI-400-A)
                virent8090DEVCR55C-ECUA(562019),      -- V8R5 for CR55C-ECUA(SBOM), Cluster Electric Cross Unit A

                virent8090DEVCR5DSFU0K06B(562021),    -- V8R5 for CR5DSFU0K06B(SBOM), NE5000E-X16 400G CLC Switch Fabric Unit B for Single Chassis (SFU-400-B)
                -- from 563000 to 564499 is for 8090 LPU Whole board
                virent8090DEVLPUA(563000),       -- the old whole board of LPUA saled before V3R7 version in 8090(whithout SBOM information)
                virent8090DEVLPUB(563001),       -- the old whole board of LPUB saled before V3R7 version in 8090(whithout SBOM information)
                virent8090DEVLPUC(563002),       -- the old whole board of LPUC saled before V3R7 version in 8090(whithout SBOM information)
                virent8090DEVLPUE(563003),       -- the old whole board of LPUE saled before V3R7 version in 8090(whithout SBOM information)
                virent8090DEVLPUG(563004),       -- the old whole board of LPUG saled before V3R7 version in 8090(whithout SBOM information)
                virent8090DEVLPUH(563005),       -- the old whole board of LPUH saled before V3R7 version in 8090(whithout SBOM information)
                virent8090DEVLPUI(563006),       -- the old whole board of LPUI saled before V3R7 version in 8090(whithout SBOM information)
                virent8090DEVLPUM(563007),       -- the old whole board of LPUM saled before V3R7 version in 8090(whithout SBOM information)
                virent8090DEVLPUF10(563008),     -- the old whole board of LPUF10 saled before V3R7 version in 8090(whithout SBOM information)
                virent8090DEVLPUK0(563009),     -- the old whole board of LPUK0(03030GQU) saled before V3R7 version in 8090(whithout SBOM information)
                virent8090DEVLPUK1(563010),     -- the old whole board of LPUK1(03030HPS) saled before V3R7 version in 8090(whithout SBOM information)
                virent8090DEVLPUK2(563011),     -- the old whole board of LPUK2(03030HVN) saled before V3R7 version in 8090(whithout SBOM information)
                virent8090DEVLPUK3(563012),     -- the old whole board of LPUK3(03030HYQ) saled before V3R7 version in 8090(whithout SBOM information)
                virent8090DEVLPUKD0(563013),     -- the old whole board of LPUKD0(03030KJY) saled before V3R7 version in 8090(whithout SBOM information)
                virent8090DEVLPUKD1(563014),     -- the old whole board of LPUKD1(03030KKB) saled before V3R7 version in 8090(whithout SBOM information)
                virent8090DEVLPUK21(563015),     -- the old whole board of LPUK21(03030KKU) saled before V3R7 version in 8090(whithout SBOM information)
                virent8090DEVLPUK31(563016),     -- the old whole board of LPUK31(03030KKV) saled before V3R7 version in 8090(whithout SBOM information)
                virent8090DEVLPUF40(563017),     -- the old whole board of LPUF40 saled before V3R7 version in 8090(whithout SBOM information)
                virent8090DEVTSUA(563018),       -- the old whole board of TSUA saled before V3R7 version in 8090(whithout SBOM information)
                virent8090DEVTSUG(563019),       -- the old whole board of TSUG saled before V3R7 version in 8090(whithout SBOM information)
                virent8090DEVTSUF10(563020),     -- the old whole board of TSUF10 saled before V3R7 version in 8090(whithout SBOM information)
                virent8090DEVLPUKB(563021),      -- the old whole board of LPUKB saled before V3R7 version in 8090(whithout SBOM information)
                virent8090DEVSPUF10(563022),     -- the old whole board of SPUF10 saled before V3R7 version in 8090(whithout SBOM information)
                virent8090DEVRNRSPU(563023),     -- the old whole board of RNRSPU saled before V3R7 version in 8090(whithout SBOM information)
                virent8090DEVRNRLPUB(563024),    -- the old whole board of RNRLPUB saled before V3R7 version in 8090(whithout SBOM information)
                virent8090DEVRNRLPUD(563025),    -- the old whole board of RNRLPUD saled before V3R7 version in 8090(whithout SBOM information)
                virent8090DEVRNRLPUF(563026),    -- the old whole board of RNRLPUF saled before V3R7 version in 8090(whithout SBOM information)

                virent8090DEVCR5MLPUF402A(563027),    -- V6R1 for CR5MLPUF402A(SBOM),Flexible Card Line Processing Unit(LPUF-40,2 sub-slots) A (L3VPN, MVPN, IPv6 Enhanced)
                virent8090DEVCR5MLPUF402B(563028),    -- V6R1 for CR5MLPUF402B(SBOM),Flexible Card Line Processing Unit(LPUF-40,2 sub-slots) B
                virent8090DEVCR5MVSUF1010(563029),     -- V6R2 for CR5MVSUF1010(SBOM),Flexible Card Versatile Service Unit 10(VSUF-10) (WP21ESPUd board)
                virent8090DEVCR5MVSUI201A(563030),     -- V6R2 for CR5MVSUI201A(SBOM),Integrated Versatile Service Unit 20 A(VSUI-20-A)
                virent8090DEVCR5DNPUI2070(563031),     -- V6R2 for CR5DNPUI2070(SBOM),Network Processing Unit Integrated with 2-Port 10GBase LAN/WAN-XFP(NPUI-20-A)

                virent8090DEVCR57LPUF41A(563032),     -- LPUF41A 40G LPU,SD58X2 Solution ,MIPS CPU
                virent8090DEVCR57LPUF101A(563033),    -- Double LPUF41A, 100G LPU
                --for V6R3 LPUF41A & LPUF101A packing boards 2011-01-15
                virent8090DEVCR57L8XXB0(563034),      -- LPUI-41,8*10GBase LAN/WAN-XFP(CR57LPUF41A+2*CR57L4XX)
                virent8090DEVCR57L4XXB0(563035),      -- LPUI-41,4*10GBase LAN/WAN-XFP(CR57LPUF41A+2*CR52L2XXN)
                virent8090DEVCR57EMGFB0(563036),      -- LPUI-41,48*FE/GE-SFP(CR57LPUF41A+2*CR57EFGF)
                virent8090DEVCR57L2XEFGB0(563037),    -- LPUI-41,2*10GBase LAN/WAN-XFP-24*FE/GE-SFP(CR57LPUF41A+CR52L2XXN+CR57EFGF)
                virent8090DEVCR57L4XXC0(563038),      -- LPUI-41,4*10GBase LAN/WAN-XFP-1588V2(CR57LPUF41A+2*CR52L2XXNB)
                virent8090DEVCR57EKGFC0(563039),      -- LPUI-41,40*FE/GE-SFP-1588V2(CR57LPUF41A+2*CR57EEGFB)
                virent8090DEVCR57L2XEEGC0(563040),    -- LPUI-41,2*10GBase LAN/WAN-XFP-20*FE/GE-SFP-1588V2(CR57LPUF41A+CR52L2XXNB+CR57EEGFB)
                virent8090DEVCR57L8XXB1(563041),      -- LPUS-41,8*10GBase LAN/WAN-XFP(CR57LPUF41A+2*CR57L4XX)
                virent8090DEVCR57L4XXB1(563042),      -- LPUS-41,4*10GBase LAN/WAN-XFP(CR57LPUF41A+2*CR52L2XXN)
                virent8090DEVCR57EMGFB1(563043),      -- LPUS-41,48*FE/GE-SFP(CR57LPUF41A+2*CR57EFGF)
                virent8090DEVCR57LAXXB0(563044),      -- LPUI-100,10*10GBase LAN/WAN-XFP-1588V2(CR57LPUF101A+2*CR56L5XX)
                virent8090DEVCR57EDXFB0(563045),      -- LPUI-100,16*10GBase LAN-SFP+(CR57LPUF101A+4*CR56E4XF)

                --end for V6R3 LPUF41A & LPUF101A packing boards 2011-01-15
                virent8090DEVCR52LPUF21E(563046),   -- V6R3C05 for CR52LPUF21E(SBOM),Flexible Card Line Processing Unit(LPUF-21,2 sub-slots) E
                virent8090DEVCR52LPUF40E(563047),   -- V6R3C05 for CR52LPUF40E(SBOM),Flexible Card Line Processing Unit(LPUF-40,2 sub-slots) E
                virent8090DEVCR57LAXXB1(563048),   -- V6R3C05 for CR57LAXXB1(SBOM),10-Port 10GBase LAN/WAN-XFP Line Processing Unit S(LPUS-100)
                virent8090DEVCR57EDXFB1(563049),   -- V6R3C05 for CR57EDXFB1(SBOM),16-Port 10GBase LAN-SFP+ Line Processing Unit S(LPUS-100)
                virent8090DEVCR57E1NCA1(563050),   -- V6R3C05 for CR57EDXFB1(SBOM),16-Port 10GBase LAN-SFP+ Line Processing Unit S(LPUS-100)
                virent8090DEVCR57L2XEFGB1(563051),   -- V6R3C05 for CR57L2XEFGB1(SBOM),2-Port 10GBase LAN/WAN-XFP+24-Port 100/1000Base-X-SFP Line Processing Unit S(LPUS-41)
                virent8090DEVCR5DVSUI201A(563052),   -- V6R3C05 for CR5DVSUI201A(SBOM),Integrated Versatile Service Unit 20 A(VSUI-20-A)
                virent8090DEVCR53LPUF50(563053),      -- LPUF50 40G LPU,SD5880 Solution ,MIPS CPU
                virent8090DEVCR5DLPUF5070(563054),    -- Flexible Card Line Processing Unit(LPUF-50,4 sub-slots)

                virent8090DEVCR5D00EKGE20(563055),    -- V6R1 for CR5D00EKGE20(SBOM), 40-Port 10/100/1000Base-RJ45 Switch Line Processing Unit(LPUS-20), V600R001 zhi hou an cheng pin ban bao zhuang, xu yao zai xin de ti xi shang bao zhuang yi ci
                virent8090DEVCR5D00EKGF21(563056),    -- V6R1 for CR5D00EKGF21(SBOM), 40-Port 100/1000Base-X-SFP Switch Line Processing Unit(LPUS-20), V600R001 zhi hou an cheng pin ban bao zhuang, xu yao zai xin de ti xi shang bao zhuang yi ci
                virent8090DEVCR5D00L4XX21(563057),    -- V6R1 for CR5D00L4XX21(SBOM), 4-Port 10GBase LAN/WAN-XFP Switch Line Processing Unit(LPUS-20), V600R001 zhi hou an cheng pin ban bao zhuang, xu yao zai xin de ti xi shang bao zhuang yi ci
                virent8090DEVCR5D00L4XX20(563058),    -- V6R1 for CR5D00L4XX20(SBOM), 4-Port 10GBase LAN/WAN-XFP Integrated Line Processing Unit (LPUI-40), V600R001 zhi hou an cheng pin ban bao zhuang, xu yao zai xin de ti xi shang bao zhuang yi ci
                virent8090DEVCR5D00EKGF20(563059),    -- V6R1 for CR5D00EKGF20(SBOM), 40-Port 100/1000Base-X-SFP Integrated Line Processing Unit(LPUI-40), V600R001 zhi hou an cheng pin ban bao zhuang, xu yao zai xin de ti xi shang bao zhuang yi ci

                --for V6R5C00 LPU packing boards 2011-09-23
                virent8090DEVCR57LPUF101E0(563100),   -- V6R5C00 for CR57LPUF101E0(SBOM),Flexible Card Line Processing Unit(LPUF-100,4 sub-slots) E

                --for V6R5C00 & JICAI packing boards 2011-12-27
                virent8090DEVCX6DSFUIA07B(563103),    -- V6R5C00 for CX6DSFUIA07B(SBOM),100Gbps Switch Fabric Unit B(SFUI-100-B)
                virent8090DEVCX6D0SRUA611(563104),    -- V6R5C00 for CX6D0SRUA611(SBOM),Switch and Route Processing Unit A6(Including 1*2G Memory and 1*1G CF Card)
                virent8090DEVCX6DSFUIA07C(563105),    -- V6R5C00 for CX6DSFUIA07C(SBOM),100Gbps Switch Fabric Unit C(SFUI-100-C)
                virent8090DEVCX6DISUF401B(563106),    -- V6R5C00 for CX6DISUF401B(SBOM),Flexible Card Integrated Service Unit(ISUF-40-B,two sub-slots)
                virent8090DEVCX6D0L4XXA1B(563107),    -- V6R5C00 for CX6D0L4XXA1B(SBOM),4-Port 10GBase LAN/WAN-XFP Integrated Integrated Service Unit (ISUI-41-B,Supporting 1588v2)
                virent8090DEVCX6D0EKGFA1B(563108),    -- V6R5C00 for CX6D0EKGFA1B(SBOM),40-Port 100/1000Base-X-SFP Integrated Integrated Service Unit (ISUI-41-B,Supporting 1588v2)
                virent8090DEVCX6DL2XEEG1B(563109),    -- V6R5C00 for CX6DL2XEEG1B(SBOM),2-Port 10GBase LAN/WAN-XFP+20-Port 100/1000Base-X-SFP Integrated Integrated Service Unit (ISUI-41-B,Supporting 1588v2)
                virent8090DEVCX6D00EMGF1B(563110),    -- V6R5C00 for CX6D00EMGF1B(SBOM),48-Port 100/1000Base-X-SFP Integrated Integrated Service Unit (ISUI-41-B)
                virent8090DEVCX6DL2XEFG1B(563111),    -- V6R5C00 for CX6DL2XEFG1B(SBOM),2-Port 10GBase LAN/WAN-XFP+24-Port 100/1000Base-X-SFP Integrated Integrated Service Unit (ISUI-41-B)
                virent8090DEVCX6DISUFA010(563112),    -- V6R5C00 for CX6DISUFA010(SBOM),Flexible Card Line Processing Unit(ISUF-100,4 sub-slots)
                virent8090DEVCX6D0LAXXA10(563113),    -- V6R5C00 for CX6D0LAXXA10(SBOM),10-Port 10GBase LAN/WAN-XFP Integrated Integrated Service Unit (ISUI-100,Supporting 1588v2)
                virent8090DEVCX6D00L4XX1B(563114),    -- V6R5C00 for CX6D00L4XX1B(SBOM),4-Port 10GBase LAN/WAN-XFP Integrated Integrated Service Unit (ISUI-41-B)

                virent8090DEVCR5DNPU50E70(563115),    -- V8R5 for SBOM ,CR5DNPU50E70, Network Processing Unit(NPU-50-E) in -country
                virent8090DEVCR5D0NPU5070(563116),    -- V8R5 for SBOM ,CR5D0NPU5070, Network Processing Unit (NPU-50), NE40E
                virent8090DEVCR5DNPU12070(563117),    -- V8R5 for SBOM ,CR5D0NPU12070, Network Processing Unit (NPU-120), NE40E
                virent8090DEVCR5DNPU1207E(563118),    -- V8R5 for SBOM ,CR5D0NPU1207E, Network Processing Unit (NPU-120-E), NE40E

                -- from 564500 to 159743 is for 8090 OTHER board
                virent8090DEVFCARD(564500),          -- the old whole board of Flex-card saled before V3R7 version in 8090(whithout SBOM information)
                virent8090DEVCR5M000CMU60(564501),   -- V6R1 for CR5M000CMU60(SBOM), Centralized Monitor Unit(CMU)
                virent8090DEVCR5M000FBX60(564502),   -- V6R1 for CR5M000FBX60(SBOM), Fan Box
                virent8090DEVCR5M000PEM60(564503),   -- V6R1 for CR5M000PEM60(SBOM), Power Filter Unit(PFU)
                -- V8R5 CX600 X1/X2   NE40E
                virent8090DEVCR5D00L2XF70(564519),   -- CR5D00L2XF70, 2-Port 10GBase LAN/WAN-SFP+  Physical Interface Card(PIC)
                virent8090DEVCR5D00E8GF71(564520),   -- CR5D00E8GF71, 8-Port 100/1000Base-X-SFP  Physical Interface Card(PIC)
                virent8090DEVCR5D00E8GE70(564521),   -- CR5D00E8GE70,  8-Port 10/100/1000Base-RJ45 Physical Interface Card(PIC)

                -- from 564610 to 564660 is for V6R6C00 LPU packing boards 2012-03-23
                -- for NE40E
                virent8090DEV0305CR5DLPUF5070(564610),   -- V6R6C00 for CR5DLPUF5070(SBOM),Flexible Card Line Processing Unit(LPUF-50,four slots)
                virent8090DEVCR5DLPUF5170(564611),   -- V6R6C00 for CR5DLPUF5170(SBOM),Flexible Card Line Processing Unit(LPUF-51,2 sub-slots)
                virent8090DEVCR5DLPUF517B(564612),   -- V6R6C00 for CR5DLPUF517B(SBOM),Flexible Card Line Processing Unit(LPUF-51,2 sub-slots) B
                virent8090DEVCR5D0L5XFA71(564614),   -- V6R6C00 for CR5D0L5XFA71(SBOM),5-Port 10GBase LAN/WAN-SFP+ Integrated Line Processing Unit (LPUI-51)
                virent8090DEVCR5D0L5XFA7B(564615),   -- V6R6C00 for CR5D0L5XFA7B(SBOM),5-Port 10GBase LAN/WAN-SFP+ Integrated Line Processing Unit B(LPUI-51-B)
                virent8090DEVCR5D00L5XF72(564616),   -- V6R6C00 for CR5D00L5XF72(SBOM),5-Port 10GBase LAN/WAN-SFP+ Line Processing Unit S(LPUS-51)
                virent8090DEVCR5D0L4XFA70(564617),   -- V6R6C00 for CR5D0L4XFA70(SBOM),4-Port 10GBase LAN/WAN-SFP+ Integrated Line Processing Unit (LPUI-51)
                virent8090DEVCR5D0L4XFA7B(564618),   -- V6R6C00 for CR5D0L4XFA7B(SBOM),4-Port 10GBase LAN/WAN-SFP+ Integrated Line Processing Unit B(LPUI-51-B)
                virent8090DEVCR5D00L4XF71(564619),   -- V6R6C00 for CR5D00L4XF71(SBOM),4-Port 10GBase LAN/WAN-SFP+ Line Processing Unit S(LPUS-51)
                virent8090DEVCR5D0EMGFA70(564620),   -- V6R6C00 for CR5D0EMGFA70(SBOM),48-Port 100/1000Base-X-SFP Integrated Line Processing Unit (LPUI-51)
                virent8090DEVCR5D0EMGFA7B(564621),   -- V6R6C00 for CR5D0EMGFA7B(SBOM),48-Port 100/1000Base-X-SFP Integrated Line Processing Unit B(LPUI-51-B)
                virent8090DEVCR5D00EMGF73(564622),   -- V6R6C00 for CR5D00EMGF73(SBOM),48-Port 100/1000Base-X-SFP Line Processing Unit S(LPUS-51)
                virent8090DEVCR5DL2XEFG7A(564623),   -- V6R6C00 for CR5DL2XEFG7A(SBOM),2-Port 10GBase LAN/WAN-SFP+ + 24-Port 100/1000Base-X-SFP Integrated Line Processing Unit (LPUI-51)
                virent8090DEVCR5DL2XEFG7B(564624),   -- V6R6C00 for CR5DL2XEFG7B(SBOM),2-Port 10GBase LAN/WAN-SFP+ + 24-Port 100/1000Base-X-SFP Integrated Line Processing Unit B(LPUI-51-B)
                virent8090DEVCR5DL2XEFG72(564625),   -- V6R6C00 for CR5DL2XEFG72(SBOM),2-Port 10GBase LAN/WAN-SFP+ + 24-Port 100/1000Base-X-SFP Line Processing Unit S(LPUS-51)
                virent8090DEVCR5D0L5XFA7L(564626),   -- V6R6C00 for CR5D0L5XFA7L(SBOM),5-Port 10GBase LAN/WAN-SFP+ Integrated Line Processing Unit L(LPUI-51-L)
                virent8090DEVCR5DL2XEIG7L(564627),   -- V6R6C00 for CR5DL2XEIG7L(SBOM),2-Port 10GBase LAN/WAN-SFP+ + 32-Port 100/1000Base-X-SFP Integrated Line Processing Unit L(LPUI-51-L)
                virent8090DEVCR5D0EMGFA7L(564628),   -- V6R6C00 for CR5D0EMGFA7L(SBOM),48-Port 100/1000Base-X-SFP Integrated Line Processing Unit L(LPUI-51-L)
                virent8090DEVCR5D0EFGFA73(564629),   -- V6R6C00 for CR5D0EFGFA73(SBOM),24-Port 100/1000Base-X-SFP Integrated Line Processing Unit L(LPUI-21-L)
                virent8090DEVCR5DL1XEDG70(564630),   -- V6R6C00 for CR5DL1XEDG70(SBOM),1-Port 10GBase LAN/WAN-SFP+ + 16-Port 100/1000Base-X-SFP Integrated Line Processing Unit L(LPUI-21-L)
                virent8090DEVCR5DLPUFA071(564632),   -- V6R6C00 for CR5DLPUFA071(SBOM),Flexible Card Line Processing Unit(LPUF-101,4 sub-slots)
                virent8090DEVCR5DLPUFA07B(564633),   -- V6R6C00 for CR5DLPUFA07B(SBOM),Flexible Card Line Processing Unit(LPUF-101,4 sub-slots) B
                virent8090DEVCR5D00E2MC70(564635),   -- V6R6C00 for CR5D00E2MC70(SBOM),2-Port 40GBase LAN-CFP Integrated Line Processing Unit (LPUI-101)
                virent8090DEVCR5D00E2MC7B(564636),   -- V6R6C00 for CR5D00E2MC7B(SBOM),2-Port 40GBase LAN-CFP Integrated Line Processing Unit B(LPUI-101-B)
                virent8090DEVCR5D00E2MC71(564637),   -- V6R6C00 for CR5D00E2MC71(SBOM),2-Port 40GBase LAN-CFP Line Processing Unit S(LPUS-101)
                virent8090DEVCR5D0LAXFA71(564638),   -- V6R6C00 for CR5D0LAXFA71(SBOM),10-Port 10GBase LAN/WAN-SFP+ Integrated Line Processing Unit (LPUI-101)
                virent8090DEVCR5D0LAXFA7B(564639),   -- V6R6C00 for CR5D0LAXFA7B(SBOM),10-Port 10GBase LAN/WAN-SFP+ Integrated Line Processing Unit B(LPUI-101-B)
                virent8090DEVCR5D0LAXFA72(564640),   -- V6R6C00 for CR5D0LAXFA72(SBOM),10-Port 10GBase LAN/WAN-SFP+ Integrated Line Processing Unit (LPUI-101)
                virent8090DEVCR5D00E1NC72(564641),   -- V6R6C00 for CR5D00E1NC72(SBOM),1-Port 100GBase-CFP Integrated Line Processing Unit (LPUI-101)
                virent8090DEVCR5D00E1NC73(564642),   -- V6R6C00 for CR5D00E1NC73(SBOM),1-Port 100GBase-CFP Line Processing Unit S(LPUS-101)

                -- for CX600 local
                virent8090DEVLOCALCX6DISUF5010(564643),   -- V6R6C00 for CX6DISUF5010(SBOM),Flexible Card Integrated Service Unit(ISUF-50,four sub-slots)
                virent8090DEVCX6DISUF5110(564644),   -- V6R6C00 for CX6DISUF5110(SBOM),Flexible Card Integrated Service Unit(ISUF-51,two sub-slots)
                virent8090DEVCX6DISUF511B(564645),   -- V6R6C00 for CX6DISUF511B(SBOM),Flexible Card Integrated Service Unit(ISUF-51-B,two sub-slots)
                virent8090DEVCX6D0L5XFA11(564646),   -- V6R6C00 for CX6D0L5XFA11(SBOM),5-Port 10GBase LAN/WAN-SFP+ Integrated Integrated Service Unit (ISUI-51,Supporting 1588v2,4 port 10GE is enabled by default)
                virent8090DEVCX6D0L5XFA1B(564647),   -- V6R6C00 for CX6D0L5XFA1B(SBOM),5-Port 10GBase LAN/WAN-SFP+ Integrated Integrated Service Unit B(ISUI-51-B,Supporting 1588v2,4 port 10GE is enabled by default)
                virent8090DEVCX6DL4XEBG1A(564648),   -- V6R6C00 for CX6DL4XEBG1A(SBOM),4-Port 10GBase LAN/WAN-SFP++12-Port 100/1000Base-X-SFP Integrated Integrated Service Unit (ISUI-51,Supporting 1588v2)
                virent8090DEVCX6DL4XEBG1B(564649),   -- V6R6C00 for CX6DL4XEBG1B(SBOM),4-Port 10GBase LAN/WAN-SFP++12-Port 100/1000Base-X-SFP Integrated Integrated Service Unit B(ISUI-51-B,Supporting 1588v2)
                virent8090DEVCX6DL2XEIG1A(564650),   -- V6R6C00 for CX6DL2XEIG1A(SBOM),2-Port 10GBase LAN/WAN-SFP++32-Port 100/1000Base-X-SFP Integrated Integrated Service Unit (ISUI-51,Supporting 1588v2,2 port 10GE + 20 port FE/GE are enabled by default)
                virent8090DEVCX6DL2XEIG1B(564651),   -- V6R6C00 for CX6DL2XEIG1B(SBOM),2-Port 10GBase LAN/WAN-SFP++32-Port 100/1000Base-X-SFP Integrated Integrated Service Unit B(ISUI-51-B,Supporting 1588v2,2 port 10GE + 20 port GE are enabled by default)
                virent8090DEVCX6D0EMGFA10(564652),   -- V6R6C00 for CX6D0EMGFA10(SBOM),48-Port 100/1000Base-X-SFP Integrated Integrated Service Unit (ISUI-51,Supporting 1588v2)
                virent8090DEVCX6D0EMGFA1B(564653),   -- V6R6C00 for CX6D0EMGFA1B(SBOM),48-Port 100/1000Base-X-SFP Integrated Integrated Service Unit B(ISUI-51-B,Supporting 1588v2)
                virent8090DEVCX6D0EFGFA12(564654),   -- V6R6C00 for CX6D0EFGFA12(SBOM),24-Port 100/1000Base-X-SFP Integrated Integrated Service Unit (ISUI-21,Supporting 1588v2)
                virent8090DEVCX6DL1XEDG1A(564655),   -- V6R6C00 for CX6DL1XEDG1A(SBOM),1-Port 10GBase LAN/WAN-SFP++16-Port 100/1000Base-X-SFP Integrated Integrated Service Unit (ISUI-21,Supporting 1588v2)
                virent8090DEVLOCALCX6D0L4XXA1B(564656),   -- V6R6C00 for CX6D0L4XXA1B(SBOM),4-Port 10GBase LAN/WAN-XFP Integrated Integrated Service Unit (ISUI-41-B,Supporting 1588v2)
                virent8090DEVLOCALCX6DL2XEEG1B(564657),   -- V6R6C00 for CX6DL2XEEG1B(SBOM),2-Port 10GBase LAN/WAN-XFP+20-Port 100/1000Base-X-SFP Integrated Integrated Service Unit (ISUI-41-B,Supporting 1588v2)
                virent8090DEVLOCALCX6D0EKGFA1B(564658),   -- V6R6C00 for CX6D0EKGFA1B(SBOM),40-Port 100/1000Base-X-SFP Integrated Integrated Service Unit (ISUI-41-B,Supporting 1588v2)
                virent8090DEVCX6DISUFA110(564659),   -- V6R6C00 for CX6DISUFA110(SBOM),Flexible Card Line Processing Unit(ISUF-101,four sub-slots)
                virent8090DEVCX6D0LAXFA11(564660),   -- V6R6C00 for CX6D0LAXFA11(SBOM),10-Port 10GBase LAN WAN-SFP+ Integrated Integrated Service Unit (ISUI-101,Supporting 1588v2)

                virent8090DEVCR5D00SNCA00(564606),   --For V600R008C20 VSUF NE SNC Atomic Router
                virent8090DEVVSUF80(564607),    --SPU2.0 Board(80)
                virent8090DEVVSUF160(564608),   --SPU2.0 Board(160)
                virent8090DEVVSUF40(564609),   -- for V600R007C00 CR5DVSUF4010(SBOM), Flexible Card Versatile Service Unit 40(VSUF-40)
                virent8090DEVVSUI160(564810),  -- for V600R009C00 CR5DVSUID010(SBOM), Integrated Versatile Service Unit(VSUI-160-E)

				-- V800R009C10
                virent8090DEVCR9D00EDNB8P(562070),  --16-Port 100GBase-QSFP28 Integrated Line Process Unit(NE9000 LPUI-2T-PC)
                virent8090DEVCR9D00E8NC8P(562071),  --8-Port 100GBase-CFP2 Integrated Line Process Unit(LPUI-1T-PC)
                virent8090DEVCR9D00D8NC8P(562072),  --8-Port 100GBase-CFP DWDM Integrated Line Process Unit(LPUI-1T-PC)
	            virent8090DEVCR9D00EPXF8P(562073),  --60-Port 10GBase LAN/WAN-SFP+ Integrated Line Process Unit(LPUI-1T-PC)
                virent8090DEVCR9D00EPXF8L(562077),   -- v8r10c10 NE9000 CR58LPU1TCB for CR9D00EPXF8L(SBOM), 60-Port 10GBase LAN/WAN-SFP+ Integrated Line Process Unit L(LPUI-1T-L)
                virent8090DEVCR5DLPUFT261(562089),   -- v8r11c00 NE5000E-20 CR5DLPUFT261(SBOM),2T Flexible Card Line Processing Unit(NE5000E LPUF-2T-A,2 sub-slots)
                virent8090DEVCR5D00LKXF6P(562074),  --40-Port 10GBase LAN/WAN-SFP+ Integrated Line Process Unit (NE5000E LPUI-400-PC)
                virent8090DEVCR5D00EDNB6P(562075),  --16-Port 100GBase-QSFP28 Integrated Line Process Unit (NE5000E LPUI-2T-PC)
                virent8090DEVCR5D00EDNB61(562083),   -- 16-Port 100GBase-QSFP28 Integrated Line Process Unit B (NE5000E LPUI-2T-B)
                virent8090DEVCR5DSFUIT28A(562084),  --2T Switch Fabric Unit for Single Chassis (SFU-2T-A)
                 virent8090DEVCR5D00EDNB80(562086),  --16-Port 100GBase-QSFP28 Integrated Line Process Unit B (NE40E LPUI-2T)
                virent8090DEVCR5DE3NL5X60(562087),  --3-Port 100GBase-QSFP28 + 5-Port 10GBase LAN/WAN SFP+ Integrated Line Process Unit (NE5000E LPUI-1T)

                -- for V800R003C00  NE5000E Manufactured Board
                virent8090DEVCR5D00EKGF60(564661),   -- 40-Port 1000Base-X-SFP Line Processing Unit (SBOM)
                virent8090DEVCR5D00P4XX60(564662),   -- 4-Port OC-192c/STM-64c POS-XFP Line Processing Unit E (SBOM)
                virent8090DEVCR5D00P8UF60(564663),   -- 8-Port OC-48c/STM-16c POS-SFP Line Processing Unit E (SBOM)
                virent8090DEVCR5D00E4XX60(564664),   -- 4-Port 10GBase LAN-XFP Line Processing Unit E (SBOM)
                virent8090DEVCR5D00W4XX60(564665),   -- 4-Port 10GBase WAN-XFP Line Processing Unit E (SBOM)
                virent8090DEVCR5D00LEXF60(564666),   -- 20 port 10GBase LAN/WAN-SFP+ Line Processing Unit(NE5000E LPUI-200) (SBOM)
                virent8090DEVCR5D00E2NC60(564667),   -- 2-Port 100GBase-CFP Integrated Line Process Unit(NE5000E LPUI-200) (SBOM)
                virent8090DEVCR5DE1NLAX60(564668),   -- 1 port 100GBase&10 port 10GBase LAN/WAN-SFP+ Line Processing Unit(NE5000E LPUI-200) (SBOM)
                virent8090DEVCR5D00E1NC60(564669),   -- 1-Port 100GBase-CFP Integrated Line Process Unit(NE5000E LPUI-100) (SBOM)
                virent8090DEVCR5D00LAXX60(564670),   -- 10-Port 10GBase LAN/WAN-XFP Integrated Line Processing Unit (NE5000E LPUI-100) (SBOM)
                virent8090DEVCR5DLPUFA060(564671),   -- 100G Flexible Card Line Processing Unit(NE5000E LPUF-100,4 sub-slots) (SBOM)
                virent8090DEVCR5DSFUIA050(564672),   -- 100G Cluster Central Switch Fabric Unit A(SFUI-100-A) (SBOM)
                virent8090DEVCR5DSFEBA06B(564673),   -- Switch Fabric Extended Unit B(100G) (SBOM)
                virent8090DEVCR5D0MPUA450(564674),   -- Central Main Processing Unit A4 (SBOM)
                virent8090DEVCR5DECUFA050(564675),   -- 100G Cluster Electric Cross Unit A(ECU-100-A) (SBOM)
                virent8090DEVCR5DSFUFA06B(564676),   -- 100G Switch Fabric Unit B(SFUF-100-B) (SBOM)
                virent8090DEVCR5D0MPUB461(564677),   -- NetEngine5000E Main Processing Unit B4 (SBOM)
                virent8090DEVCR5D0MPUA550(564716),   -- NE5000E Main Processing Unit A5(SBOM)
                virent8090DEVCR5D00ICUB50(564717),   -- NE5000E Internal Communication Unit B(SBOM)
                virent8090DEVCR5DSFUFK050(564718),   -- 400G Cluster Central Switch Fabric Unit A(SFUF-400-A) (SBOM)
                virent8090DEVCR5DSFUIK06B(564719),   -- 400G Switch Fabric Unit B for multi Chassis(SFUI-400-B) (SBOM)
                virent8090DEVCR5DSFUIE060(564678),   -- 200G Switch Fabric Unit B(SFU-200-A) (SBOM)
                virent8090DEVCR5DSFUIT060(562022),   -- 1T Switch Fabric Unit A for Single Chassis
                virent8090DEVCR5D00EFMB60(564888),   -- NetEngine5000E,CR56EFMBA0,1000Gbps Line Processing Unit
                virent8090DEVCR5D00E8NC60(564889),   -- NetEngine5000E,CR56E8NCA0,1000Gbps Line Processing Unit
                virent8090DEVCR5D0SRUB060(562028),   -- NE5000E-X8 1T Switching and Routing Unit
                virent8090DEVCR5D0SRUB061(562029),   -- NE5000E-X8 400G Switching and Routing Unit
                virent8090DEVCR5D0SFUT061(562030),   -- NE5000E-X8 1T Switching Fabric Unit for Single Chassis (SFU-1T)
                virent8090DEVCR5D0SFUK061(562031),   -- NE5000E-X8 400G Switching Fabric Unit for Single Chassis (SFU-400)
                virent8090DEVCR56FRA1TA(562032),   -- NE5000E-X8 1T Switching and Routing Unit
                virent8090DEVCR5DLPUFK062(562033),   -- 400G Flexible Card Line Processing Unit B(NE5000E LPUF-400-B,2 sub-slots)
                virent8090DEVCR5D0MPUA451(562034),   -- NetEngine5000E Cluster-CR55MPUA5
                virent8090DEVCCR5D00ICUA51(562035),   -- NetEngine5000E Cluster-CR55ICUA1
                virent8090DEVCR5DSFUFK051(562036),   -- NetEngine5000E Cluster-CR55SFUF400D
                virent8090DEVCR5D00L4NC60(562037),   -- NE5000E,CR56E4NCC0,4-Port 100GBase-CFP2 Integrated Line Processing Unit (LPUI-400)
                virent8090DEVCR5D00LKXF60(562038),   -- NE5000E,CR56LKXFA0,40-Port 10GBase LAN/WAN-SFP+ Integrated Line Process Unit(NE5000E LPUI-400)
                virent8090DEVCR5DL2NLEX60(562039),   -- NE5000E,CR56E2NLEXF0,2 port 100GBase CFP2 & 20 port 10GBase LAN/WAN-SFP+ Line Processing Unit(NE5000E LPUI-400)
                virent8090DEVCR9D0MPUN180(562040),   -- CR58MPUN10,NE9000-20 Main Processing Unit N1(MPUN1)
                virent8090DEVCR9D00E8NC80(562041),   -- 8-Port 100GBase-CFP2- Integrated Line Process Unit(NE9000 LPUI-1T)
                virent8090DEVCR9D00EFMB80(562042),   -- 24-Port 40GBase-QSFP+ Integrated Line Process Unit (NE9000 LPUI-1T)
                virent8090DEVCR5D0SFUT080(562043),   -- NE9000 1T Switch Fabric Unit for Single Chassis (NE9000 SFUI-1T)
                virent8090DEVCR9D00EPXF80(562044),   -- 60-Port 10GBase LAN/WAN-SFP+ Integrated Line Process Unit (NE9000 LPUI-1T)
                virent8090DEVCR5D00E8NC61(562045),   -- 8-Port 100GBase-CFP4- Integrated Line Process Unit(NE5000E LPUI-1T)
                virent8090DEVCR5DE8NEDX61(562046),   -- 8-Port 100GBase-CFP4 + 16-Port 10GBase-QSFP+ Integrated Line Process Unit (NE5000E LPUI-1T)
                virent8090DEVCR5DSFUIT06E(562047),   -- NE5000E 1T Switch Fabric Unit for Single Chassis
                virent8090DEVCR5DSFUIT26A(562048),   -- NE5000E-X16B 2T CLC Switch Fabric Unit for Single Chassis (SFU-2T-A)
                virent8090DEVCR5D00EDNB60(562049),   -- 16-Port 100GBase-QSFP28 Integrated Line Process Unit (NE5000E LPUI-2T)
                virent8090DEVCR5DEDNLIX60(562050),  -- 16-Port 100GBase-QSFP28 + 32-Port 10GBase-QSFP+ Integrated Line Process Unit (NE5000E LPUI-2T)
                virent8090DEVCR58CMUB(562052),   -- NE9000 Centralized Monitoring Board
                virent8090DEVCCR5D0OFCK051(561415),   -- NetEngine5000E Cluster-CR55OFC400D-400G
                virent8090DEVCR5DSFUFT050(562058),   -- NE50000E V8R9C00 for CR5DSFUFT050(sbom)
                virent8090DEVCR5DSFUIT06H(562059),   -- NE50000E V8R9C00 for CR5DSFUIT06H(sbom)
                virent8090DEVCR5D0MPUA750(562060),   -- NE50000E V8R9C00 for CR5D0MPUA750(sbom)
                virent8090DEVCR5D0MPUB660(562061),   -- NE50000E V8R9C00 for CR5D0MPUB660(sbom)
                virent8090DEVCR5DLPUFT060(562062),   -- NE50000E V8R9C00 for CR5DLPUFT060(sbom)
                virent8090DEVCR9D00D8NC80(562063),   --NE9000 V8R9C00 for CR9D00D8NC80 (sbom)
                virent8090DEVCR5D00E8NB60(562064), -- V8R9C00 for CR5D00E8NB60 CR56LPUI1T(sbom)
                virent8090DEVCR5D0MPUB580(562065),   -- Main Processing Unit B5,CR57MPUB5
                virent8090DEVCR5D00E8NC80(562068),   -- 8-Port 100GBase-CFP4- Integrated Line Process Unit(LPUI-1T),CR57LPU1TF
				virent8090DEVCR57MPUB6(562090),  --Main Processing Unit B6
				virent8090DEVCR57SFU2TE(562091), --2T Switch Fabric Unit for Single Chassis (SFU-2T-A)
				virent8090DEVCR56LPUI1T(562092), --8-Port 100GBase-QSFP28- Integrated Line Process Unit(LPUI-1T) NE40E-X16B
				virent8090DEVCR5DSFUIT250(562093),   
				virent8090DEVCR5DSFUIT26H(562094),  

                virent8090DEVCR5D0OFCT050(561716),   -- NE50000E V8R9C00 for CR5D0OFCT050(sbom)
                -- V8R9C00 NE9000 1T6C
                virent8090DEVCR9DEDNEIXB80(562053),   -- NE9000 LPUI-1T6C CR9DEDNEIXB80
		virent8090DEVCR9DLPUFK080(562054),   -- NE9000 LPUF-400 CR9DLPUFK080
                virent8090DEVCR9D0MPUP180(564905),    -- V8R10C00 for CR9D0MPUP180(SBOM) NE9000-8 Main Processing Unit P1(MPUP1)
                virent8090DEVCR9D0SFUT481(564906),   -- V8R10C00 for CR9D0SFUT481(SBOM) NE9000-8 Switch Fabric Unit for Single Chassis(SFU4T-A)
                -- V6R7 NE&OC CX packing
                virent8090DEVCR5DL2XEFG7E(564679),    -- V6R7C00 for CR5DL2XEFG7E(SBOM),2-Port 10GBase LAN/WAN-SFP+ + 24-Port 100/1000Base-X-SFP Integrated Line Processing Unit E(LPUI-51-E)
                virent8090DEVCR5D0L5XFA7E(564680),    -- V6R7C00 for CR5D0L5XFA7E(SBOM),5-Port 10GBase LAN/WAN-SFP+ Integrated Line Processing Unit E(LPUI-51-E)
                virent8090DEVCR5DLPUFB070(564681),    -- V6R7C00 for CR5DLPUFB070(SBOM),Flexible Card Line Processing Unit(LPUF-120,2 sub-slots)
                virent8090DEVCR5DLPUFB07B(564682),    -- V6R7C00 for CR5DLPUFB07B(SBOM),Flexible Card Line Processing Unit(LPUF-120,2 sub-slots) B
                virent8090DEVCR5D0LBXFA70(564683),    -- V6R7C00 for CR5D0LBXFA70(SBOM),12-Port 10GBase LAN/WAN-SFP+ Integrated Line Processing Unit(LPUI-120)
                virent8090DEVCR5D0E2MCA70(564684),    -- V6R7C00 for CR5D0E2MCA70(SBOM),2-Port 40GBase LAN-CFP Integrated Line Processing Unit(LPUI-120)
                virent8090DEVCR5D00E1NC76(564685),    -- V6R7C00 for CR5D00E1NC76(SBOM),1-Port 100GBase-CFP Integrated Line Processing Unit (LPUI-120)
                virent8090DEVCR5D0LBXFA7B(564686),    -- V6R7C00 for CR5D0LBXFA7B(SBOM),12-Port 10GBase LAN/WAN-SFP+ Integrated Line Processing Unit B(LPUI-120-B)
                virent8090DEVCR5D0E2MCA7B(564687),    -- V6R7C00 for CR5D0E2MCA7B(SBOM),2-Port 40GBase LAN-CFP Integrated Line Processing Unit B(LPUI-120-B)
                virent8090DEVCR5D00E1NC7B(564688),    -- V6R7C00 for CR5D00E1NC7B(SBOM),1-Port 100GBase-CFP Integrated Line Processing Unit (LPUI-120-B)
                virent8090DEVCR5DLPUFB07E(564689),    -- V6R7C00 for CR5DLPUFB07E(SBOM),Flexible Card Line Processing Unit(LPUF-120,2 sub-slots) E
                virent8090DEVCR5D0LAXFA7E(564690),    -- V6R7C00 for CR5D0LAXFA7E(SBOM),10-Port 10GBase LAN/WAN-SFP+ Integrated Line Processing Unit E(LPUI-120-E)
                virent8090DEVCR5DLPUFF07B(564691),    -- V6R7C00 for CR5DLPUFF07B(SBOM),Flexible Card Line Processing Unit(LPUF-240-B, 2 sub-slots)
                virent8090DEVCR5DLPUFF070(564692),    -- V6R7C00 for CR5DLPUFF070(SBOM),Flexible Card Line Processing Unit(LPUF-240, 2 sub-slots)
                virent8090DEVCR5D00E2NC70(564693),    -- V6R7C00 for CR5D00E2NC70(SBOM),2-Port 100GBase-CFP Integrated Line Processing Unit (LPUI-240)
                virent8090DEVCR5D00LFXF70(564694),    -- V6R7C00 for CR5D00LFXF70(SBOM),24-Port 10GBase LAN/WAN-SFP+ Integrated Line Processing Unit (LPUI-240)
                virent8090DEVCR5DE2NLBX70(564695),    -- V6R7C00 for CR5DE2NLBX70(SBOM),1-Port 100GBase-CFP + 12-Port 10GBase LAN/WAN-SFP+ Integrated Line Processing Unit (LPUI-240)
                virent8090DEVCR5D00E2NC73(564696),    -- V6R7C00 for CR5D00E2NC73(SBOM),2-Port 100GBase LAN-CFP Integrated Line Processing Unit B(LPUI-240-B)
                virent8090DEVCR5D00LFXF73(564697),    -- V6R7C00 for CR5D00LFXF73(SBOM),24-Port 10GBase LAN/WAN-SFP+ Integrated Line Processing Unit B(LPUI-240-B)
                virent8090DEVCR5DE2NLBX73(564698),    -- V6R7C00 for CR5DE2NLBX73(SBOM),1-Port 100GBase-CFP + 12-Port 10GBase LAN/WAN-SFP+ Integrated Line Processing Unit B(LPUI-240-B)
                virent8090DEVCR5DLPUFA07J(564699),    -- V6R7C00 for CR5DLPUFA07J(SBOM),Flexible Card Line Processing Unit(LPUF-102,2 sub-slots)
                virent8090DEVCR5DLPUFA27E(564700),    -- V6R7C00 for CR5DLPUFA27E(SBOM),Flexible Card Line Processing Unit(LPUF-102,2 sub-slots) E
                virent8090DEVCR5DLPUF517E(564701),    -- V6R7C00 for CR5DLPUF517E(SBOM),Flexible Card Line Processing Unit(LPUF-51,2 sub-slots) E
                virent8090DEVCR5D0LAXFA7J(564702),    -- V6R7C00 for CR5D0LAXFA7J(SBOM),10-Port 10GBase LAN/WAN-SFP+ Integrated Line Processing Unit (LPUI-102)
                virent8090DEVCR5DLAXFAJ7E(564703),    -- V6R7C00 for CR5DLAXFAJ7E(SBOM),10-Port 10GBase LAN/WAN-SFP+ Integrated Line Processing Unit E(LPUI-102-E)
                -- V6R7 NE&OC CX packing
                -- V6R7 CX60086 packing
                virent8090DEVCX6DISUFB010(564704),    -- V6R7C00 for CX6DISUFB010(SBOM),Flexible Card Line Processing Unit(ISUF-120,two sub-slots)
                virent8090DEVCX6D0LBXFA11(564705),    -- V6R7C00 for CX6D0LBXFA11(SBOM),12-Port 10GBase LAN/WAN-SFP+ Integrated Integrated Service Unit (ISUI-120,Supporting 1588v2)
                -- V6R7 CX60086 packing
                virent8090DEVCR5DLPUFK061(564706),   -- NE5000E 400G Flexible Card Line Processing Unit(NE5000E LPUF-400,2 sub-slots)
                virent8090DEVCR5D0MPUB560(564707),   -- NE5000E Main Processing Unit B5
                --Begin: V6R7 3.28 NE added
                virent8090DEVCR5DL3XEFG7C(564708),    -- V6R7C00 for CR5DL3XEFG7C(SBOM),3-Port 10GBase LAN/WAN-SFP+ + 24-Port 100/1000Base-X-SFP Integrated Line Processing Unit(LPUI-51)
                virent8090DEVCR5D0L5XFA7J(564709),    -- V6R7C00 for CR5D0L5XFA7J(SBOM),5-Port 10GBase LAN/WAN-SFP+ Integrated Line Processing Unit E(LPUI-51-E)
                virent8090DEVCR5DL2XEFG7J(564710),    -- V6R7C00 for CR5DL2XEFG7J(SBOM),2-Port 10GBase LAN/WAN-SFP+ + 24-Port 1000Base-X-SFP Integrated Line Processing Unit E(LPUI-51-E)
                virent8090DEVCR5D0EMGFA7J(564711),    -- V6R7C00 for CR5D0EMGFA7J(SBOM),48-Port 100/1000Base-X-SFP Integrated Line Processing Unit E(LPUI-51-E)
                virent8090DEVCR5D0LBXFA7L(564712),    -- V6R7C00 for CR5D0LBXFA7L(SBOM),12-Port 10GBase LAN/WAN-SFP+ Integrated Line Processing Unit L(LPUI-120-L)
                virent8090DEVCR5D0LAXFA7L(564713),    -- V6R7C00 for CR5D0LAXFA7L(SBOM),10-Port 10GBase LAN/WAN-SFP+ Integrated Line Processing Unit L(LPUI-102-L)
                virent8090DEVCR5D00LFXF7L(564714),    -- V6R7C00 for CR5D00LFXF7L(SBOM),24-Port 10GBase LAN/WAN-SFP+ Integrated Line Processing Unit L(LPUI-240-L)
                --End: V6R7 3.28 NE added
                virent8090DEVCR5D00LMXF61(564715),   -- NE5000E 400G Flexible Card Line Processing Unit(NE5000E LPUI480,2 sub-slots)
        --V6R7 2013.5.6 add by h00205464
        virent8090DEVCR5D0LBXFA71(564720),    -- V6R7C00 for CR5D0LBXFA71(SBOM),12-Port 10GBase LAN/WAN-SFP+ Line Processing Unit(LPUS-120)
        virent8090DEVCX6DSFUIE07B(564721),    -- V6R7C00 for CX6DSFUIE07B(SBOM),200Gbps Switch Fabric Unit B(SFUI-200-B)
        virent8090DEVCX6D0SRUA511(564722),    -- V6R7C00 for CX6D0SRUA511(SBOM),Switch and Route Processing Unit A5
        virent8090DEVCX6DSFUIE07C(564723),    -- V6R7C00 for CX6DSFUIE07C(SBOM),200Gbps Switch Fabric Unit C(SFUI-100-C)
        virent8090DEVCX6DISUFF010(564724),    -- V6R7C00 for CX6DISUFF010(SBOM),Flexible Card Integrated Service Unit(ISUF-240)
        virent8090DEVCX6D0LFXFA10(564725),    -- V6R7C00 for CX6D0LFXFA10(SBOM),24-Port 10GBase LAN/WAN-SFP+ Integrated Integrated Service Unit (ISUI-240,Supporting 1588v2)
        --V6R7 2013.05.10 added by xuelu for X16A
        virent8090DEVCR5DSFUIE07D(564726),    -- V6R7C00 for CR5DSFUIE07D(SBOM),200Gbps Switch Fabric Unit D(SFUI-200-D)
        virent8090DEVCR5DLPUFF07E(564727),    -- V6R7C00 for CR5DLPUFF07E(SBOM),Flexible Card Line Processing Unit(LPUF-240-E)
        -- from 159744 to 659456 is for ME60 Whole BOARD
        virent8090DEVCX6D0LBXFA12(564728),    -- V6R7C00 for CX6D0LBXFA12(SBOM),12-Port 10GBase LAN/WAN-SFP+ Flexible Card A(S240-A)
        virent8090DEVCX6DL1XESG1A(564730),    -- V6R7C00 for CX6DL1XESG1A(SBOM),1-Port 10GBase LAN/WAN-SFP+ +11-Port 1000Base-X-SFP Flexible Card A(S51-A)
        virent8090DEVCX6DL2XEAG1A(564731),    -- V6R7C00 for CX6DL2XEAG1A(SBOM),2-Port 10GBase LAN/WAN-SFP+ +10-Port 1000Base-X-SFP Flexible Card A(S51-A)
        virent8090DEVCR5D00LAXF60(564732),    -- 10-Port 10GBase LAN/WAN-SFP+ Integrated Line Processing Unit (NE5000E LPUI-100)
        virent8090DEVCR5DLPUFM070(564733),    -- V8R6C10 for CR5DLPUFM070(SBOM),Flexible Card Line Processing Unit(LPUF-480)
        virent8090DEVCR57SRU1TA(564734),    -- V8R6C20 for NE40E CR57SRU1TA
        virent8090DEVCR56SRU1TA(564735),    -- V8R6C20 for NE5000E CR57SRU1TA
        virentCX61DEVCR57SRU1TA(564736),    -- V8R6C20 for OC-CX600 CR57SRU1TA
        virent8090DEVCR57SFU1TC(564737),    -- V8R6C20 for NE40E CR57SFU1TC
        virent8090DEVCR56SFU1TC(564738),    -- V8R6C20 for NE5000E CR56SFU1TC
        virentCX61DEVCR57SFU1TC(564739),    -- V8R6C20 for OC-CX600 CR57SFU1TC
        virent8090DEVCR57EBGFD0(564742),      -- V6R8C00 for 12xFE/GE-SFP Fixed Card
        virent8090DEVCR57LAXFB0(564743),      -- V6R8C00 for 10-port 10GBase LAN/WAN-SFP+ Flexible Card
        virent8090DEVCR57L3XFB0(564744),      -- V6R8C00 for 3-port 10GBase LAN/WAN-SFP+ Fixed Card
        virent8090DEVCR57EBGFE0(564745),      -- V6R8C00 for 12xFE-SFP-E Fixed Card
        virent8090DEVCR57L4XFE0(564746),      -- V6R8C00 for 4x10GBase LAN/WAN-SFP+ Fixed Card
        virent8090DEVCR57L3XFE0(564747),      -- V6R8C00 for 3x10GBase LAN/WAN-SFP+ -E Fixed Card
        virent8090DEVCR5DL3XEFG7E(564748),   -- V6R8C00 for CR5DL3XEFG7E(SBOM),3-Port 10GBase LAN/WAN-SFP+ + 24-Port 1000Base-X-SFP Integrated Line Processing Unit E(LPUI-51-E)
        virent8090DEVCR5DL4XEBG7E(564749),   -- V6R8C00 for CR5DL4XEBG7E(SBOM),4-Port 10GBase LAN/WAN-SFP+ + 12-Port 1000Base-X-SFP Integrated Line Processing Unit E(LPUI-51-E)
        virent8090DEVCR5DL4XEBG7L(564750),   -- V6R8C00 for CR5DL4XEBG7L(SBOM),4-Port 10GBase LAN/WAN-SFP+ + 12-Port 100/1000Base-X-SFP Integrated Line Processing Unit L(LPUI-51-L)
        virent8090DEVCR5D0MPUD270(564751),   -- V6R8C00 for CR5D0MPUD270(SBOM),Main Processing Unit D3
        virent8090DEVCR2D000MPU11(564752),   -- V6R8C00 for CR2D000MPU11(SBOM),Main Processing Unit 2
        virent8090DEVCR2DLPUF5010(564753),   -- V6R8C00 for CR2DLPUF5010(SBOM),Flexible Card Line Processing Unit(NE20E LPUF-50,four slots)
        virent8090DEVCR21LPU50A00(564754),   -- V6R8C00 for CR21LPU50A00(SBOM),FIC Service Processing Engine(NE20E-X6,four slots)
        virent8090DEVCR5DL4XEBG7C(564755),   -- V6R8C00 for CR5DL4XEBG7C(SBOM),4-Port 10GBase LAN/WAN-SFP+ + 12-Port 100/1000Base-X-SFP Integrated Line Processing Unit (LPUI-51)
        virent600DEVCX6D0MPUD270(564756),   -- V6R8C00 for CX6D0MPUD270(SBOM),Main Processing Unit D3
        virent8090DEVCR2D0EMGFA1L(564757),   -- V6R8C00 for CR2D0EMGFA1L(SBOM),48-Port 100/1000Base-X-SFP Integrated Line Processing Unit L(LPUI-51-L)
        virent8090DEVCR5D0SRUA870(564758),   -- V8R6C20 for CR5D0SRUA870(SBOM), Switch and Route Processing Unit A8
        virent8090DEVCR5DSFUIM07C(564759),   -- V8R6C20 for CR5DSFUIM07C(SBOM), 480Gbps Switch Fabric Unit C(SFUI-480-C)
        virent8090DEVCR5DSFUIU07B(564760),   -- V8R6C20 for CR5DSFUIU07B(SBOM), 1Tbps Switch Fabric Unit B(SFUI-1T-B)
        virent8090DEVCR5DSFUIM07B(564761),   -- V8R6C20 for CR5DSFUIM07B(SBOM), 480Gbps Switch Fabric Unit B(SFUI-480-B),V8R6C10 shen qing de zhi mei you lu ru, chong xin shen qing yi ci
        virent600DEVCX6D0SRUA870(564762),    -- V8R6C20 for CX6D0SRUA870(SBOM), Switch and Route Processing Unit A8
        virent600DEVCX6DSFUIM07C(564763),    -- V8R6C20 for CX6DSFUIM07C(SBOM), 480Gbps Switch Fabric Unit C(SFUI-480-C)
        virent600DEVCX6D0MPUB570(564764),    -- V8R6C20 for CX6D0MPUB570(SBOM), Main Processing Unit B5
        virent600DEVCX6DSFUIM07B(564765),    -- V8R6C20 for CX6DSFUIM07B(SBOM), 480Gbps Switch Fabric Unit B(SFUI-480-B)
        virent600DEVCX6DSFUIU07B(564766),    -- V8R6C20 for CX6DSFUIU07B(SBOM), 1Tbps Switch Fabric Unit B(SFUI-1T-B)
        virent600DEVCX6PM2EBAS70(564767),    -- V8R6C20 V8R7 for CX67MNPUI(SBOM), 80Gbps MNPUI DC
        virent600DEVCX6PM2EBAS71(564802),    -- V8R6C20 V8R7 for CX67MNPUI(SBOM), 80Gbps MNPUI AC
        virent600DEVCX6PM2FBAS70(564785),    --V8R6C20 V8R7 CX600-M2F CX67MNPUI(SBOM), 160Gbps MNPUI DC
        virent600DEVCX6PM2FBAS71(564786),    --V8R6C20 V8R7 CX600-M2F CX67MNPUI(SBOM), 160Gbps MNPUI AC
        virent600DEVCR2P2EBASD10(564787),    --V8R6C20 V8R7 NE20E-S2E CX67MNPUI(SBOM), 80Gbps MNPUI DC
        virent600DEVCR2P2EBASA10(564788),    --V8R6C20 V8R7 NE20E-S2E CX67MNPUI(SBOM), 80Gbps MNPUI AC
        virent600DEVCR2P2FBASD10(564789),    --V8R6C20 V8R7 NE20E-S2F CX67MNPUI(SBOM), 160Gbps MNPUI DC
        virent600DEVCR2P2FBASA10(564790),    --V8R6C20 V8R7 NE20E-S2F CX67MNPUI(SBOM), 160Gbps MNPUI AC
        virent600DEVCR5PM2EBAS70(564791),    --V8R6C20 V8R7 NE40E-M2E CX67MNPUI(SBOM), 80Gbps MNPUI DC
        virent600DEVCR5PM2EBAS71(564792),    --V8R6C20 V8R7 NE40E-M2E CX67MNPUI(SBOM), 80Gbps MNPUI AC
        virent600DEVCR5PM2FBAS70(564793),    --V8R6C20 V8R7 NE40E-M2F CX67MNPUI(SBOM), 160Gbps MNPUI DC
        virent600DEVCR5PM2FBAS71(564794),    --V8R6C20 V8R7 NE40E-M2F CX67MNPUI(SBOM), 160Gbps MNPUI AC
        virent600DEVTNRPM2EBAS70(564795),    --V8R6C20 V8R7 PTN6900-M2E CX67MNPUI(SBOM), 80Gbps MNPUI DC
        virent600DEVTNRPM2EBAS71(564796),    --V8R6C20 V8R7 PTN6900-M2E CX67MNPUI(SBOM), 80Gbps MNPUI AC
        virent600DEVTNRPM2FBAS70(564797),    --V8R6C20 V8R7 PTN6900-M2F CX67MNPUI(SBOM), 160Gbps MNPUI DC
        virent600DEVTNRPM2FBAS71(564798),    --V8R6C20 V8R7 PTN6900-M2F CX67MNPUI(SBOM), 160Gbps MNPUI AC
		virent600DEVCR8P0BKP03C2(688900),    -- V8R21C10 for CR8P0BKP03C2(SBOM) Integration Processing Unit
		virent600DEVCR8P0BKP03C3(688901),    -- V8R21C10 for CR8P0BKP03C3(SBOM) Integration Processing Unit
        virent8090DEVCX68FCBD(564799),       --V8R6C20 V8R7 M2 fan unit
        virent8090DEVCX68PSUF(564800),       --V8R6C20 V8R7 M2 DC power supply unit
        virent8090DEVCX68PSUG(564801),       --V8R6C20 V8R7 M2 AC power supply unit
        virent600DEVCX6DL2XEEG7B(564774),   -- V6R8C10 for CX6DL2XEEG7B(SBOM),2-Port 10GBase LAN/WAN-XFP+20-Port 100/1000Base-X-SFP Integrated Integrated Service Unit (ISUI-51-B,Supporting 1588v2)
        virent8090DEVCR5D0E6MFA70(564775),    -- V6R8C10 for CR5D0E6MFA70(SBOM), 6-Port 40GBase-QSFP+ Integrated Line Processing Unit (LPUI-240)
        virent8090DEVCR5D0E6MFA71(564776),    -- V6R8C10 for CR5D0E6MFA71(SBOM), 6-Port 40GBase-QSFP+ Integrated Line Processing Unit (LPUI-240-B)
        virent600DEVCX6DISUFE011(564777),    -- V6R8C10 for CX6DISUFE011(SBOM), Flexible Card Integrated Service Unit(ISUF-200)
        virent600DEVCX6DISUFA210(564778),    -- V6R8C10 for CX6DISUFA210(SBOM), Flexible Card Integrated Service Unit(ISUF-102)
        virent600DEVCX6D0LEXFA10(564779),    -- V6R8C10 for CX6D0LEXFA10(SBOM), 20-Port 10GBase LAN/WAN-SFP+ Integrated  Integrated Service Unit (ISUI-200,Supporting 1588v2)
        virent600DEVCX6D0LAXFA10(564780),    -- V6R8C10 for CX6D0LAXFA10(SBOM), 10-Port 10GBase LAN/WAN-SFP+ Integrated  Integrated Service Unit (ISUI-102,Supporting 1588v2)
        virent600DEVCX6DVSUI2010(564781),    -- V6R8C10 for CX6DVSUI2010(SBOM), Integrated Versatile Service Unit(VSUI-20)

        virent8090DEVCR5D00LMXF70(564782),    -- V8R6C10 for CR5D00LMXF70(SBOM),48-Port 10GBase LAN/WAN-SFP+ Integrated Line Processing Unit (LPUI-480)
        virent8090DEVCR5DE2NLFX70(564783),    -- V8R6C10 for CR5DE2NLFX70(SBOM),2-Port 100GBase-CFP2 + 24-Port 10GBase LAN/WAN-SFP+ Integrated Line Processing Unit (LPUI-480)
        virent8090DEVCR5D00E4NC70(564784),    -- V8R6C20 for CR5D00E4NC70(SBOM),4-Port 100GBase-CFP2 Integrated Line Processing Unit (LPUI-480)
        virent8090DEVCR5DOMPUB061(564901),   -- V8R7C00 for CR5DOMPUB061(SBOM), -16 Main Processing Uint
        virent600DEVCX62SNCA00(564803),       -- V600R008C20 for VSUF CH-CX SNC Atomic Router
        virent8090DEVCR5DSFUIK06C(564902),     -- V8R7C10 for CR5DSFUIK06C(SBOM), X16 400G Cluster
        virent8090DEVCR5D00TBXF71(564903),    -- V8R7C10 for 12-Port OTU2-SFP+ Integrated Line Processing Unit (LPUI-120)
        virent8090DEVCR5D00TFXF71(564904),    -- V8R7C10 for 24-Port OTU2-SFP+ Integrated Line Processing Unit (LPUI-240)

        --V8R7 2014.06.13 added by raopeitao for lpu1te
        virent8090DEVCR5D00E8NC70(564740),    -- V8R7C00 for CR5D00E8NC70(SBOM),8-Port 100GBase-CFP2 Integrated Line Processing Unit (LPUI-1T)
        virent8090DEVCR5D00E8NC7B(564741),    -- V8R8C00 for CR5D00E8NC7B(SBOM),8-Port 100GBase-CFP2 Integrated Line Processing Unit B(LPUI-1T-B)

        --V8R7 2015.06.17 added by zhouyinghui
          virentPTN6900DEVTNRDSFUIU07C(229475),   --for V800R007C00 TNRDSFUIU07C(SBOM),1Tbps Switch Fabric Unit C(SFUI-1T-C)
          virentPTN6900DEVTNRD0MPUB570(229476),   --for V800R007C00 TNRD0MPUB570(SBOM),Main Processing Unit B5
          virentPTN6900DEVTNRDSFUIM07B(229477),   --for V800R007C00 TNRDSFUIM07B(SBOM),480Gbps Switch Fabric Unit B(SFUI-480-B)
          virentPTN6900DEVTNRDSFUIU07B(229478),   --for V800R007C00 TNRDSFUIU07B(SBOM),1Tbps Switch Fabric Unit B(SFUI-1T-B)
          virent8090DEVCR5D0MPUD470(561175),      -- for V800R007C00 CR5D0MPUD470(SBOM), Main Processing Unit D4
          virent600DEVCR5DLPUF507L(564804),       -- for V800R007C00 CR5DLPUF507L(SBOM),Flexible Card Line Processing Unit L(LPUF-50-L,four sub-slots)
          virent600DEVCR5D00LBXF7L(564805),       -- for V800R007C00 CR5D00LBXF7L(SBOM),12-Port 10GBase LAN/WAN-SFP+ Integrated Line Processing Unit L(LPUI-120-L)
          virent600DEVCR5D00LFXF7L(564806),       -- for V800R007C00 CR5D00LFXF7L(SBOM),24-Port 10GBase LAN/WAN-SFP+ Integrated Line Processing Unit L(LPUI-240-L)
          virent600DEVCR5D00D2NT70(564807),       -- for V800R007C00 CR5D00D2NT70(SBOM),2-Port 100GE Tunable DWDM Integrated Line Processing Unit (LPUI-200)
          virent600DEVCR5DLPUFE070(564808),       -- for V800R007C00 CR5DLPUFE070(SBOM),Flexible Card Line Processing Unit(LPUF-200)
          virent600DEVCX6D0MPUD470(564809),       -- for V800R007C00 CX6D0MPUD470(SBOM),Main Processing Unit D4
          virentME60DEVME0P0MPUD470(159758),      -- for V800R007C00 ME0P0MPUD470(SBOM), Main Processing Unit D4
          virentME60DEVME0D0SRUA970(159759),      -- for V800R007C00 ME0D0SRUA970(SBOM),Switch and Route Processing Unit A9
          virentME60DEVME0D0MPUB570(159760),      -- for V800R007C00 ME0D0MPUB570(SBOM),Main Processing Unit B5
          virentME60DEVME0D0SRUA870(159761),      -- for V800R007C00 ME0D0SRUA870(SBOM),Switch and Route Processing Unit A8
          virentME60DEVME0DSFUIU07C(160512),      -- for V800R007C00 ME0DSFUIU07C(SBOM),1Tbps Switch Fabric Unit C(SFUI-1T-C)
          virentME60DEVME0DSFUIK07B(160513),      -- for V800R007C00 ME0DSFUIK07B(SBOM),480Gbps Switch Fabric Unit(SFUI-480-B)
          virentME60DEVME0DSFUIU07B(160514),      -- for V800R007C00 ME0DSFUIU07B(SBOM),1Tbps Switch Fabric Unit B(SFUI-1T-B)
          virentME60DEVME0DSFUIK07A(160515),      -- for V800R007C00 ME0DSFUIK07A(SBOM),480Gbps Switch Fabric Unit(SFUI-480-A)
          virentPTN6900DEVTNRD0MPUD370(229405),   --for V800R007C00 TNRD0MPUD370(SBOM),Main Processing Unit D3
          virentPTN6900DEVTNRD0MPUD470(229406),   --for V800R007C00 TNRD0MPUD470(SBOM),Main Processing Unit D4

        --V8R7 2015.06.17 added by zhouyinghui
        --LPUI-51-S
          virent8090DEVCR5D00EMGF74(564811),      -- for V800R007C00 CR5D00EMGF74(SBOM), 48-Port 100/1000Base-X-SFP Integrated Line Processing Unit S(LPUI-51-S)
          virent8090DEVCR5DL2XEFG73(564812),      -- for V800R007C00 CR5DL2XEFG73(SBOM), 2-Port 10GBase LAN/WAN-SFP+ + 24-Port 100/1000Base-X-SFP Integrated Line Processing Unit S(LPUI-51-S)

        --MPUK1
          virent8090DEVCX6D0MPUK170(561176),      -- for V800R007C00 CX6D0MPUK170(SBOM), Main Processing Unit K1
          virent8090DEVCR5D0MPUK170(561177),      -- for V800R007C00 CR5D0MPUK170(SBOM), Main Processing Unit K1
          virent8090DEVCR2D0MPUE110(561178),      -- for V800R007C00 CR2D0MPUE110(SBOM), Main Processing Unit K1
          virentPTN6900DEVTNUD00MPUK71(229407),    --for V800R007C00 TNUD00MPUK71(SBOM), Main Processing Unit K1
          virent8090DEVCX6D00MPUK11(570058),      -- for V800R010C00 CX6D00MPUK11(SBOM), Main Processing Unit K1

        --IPU (M2E)
          virent8090DEVCR2B0BKP0210(561179),      -- for V800R007C00 CR2B0BKP0210(SBOM), Integration Processing Unit
          virent8090DEVCR5B0BKP0371(561180),      -- for V800R007C00 CR5B0BKP0371(SBOM), Integration Processing Unit
          virent8090DEVCX6B0BKP0371(561181),      -- for V800R007C00 CX6B0BKP0371(SBOM), Integration Processing Unit
          virentPTN6900DEVTNRB0BKP0371(229408),    --for V800R007C00 TNUD00MPUK71(SBOM), Integration Processing Unit

        --IPU(M2F)
          virent8090DEVCR2B0BKP0211(561182),      -- for V800R007C00 CR2B0BKP0211(SBOM), Integration Processing Unit
          virent8090DEVCR5B0BKP0372(561183),      -- for V800R007C00 CR5B0BKP0372(SBOM), Integration Processing Unit
          virent8090DEVCX6B0BKP0372(561184),      -- for V800R007C00 CX6B0BKP0372(SBOM), Integration Processing Unit
          virentPTN6900DEVTNRB0BKP0372(229409),    --for V800R007C00 TNRB0BKP0372(SBOM), Integration Processing Unit
        --V8R8 2015.06.17 added by zhouyinghui
        --CR57LPUF200C
          virent8090DEVCR5D00E2NC76(564813),      -- for V800R008C00 CR5D00E2NC76(SBOM), 2-Port 100GBase-CFP Integrated Line Processing Unit(LPUI-200)
          virent8090DEVCR5D00LEXF76(564814),      -- for V800R008C00 CR5D00LEXF76(SBOM), 20-Port 10GBase LAN/WAN-SFP+ Integrated Line Processing Unit(LPUI-200)
          virent8090DEVCR5DE1NLAX76(564815),      -- for V800R008C00 CR5DE1NLAX76(SBOM), 1-Port 100GBase-CFP + 10-Port 10GBase LAN/WAN-SFP+ Integrated Line Processing Unit(LPUI-200)
          virent8090DEVCR5D00E2NC75(564816),      -- for V800R008C00 CR5D00E2NC75(SBOM), 2-Port 100GBase-CFP Integrated Line Processing Unit L(LPUI-200-L)
          virent8090DEVCR5D00LEXF75(564817),      -- for V800R008C00 CR5D00LEXF75(SBOM), 20-Port 10GBase LAN/WAN-SFP+ Integrated Line Processing Unit L(LPUI-200-L)
          virent8090DEVCR5DE1NLAX75(564818),      -- for V800R008C00 CR5DE1NLAX75(SBOM), 1-Port 100GBase-CFP + 10-Port 10GBase LAN/WAN-SFP+ Integrated Line Processing Unit L(LPUI-200-L)
          virent8090DEVCR5D0SRUB570(564819),      -- for V800R008C00 CR5D0SRUB570(SBOM), Switch and Route Processing Unit A5E
         virent8090DEVCX6DISUFM010(564820),     -- V8R8C10,LPUF480,Flexible Card Line Processing Unit(LPUF-480)
          virent8090DEVCX6DISUFE012(564821),     -- V8R8C10,LPUF-200,Flexible Card Integrated Service Unit(ISUF-201)
          virent8090DEVCR5D00E8NC7C(564822),      -- for V800R008C10 CR5D00E8NC7C(SBOM), 8-Port 100GBase-CFP2 Integrated Line Processing Unit B(LPUI-1T-L)
          virent8090DEVCR5D00LMXF7C(564823),      -- for V800R008C10 CR5D00LMXF7C(SBOM), 48-Port 10GBase LAN/WAN-SFP+ Integrated Line Processing Unit (LPUI-480-L)
          virent8090DEVCR5DE2NLFX7C(564825),      -- for V800R008C10 CR5DE2NLFX7C(SBOM), 2-Port 100GBase-CFP2 + 24-Port 10GBase LAN/WAN-SFP+ Integrated Line Processing Unit (LPUI-480-L)
          virent8090DEVCX6DSFUIM01B(564826),     --CX6DSFUIM01B,480Gbps Switch Fabric Unit B(SFUI-480-B)
          virent8090DEVCR5D00E4NC7C(564827),      -- for V800R008C10 CR5D00E4NC7C(SBOM), 4-Port 100GBase-CFP2 Integrated Line Processing Unit (LPUI-480-L)
          virent8090DEVCX6DSFUIM01C(564828),     --CX6DSFUIM01C 480Gbps Switch Fabric Unit(SFUI-480-B)
          virent8090DEVCX6D0MPUB510(564829),     --CX6D0MPUB510 Main Processing Unit B5
          virent8090DEVCX6D0SRUA810(564830),     --CX6D0SRUA810 Switch and Route Processing Unit A8
          virent8090DEVCX6D0MPUD410(564832),     --CX6D0MPUD410,Main Processing Unit D4
          virent8090DEVCX6D0SRUB510(564834),     --CX6D0SRUB510,Enhanced Switch and Route Processing Unit A5
          virent8090DEVCR5DLPUFM07B(564836),      -- CR5DLPUFM07B,Flexible Card Line Processing Unit(LPUF-480-B)
          virent8090DEVCR5D00LMXF7B(564837),      -- CR5D00LMXF7B,48-Port 10GBase LAN/WAN-SFP+ Integrated Line Processing Unit (LPUI-480-B)
          virent8090DEVCR5DE2NLFX7B(564838),      -- CR5DE2NLFX7B,2-Port 100GBase-CFP2 + 24-Port 10GBase LAN/WAN-SFP+ Integrated Line Processing Unit (LPUI-480-B)
          virent8090DEVCR5D00E4NC7B(564839),      -- CR5D00E4NC7B,4-Port 100GBase-CFP2 Integrated Line Processing Unit (LPUI-480-B)
          virent8090DEVCX6D0LEXFA11(564840),      --CX6D0LEXFA11,20-Port 10GBase LAN/WAN-SFP+ Integrated  Integrated Service Unit (ISUI-201)
          virent8090DEVCR5D0L5XFA7F(564841),      --CR5D0L5XFA7F,5-Port 10GBase LAN/WAN-SFP+ Integrated Line Processing Unit E(LPUI-52-E,Enhanced HQos)
          virent8090DEVCR5DL2XFFG7E(564842),      --CR5DL2XFFG7E,2-Port 10GBase LAN/WAN-SFP+ + 24-Port 1000Base-X-SFP Integrated Line Processing Unit E(LPUI-52-E,Enhanced HQos)
          virent8090DEVCR5DLAXFAJ7F(564843),      --CR5DLAXFAJ7F,10-Port 10GBase LAN/WAN-SFP+ Integrated Line Processing Unit E(LPUI-120-E)

          virent8090DEVME0DL2XEFG8E(564844),      --ME0DL2XEFG8E,2-Port 10GBase LAN/WAN-SFP++24-Port 1000Base-SFP Broadband Service Unit Integrated E(BSUI-52-E)
          virent8090DEVME0D0L5XXE71(564845),      --ME0D0L5XXE71,5-Port 10GBase LAN/WAN-SFP+ Broadband Service Unit Integrated E(BSUI-52-E)
          virent8090DEVME0D0LAXXH71(564846),      --ME0D0LAXXH71,10-Port 10GBase LAN/WAN-SFP+ Broadband Service Unit Integrated E(BSUI-120-E)
		  virent8090DEVME0D0LAXXE70(675941),      --ME0D0LAXXE70,10-Port 10GBase LAN/WAN-SFP+ Broadband Service Unit Integrated E(BSUI-100-E)

          virent8090DEVCR5DLPUFE07E(564847),      --CR5DLPUFE07E,Flexible Card Line Processing Unit(LPUF-200-E)
          virent8090DEVME0DBSUFB070(564848),      --ME0DBSUFB070,Flexible Card Broadband Service Unit(BSUF-120,2 sub-slots)
          virent8090DEVME0DBSUFC870(564849),      --ME0DBSUFC870,Flexible Card Broadband Service Unit(BSUF-200,2 sub-slots)
          virent8090DEVCR5D0L5XFL70(675750),      --CR5DLAXFAJ7F,10-Port 10GBase LAN/WAN-SFP+ Integrated Line Processing Unit E(LPUI-120-E)
          virent8090DEVCR5DL4XEFG70(675751),      --CR5DLAXFAJ7F,10-Port 10GBase LAN/WAN-SFP+ Integrated Line Processing Unit E(LPUI-120-E)
          virent8090DEVCR5D0EMGFL70(675752),      --CR5DLAXFAJ7F,10-Port 10GBase LAN/WAN-SFP+ Integrated Line Processing Unit E(LPUI-120-E)
          virent8090DEVCR5DL2XEFG71(675753),      --CR5DLAXFAJ7F,10-Port 10GBase LAN/WAN-SFP+ Integrated Line Processing Unit E(LPUI-120-E)
          virent8090DEVCR5D0EFGFL70(675754),      --CR5DLAXFAJ7F,10-Port 10GBase LAN/WAN-SFP+ Integrated Line Processing Unit E(LPUI-120-E)

         virent8090DEVCR57E1NCF20(675902), --03057445,  1-Port 100GBase-CFP2 Integrated Line Processing Unit (LPUI-120)
         virent8090DEVCR57E1NCF21(675903), --03057446,  1-Port 100GBase-CFP2 Integrated Line Processing Unit B(LPUI-120-B)
         virent8090DEVCR57E2NCF22(675904), --03057447,  2-Port 100GBase-CFP2 Integrated Line Processing Unit (LPUI-240)
         virent8090DEVCR57E2NLBX24(675905), --03057448,  1-Port 100GBase-CFP2 + 12-Port 10GBase LAN/WAN-SFP+ Integrated Line Processing Unit (LPUI-240)
         virent8090DEVCR57E2NCF23(675906), --03057449,  2-Port 100GBase LAN-CFP2 Integrated Line Processing Unit B(LPUI-240-B)
         virent8090DEVCR57E2NLBX25(675907), --03057450,  1-Port 100GBase-CFP2 + 12-Port 10GBase LAN/WAN-SFP+ Integrated Line Processing Unit B(LPUI-240-B)
         virent8090DEVCR57E1NBA20(675912), --CR5D00E1ND71, 1-Port 100GBase-QSFP28 Integrated Line Processing Unit (LPUI-120)
         virent8090DEVCR57E1NBA21(675913), --CR5D00E1ND72, 1-Port 100GBase-QSFP28 Integrated Line Processing Unit B(LPUI-120-B)
         virent8090DEVCR57E2NBA20(675914), --CR5D00E2ND70, 2-Port 100GBase-QSFP28 Integrated Line Processing Unit (LPUI-240)
         virent8090DEVCR57E2NBA21(675915), --CR5D00E2ND71, 2-Port 100GBase LAN-QSFP28 Integrated Line Processing Unit B(LPUI-240-B)
         virent8090DEVCR57E1NLBX25(675916), --CR5DE1NLBX73, 1-Port 100GBase-QSFP28 + 12-Port 10GBase LAN/WAN-SFP+ Integrated Line Processing Unit B(LPUI-240-B)
         virent8090DEVCR57E1NLBX24(675917), --CR5DE1NLBX72, 1-Port 100GBase-QSFP28 + 12-Port 10GBase LAN/WAN-SFP+ Integrated Line Processing Unit (LPUI-240)
         virent8090DEVCR57E2NLAX20(675908), --03057451,  1-Port 100GBase-CFP2 + 10-Port 10GBase LAN/WAN-SFP+ Integrated Line Processing Unit (LPUI-200)
         virent8090DEVCR57E2NLAX21(675909), --03057452,  1-Port 100GBase-CFP2 + 10-Port 10GBase LAN/WAN-SFP+ Integrated Line Processing Unit (LPUI-200-L)
         virent8090DEVCR57E2NCF24(675910), --03057453,  2-Port 100GBase-CFP2 Integrated Line Processing Unit (LPUI-200)
         virent8090DEVCR57E2NCF25(675911), --03057454,  2-Port 100GBase-CFP2 Integrated Line Processing Unit (LPUI-200-L)
          virent600DEVCR5PM2HBAS72(564858),    --V8R9C00 NE40E-M2H CR5PM2HBAS72(SBOM), 480Gbps MNPUI DC
          virent600DEVCR5PM2HBAS73(564859),    --V8R9C00 NE40E-M2H CR5PM2HBAS73(SBOM), 480Gbps MNPUI AC
          virent600DEVCR5B0BKP0377(564860),    --V8R9C00 NE40E-M2H CR5B0BKP0377(SBOM), 480Gbps MNPUI NO POWER
          virent600DEVCX6PM2HBAS72(564861),    --V8R9C00 CX600-M2H CX6PM2HBAS72(SBOM), 480Gbps MNPUI DC
          virent600DEVCX6PM2HBAS73(564862),    --V8R9C00 CX600-M2H CX6PM2HBAS73(SBOM), 480Gbps MNPUI AC
          virent600DEVCX6B0BKP0375(564863),    --V8R9C00 CX600-M2H CX6B0BKP0375(SBOM), 480Gbps MNPUI NO POWER
         --END: add for V8R9C00 M2H by g00181543

         --BEGIN: add for V8R10C10 M2K by wwx365872
          virent600DEVCX6PM2KBAS90(675932),    --V8R10C10 CX600-M2K CX6PM2KBAS90(SBOM), 1T MNPUI DC
          virent600DEVCX6PM2KBAS91(675933),    --V8R10C10 CX600-M2K CX6PM2KBAS91(SBOM), 1T MNPUI AC
          virent600DEVCX6B0BKP0391(675934),    --V8R10C10 CX600-M2K CX6B0BKP0391(SBOM), 1T MNPUI NO POWER
          virent600DEVCR5PM2KBAS90(675935),    --V8R10C10 NE40E-M2K CR5PM2KBAS90(SBOM), 1T MNPUI DC
          virent600DEVCR5PM2KBAS91(675936),    --V8R10C10 NE40E-M2K CR5PM2KBAS91(SBOM), 1T MNPUI AC
          virent600DEVCR5B0BKP0391(675937),    --V8R10C10 NE40E-M2K CR5B0BKP0391(SBOM), 1T MNPUI NO POWER
          virent600DEVCX6P02ABAS00(675938),    --V8R10C10 CX6602 CX6P02ABAS00(SBOM), 1T MNPUI DC
          virent600DEVCX6P02ABAS01(675939),    --V8R10C10 CX6602 CX6P02ABAS01(SBOM), 1T MNPUI AC
          virent600DEVCX6B0BKP0292(675940),    --V8R10C10 CX6602 CX6B0BKP0292(SBOM), 1T MNPUI NO POWER
		  virent8090DEVCR5D0MPUN160(570061),     -- V8R10C10 for CR5D0MPUN160(SBOM) NE5000E-20 Main Processing Unit N1(MPUN1)
         --END: add for V8R10C10 M2K by wwx365872
          virent8090DEVCR5DE2NLFX71(564920), --CR5DE2NLFX71, 2-Port 100GBase-QSFP28 + 24-Port 10GBase LAN/WAN-SFP+ Integrated Line Processing Unit (LPUI-480)
          virent8090DEVCR5DE2NLFX72(564921), --CR5DE2NLFX72, 2-Port 100GBase-QSFP28 + 24-Port 10GBase LAN/WAN-SFP+ Integrated Line Processing Unit B(LPUI-480-B)
          virent8090DEVCR5DE2NLFX73(564922), --CR5DE2NLFX73, 2-Port 100GBase-QSFP28 + 24-Port 10GBase LAN/WAN-SFP+ Integrated Line Processing Unit L(LPUI-480-L)
          virent8090DEVCR5D00E4NB70(564923), --CR5D00E4NB70, 4-Port 100GBase-QSFP28 Integrated Line Processing Unit (LPUI-480)
          virent8090DEVCR5D00E4NB7B(564924), --CR5D00E4NB7B, 4-Port 100GBase-QSFP28 Integrated Line Processing Unit B(LPUI-480-B)
          virent8090DEVCR5D00E4NB7C(564925), --CR5D00E4NB7C, 4-Port 100GBase-QSFP28 Integrated Line Processing Unit L(LPUI-480-L)
		  virent600DEVCR5B0BKP0381(675718),    --V8R11C00 NE40E-M2K CR5B0BKP0381(SBOM), 1T MNPUI NO POWER

 -- ME60:
                virentME60DEVME0D0LFXFB70(160520),      -- for V800R011C10 ME0D0LFXFB70(SBOM), 24-Port 10GBase LAN/WAN-SFP+ Broadband Service Unit Integrated(BSUI-240)
                virentME60DEVME0DE2NLEX7C(564926), --ME0DE2NLEX7C, 2-Port 100GBase-QSFP28 + 20-Port 10GBase LAN/WAN-SFP+ Broadband Service Unit Integrated(BSUI-400)
                virentME60DEVLPU(159744),            -- The whole IO board, incude all entitys on the slot
                virentME60DEVMPU(159745),            -- Whole MPU Board, incude all entitys on the slot, virtual entity
                virentME60DEVSRU(159746),            -- Whole SRU Board, incude all entitys on the slot, virtual entity
                virentME60DEVSFUA(159747),           -- Switch Fabric Unit for Full Capacity System, incude all entitys on the slot,virtual entity
                virentME60DEVSFUB(159748),           -- Switch Fabric Unit for Half & Halflow Frame System, incude all entitys on the slot,virtual entity

                -- from 159749 to 160499 is for ME60 MPU Whole board
                virentME60DEVCR52SRUA(159749),       -- the old whole board of SRUA saled before V3R8 version in ME60(whithout SBOM information)
                virentME60DEVCR52MPUA(159750),       -- the old whole board of MPUA saled before V3R8 version in ME60(whithout SBOM information)
                virentME60DEVCR52MPUB(159751),       -- the old whole board of MPUB saled before V3R8 version in ME60(whithout SBOM information)

                virentME60DEVME0D00MPUD70(159752),   -- V3R8 for ME0D00MPUD70(SBOM), ME60-X3 Main Processing Unit D
                virentME60DEVME03SRUA3(159753),      -- V3R8 for ME03SRUA3(SBOM), ME60-8 Switch and Route Processing Unit A3
                virentME60DEVME0D0SRUA470(159754),   -- V3R8 for ME0D0SRUA470(SBOM), ME60-X16 Main Processing Unit B4
                virentME60DEVME03MPUA0(159755),      -- V3R8 for ME03MPUA0(SBOM), ME60-16 Main Processing Unit A0
                virentME60DEVME0D0MPUB470(159756),   -- V3R8 for ME0D0MPUB470(SBOM), ME60-X8 Switch and Route Processing Unit A4
                virentME60DEVME0D00MPUH(159757),     -- V6R5 for ME0D00MPUH(SBOM), ME60-X3 Main Processing Unit H
                virentME60DEVME0D0SRUA570(159798),   -- V6R3C05 for ME0D0SRUA570(SBOM),Switch and Route Processing Unit A5(Including 1*2G Memory and 1*1G CF Card)

                -- from 160500 to 161499 is for ME60 SFU Whole board
                virentME60DEVCR52SFUA(160500),          -- the old whole board of SFUA saled before V3R8 version in ME60(whithout SBOM information)
                virentME60DEVCR52SFUD(160501),           -- the old whole board of SFUD saled before V3R8 version in ME60(whithout SBOM information)
                virentME60DEVCR52SFUF(160502),           -- the old whole board of SFUF saled before V3R8 version in ME60(whithout SBOM information)
                virentME60DEVCR52SFUG(160503),           -- the old whole board of SFUG saled before V3R8 version in ME60(whithout SBOM information)

                virentME60DEVME0DSFUI407B(160504),   -- V3R8 for ME0DSFUI407B(SBOM), ME60-X16 40G Switch Fabric Unit B
                virentME60DEVME0DSFUI407C(160505),   -- V3R8 for ME0DSFUI407C(SBOM), ME60-X8 40G Switch Fabric Unit C
                virentME60DEVME0D00SFUG20(160506),   -- V3R8 for ME0D00SFUG20(SBOM), ME60-16 Switch Fabric Unit G
                virentME60DEVME03SFU200B0(160507),   -- V6R3C05 for ME03SFU200B0(SBOM),200Gbps Switch Fabric Unit B(SFUI-200-B)
                virentME60DEVME03SFU200C0(160508),   -- V6R3C05 for ME03SFU200C0(SBOM),200Gbps Switch Fabric Unit C(SFUI-200-C)
                -- V6R7 packing for mpu 2012-12-09 begin
                virentME60DEVSRU100D(160509),     -- V6R7C00,SRU100D,Switch and Route Processing Unit A7(Including 1*2G Memory and 1*1G CF Card)
                virentME60DEVSFU100D(160510),     -- V6R7C00,SFU100D,100Gbps Switch Fabric Unit D(SFUI-100-D)
                virentME60DEVME0DSFUIE07D(160511),     -- V6R7C00,ME0DSFUIE07D(SBOM),100Gbps Switch Fabric Unit B(SFUI-100-B)
                -- V6R7 packing for mpu 2012-12-09 end

                -- from 161500 to 162999 is for ME60 LPU Whole board
                virentME60DEVCR52BSUA(161500),       -- the old whole board of BSUA(CR52LPUA) saled before V3R8 version in ME60(whithout SBOM information)
                virentME60DEVCR52MSUA(161501),       -- obsolete,
                virentME60DEVCR52SSUA(161502),       -- the old whole board of SSUA(CR52LPUA) saled before V3R8 version in ME60(whithout SBOM information)
                virentME60DEVCR52SCUA(161503),       -- the old whole board of SCUA(CR52LPUA) saled before V3R8 version in ME60(whithout SBOM information)
                virentME60DEVCR52TSUA(161504),       -- the old whole board of TSUA(CR52LPUA) saled before V3R8 version in ME60(whithout SBOM information)
                virentME60DEVCR52DSUA(161505),       -- the old whole board of DSUA(CR52LPUA) saled before V3R8 version in ME60(whithout SBOM information)
                virentME60DEVCR52NSUA(161506),       -- obsolete,
                virentME60DEVCR52ESUA(161507),       -- the old whole board of ESUA(CR52LPUA) saled before V3R8 version in ME60(whithout SBOM information)
                virentME60DEVME01BSUA(161508),       -- the old whole board of BSUA(ME01LPUA) saled before V3R8 version in ME60(whithout SBOM information)
                virentME60DEVME01MSUA(161509),       -- the old whole board of MSUA(ME01LPUA) saled before V3R8 version in ME60(whithout SBOM information)
                virentME60DEVME01SSUA(161510),       -- obsolete,
                virentME60DEVME01SCUA(161511),       -- obsolete,
                virentME60DEVME01TSUA(161512),       -- obsolete,
                virentME60DEVME01DSUA(161513),       -- obsolete,
                virentME60DEVME01NSUA(161514),       -- obsolete,
                virentME60DEVME01VSUA(161515),       -- the old whole board of VSUA(ME01LPUA) saled before V3R8 version in ME60(whithout SBOM information)

                virentME60DEVME03BSUF10(161516),     -- V3R8 for ME03BSUF10(SBOM), Flexible Card Broadband Service Unit(BSUF-10,four sub-slots)
                virentME60DEVME0MBSUF2120(161517),   -- V3R8 for ME0MBSUF2120(SBOM), Flexible Card Broadband Service Unit(BSUF-21,2 sub-slots)
                virentME60DEVME03MSUF21(161518),     -- V3R8 for ME03MSUF21(SBOM), Flexible Card Multi Service Unit(MSUF-21,2 sub-slots)
                virentME60DEVME0MMSUF4020(161519),   -- V3R8 for ME0MMSUF4020(SBOM), Flexible Card Multi Service Unit(MSUF-40,2 sub-slots)
                virentME60DEVME03SPUC(161520),       -- V3R8 for ME03SPUC(SBOM), Versatile Service Process Unit C
                virentME60DEVME0MVSUF1010(161521),   -- V3R8 for ME0MVSUF1010(SBOM), Flexible Card Versatile Service Unit 10(VSUF-10)
                virentME60DEVME0MBSUF4020(161522),   -- V3R8 for ME0MBSUF4020(SBOM), Flexible Card Broadband Service Unit(BSUF-40,2 sub-slots)
                virentME60DEVME0MMSUF1010(161523),   -- V3R8 for ME0MMSUF1010(SBOM), Flexible Card Multi Service Unit(MSUF-10,2 sub-slots)
                virentME60DEVME0MVSUI201A(161524),   -- V3R8 for ME0MVSUI201A(SBOM), Integrated Versatile Service Unit 20 A(VSUI-20-A)
                virentME60DEVME0MWSUF2120(161525),   -- V6R2C09 for ME0MWSUF2120(SBOM),Flexible Card WLAN Service Unit(WSUF-21,2 sub-slots)
                virentME60DEVME03MSUF100(161526),   -- V6R3C05 for ME03MSUF100(SBOM),Flexible Card Multi Service Unit (MSUF-100,4 sub-slots)
                virentME60DEVME03LAXXB0(161527),   -- V6R3C05 for ME03LAXXB0(SBOM),10-Port 10GBase LAN/WAN-XFP Multi Service Unit Integrated (MSUI-100)
                virentME60DEVME03VSUI20A(161528),   -- V6R3C05 for CR5DME03VSUI20A(SBOM),Integrated Versatile Service Unit 20 A(VSUI-20-A)
                virentME60DEVME03E1NC0(161529),   -- V6R3C05 for ME03E1NC0(SBOM),1-Port 100GBase-CFP Multi Service Unit Integrated (MSUI-100)
                virentME60DEVME0D0EKGFE70(161530),   -- for V600R005C00 ME0D0EKGFE70(SBOM),40-Port 100/1000Base-SFP Broadband Service Unit Integrated(BSUI-40)
                virentME60DEVME0D0L4XXE70(161531),   -- for V600R005C00 ME0D0L4XXE70(SBOM),4-Port 10GBase LAN/WAN-XFP Broadband Service Unit Integrated(BSUI-40)
                virentME60DEVME0DL2XEEG7E(161532),   -- for V600R005C00 ME0DL2XEEG7E(SBOM),2-Port 10GBase LAN/WAN-XFP+20-Port 100/1000Base-SFP Broadband Service Unit Integrated(BSUI-40)
                virentME60DEVME0D0L4XXB70(161533),   -- for V600R005C00 ME0D0L4XXB70(SBOM),4-Port 10GBase LAN/WAN-XFP Multi Service Unit Integrated(MSUI-40)
                virentME60DEVME0D0EEGFE20(161534),   -- for V600R005C00 ME0D0EEGFE20(SBOM),20-Port 100/1000Base-SFP Broadband Service Unit Integrated(BSUI-21)
                virentME60DEVME0D0L2XXE20(161535),   -- for V600R005C00 ME0D0L2XXE20(SBOM),2-Port 10GBase LAN/WAN-XFP Broadband Service Unit Integrated(BSUI-21)
                virentME60DEVME0DEBGE1X20(161536),   -- for V600R005C00 ME0DEBGE1X20(SBOM),1-Port 10GBase LAN/WAN-XFP+10-Port 100/1000Base-X-SFP Broadband Service Unit Integrated(BSUI-21)
                virentME60DEVME0D0L2XXB70(161537),   -- for V600R005C00 ME0D0L2XXB70(SBOM),2-Port 10GBase LAN/WAN-XFP Multi Service Unit Integrated(MSUI-21)
                virentME60DEVME0D0EFGFB50(161538),   -- for V600R005C00 ME0D0EFGFB50(SBOM),24-Port 100/1000Base-X-SFP Broadband Service Unit Integrated(BSUI-22)
                virentME60DEVME0D0L2XXB50(161539),   -- for V600R005C00 ME0D0L2XXB50(SBOM),2-Port 10GBase WAN/LAN-XFP Broadband Service Unit Integrated(BSUI-22)
                virentME60DEVMEODE1XEBG50(161540),   -- for V600R005C00 MEODE1XEBG50(SBOM),1-Port 10GBase WAN/LAN-XFP+12-Port 100/1000Base-X-SFP Broadband Service Unit Integrated(BSUI-22)
                virentME60DEVME0D0L4XXB50(161541),   -- for V600R005C00 ME0D0L4XXB50(SBOM),4-Port 10GBase WAN/LAN-XFP Broadband Service Unit Integrated(BSUI-41)
                virentME60DEVME0D0EKGFE50(161542),   -- for V600R005C00 ME0D0EKGFE50(SBOM),40-Port 100/1000Base-X-SFP Broadband Service Unit Integrated(BSUI-41)
                virentME60DEVME0DL2XEEG50(161543),   -- for V600R005C00 ME0DL2XEEG50(SBOM),2-Port 10GBase WAN/LAN-XFP+20-Port 100/1000Base-X-SFP Broadband Service Unit Integrated(BSUI-41)
                virentME60DEVVSUF80(161544),         -- SPU2.0 Board(80)
                virentME60DEVVSUF160(161545),        -- SPU2.0 Board(160)
                virentME60DEVVSUI160(161579),        -- for V600R009C00 ME0DVSUID070(SBOM),Integrated Versatile Service Unit(VSUI-160-E)
                --V8R9C10
                virentME60ME0D0VSE0070(564918),      -- for V800R009C10 ME0D0VSE0070(SBOM),Value-added Service Engine Unit (VSE-A) 1.3.6.1.4.1.2011.20021210.15.564918

                -- V6R7 ME packing 2012-10-11 begin
                virentME60DEVME0DBSUF5170(161546),   -- for V600R007C00 ME0DBSUF5170(SBOM),Flexible Card Broadband Service Unit(BSUF-51,2 sub-slots)
                virentME60DEVME0DL2XEFG7E(161547),   -- for V600R007C00 ME0DL2XEFG7E(SBOM),2-Port 10GBase LAN/WAN-XFP++24-Port 1000Base-SFP Broadband Service Unit Integrated E(BSUI-51-E)
                virentME60DEVME0DL2XEFG7B(161548),   -- for V600R007C00 ME0DL2XEFG7B(SBOM),2-Port 10GBase LAN/WAN-XFP++24-Port100/1000Base-SFP Broadband Service Unit Integrated (BSUI-51)
                virentME60DEVME0D0L5XXE70(161549),   -- for V600R007C00 ME0D0L5XXE70(SBOM),5-Port 10GBase WAN/LAN-XFP Broadband Service Unit Integrated E(BSUI-51-E)
                virentME60DEVME0D0L5XXB70(161550),   -- for V600R007C00 ME0D0L5XXB70(SBOM),5-Port 10GBase WAN/LAN-XFP Broadband Service Unit Integrated(BSUI-51)
                virentME60DEVME0DMSUF5170(161551),   -- for V600R007C00 ME0DMSUF5170(SBOM),Flexible Card Multi Service Unit(MSUF-51,2 sub-slots)
                virentME60DEVME0D0L5XXM70(161552),   -- for V600R007C00 ME0D0L5XXM70(SBOM),5-Port 10GBase WAN/LAN-SFP+ Multi Service Unit Integrated(MSUI-51)
                virentME60DEVME0DBSUFA070(161553),   -- for V600R007C00 ME0DBSUFA070(SBOM),Flexible Card Broadband Service Unit(BSUF-100,2 sub-slots)
                virentME60DEVME0DMSUFA070(161554),   -- for V600R007C00 ME0DMSUFA070(SBOM),Flexible Card Multi Service Unit(MSUF-100,2 sub-slots)
                virentME60DEVME0D0LAXXE70(161555),   -- for V600R007C00 ME0D0LAXXE70(SBOM),10-Port 10GBase WAN/LAN-SFP+ Broadband Service Unit Integrated E(BSUI-100-E)
                virentME60DEVME0D0L1NXM70(161556),   -- for V600R007C00 ME0D0L1NXM70(SBOM),1-Port 100GBase WAN/LAN-XFP Multi Service Unit Integrated(MSUI-100)
                virentME60DEVME0DBSUFF070(161557),   -- for V600R007C00 ME0DBSUFF070(SBOM),Flexible Card Broadband Service Unit(BSUF-240,2 sub-slots)
                -- V6R7 ME packing 2012-10-11 end
                -- V6R7 ME packing 2013-03-28 begin
                virentME60DEVME0DL3XEFG7B(161558),   -- for V600R007C00 ME0DL3XEFG7B(SBOM),3-Port 10GBase LAN/WAN-SFP++24-Port100/1000Base-SFP Broadband Service Unit Integrated (BSUI-51)
                virentME60DEVME0D0EMGFB70(161559),   -- for V600R007C00 ME0D0EMGFB70(SBOM),48-Port100/1000Base-SFP Broadband Service Unit Integrated (BSUI-51)
                virentME60DEVME0D0LAXXB70(161560),   -- for V600R007C00 ME0D0LAXXB70(SBOM),10-Port 10GBase LAN/WAN-SFP+ Broadband Service Unit Integrated(BSUI-100)
                virentME60DEVME0D0LBXFA70(161561),   -- for V600R007C00 ME0D0LBXFA70(SBOM),12-Port 10GBase LAN/WAN-SFP+ Broadband Service Unit Integrated(BSUI-100)
                virentME60DEVME0D0LBXXA70(161562),   -- for V600R007C00 ME0D0LBXXA70(SBOM),12-Port 10GBase LAN/WAN-XFP Broadband Service Unit Integrated(MSUI-100)
                -- V6R7 ME packing 2013-03-28 end
                -- V6R7 V6R7 2013.5.6 add by h00205464
                virentME60DEVME0D0LAXFA70(161563),   -- for V600R007C00 ME0D0LAXFA70(SBOM),10-Port 10GBase LAN/WAN-SFP+ Broadband Service Unit Integrated(MSUI-100)
                virentME60DEVVSUF40(161564),         -- for V600R007C00 ME0DVSUF4070(SBOM), Flexible Card Versatile Service Unit 40(VSUF-40)
                virentME0DL4XEBG7B(161565),          -- for V600R008C00 ME0DL4XEBG7B(SBOM), 4-Port 10GBase LAN/WAN-SFP++12-Port100/1000Base-SFP Broadband Service Unit Integrated (BSUI-51)
                virentME0DMSUFF070(161566),          -- for V600R008C00 ME0DMSUFF070(SBOM), Flexible Card Multi Service Unit(MSUF-240,2 sub-slots)
                virentME0D00MPUD72(161567),          -- for V600R008C00 ME0D00MPUD72(SBOM),Main Processing Unit D3
                virentME60DEVME2D00MPUE10(159762),  --for Main Processing Unit E  ME60-S
                virentME60DEVME0D00MPUK70(159763),  --for Main Processing Unit K  ME60-M

                virentME60DEVME2DSPUA0010(161581),  --for ME2DSPUA0010 Service Processor Unit(SPU-A)
                virentME60DEVME2DSPUB0010(161582),  --for ME2DSPUB0010 Service Processor Unit(SPU-B)
                virentME60DEVME0DBSU24071(161580),  --for ME0DBSU24071 Broadband Service Unit (BSU-240-A)

        --V8R8C10 ME
                virentME60DEVME0D0SRUB570(161589),     -- for V800R008C10 ME0D0SRUB570 Switch and Route Processing Unit A10
                virentME60DEVME0DSFUIM07B(161590),     -- for V800R008C10 ME0DSFUIM07B(SBOM),480Gbps Switch Fabric Unit B(SFUI-480-B)
                virentME60DEVME0DSFUIM07C(161591),     -- for V800R008C10 ME0DSFUIM07C(SBOM),480Gbps Switch Fabric Unit C(SFUI-480-C)
      --V8R8C10 ME END
--  BGW         Add for BGW series V6R8C10
                fnameBGW9916(561190),                -- BGW9916 FRAME
                virentBGW9916DEVBGWD0MPUB470(161568),            -- for V600R008C10 BGWD0MPUB470(SBOM),BGW9916 Main Processing Unit B4
                virentBGW9916DEVBGWDSFUIE07B(161569),            -- for V600R008C10 BGWDSFUIE07B(SBOM),200Gbps Switch Fabric Unit B(SFUI-200-B)
                virentBGW9916DEVBGWDBPUFA070(161570),            -- for V600R008C10 BGWDBPUFA070(SBOM),Flexible Card Bonding Processing Unit(BPUF-100)
                virentBGW9916DEVBGWDBPUFC870(161571),            -- for V600R008C10 BGWDBPUFC870(SBOM),Flexible Card Bonding Processing Unit(BPUF-200)
                virentBGW9916DEVBGWDASUFD070(161572),     -- for V600R008C10 BGWDASUFD070(SBOM), Flexible Card Aggregation Service Unit 160(ASUF-160)
                subbnameBGW9916DEVBGWD00SPD070(161573),   -- for V600R008C10 BGWD00SPD070(SBOM), Aggregation Service Daught Card(SP160)
                subbnameBGW9916DEVBGWD0L5XF070(161574),   -- for V600R008C10 BGWD0L5XF070(SBOM), 5-Port 10GBase LAN/WAN-SFP+ Flexible Card(BP100)
                subbnameBGW9916DEVBGWD0EFGF070(161575),   -- for V600R008C10 BGWD0EFGF070(SBOM), 24-Port 100/1000Base-X-SFP Flexible Card(BP100)
                subbnameBGW9916DEVBGWD0LAXF070(161576),   -- for V600R008C10 BGWD0LAXF070(SBOM), 10-Port 10GBase LAN/WAN-SFP+ Flexible Card(BP200)
                virentME60DEVME0D00SNCA00(161578),        -- for V600R008C20 VSUF ME SNC Atomic Router

                -- from 163000 to 163499 is for ME60 OTHER Whole board
                virentME60DEVFCARD(163000),          -- the old whole board of Flex-card saled before V3R8 version in ME60(whithout SBOM information)
-- atn
                virentATNDEVANE7MPUG0(225280),     -- Main Processing Unit G(Including 1*1G CF Card)
                virentATNDEVANE7NPUI20(225281),    -- Network Processing Unit Integrated with 2-Port 10GBase LAN/WAN-XFP
                virentATNDEVANE7PIUD0(225282),    -- Power Supply Unit
--ATN910&950, ATN950B

               virentATNBoard(225290),          --Unknown board type
               virentATNCXPG(225291),           --System control, switching and timing board, with 4x FE service interfaces, 2x GE service interfaces, and 16x E1 interfaces (matching 75-ohm E1)
               virentATNCXPH(225292),           --System control, switching and timing board, with 4x FE service interfaces, 2x GE service interfaces, and 16x E1 interfaces (matching 120-ohm E1)
               virentATNCXPI(225293),           --System control, switching and timing board, with 8x FE service interfaces, 2x GE service interfaces
               virentATNCXP(225294),             --System control, switching and timing board
               virentATNCXPA(225475),            --System control, switching and timing board for ATN950B
               virentATNCXPB(225476),            --System control, switching and timing board for ATN950B
               virentATNCXPC(225478),            --System control, switching and timing board for ATN950B
               virentATNC2CXPL(225493),         --System control, switching and timing board, with 2GE(o),4GE/FE(o),4GE/FE(e)
               virentATNC2CXPI(225501),         --System control, switching and timing board, with 2GE(o),4FE(o),4FE(e)
               virent910I-AC(225484),           --System control, switching and timing board, with 4GE(o),4GE/FE(o),4GE/FE(e),AC POWER
               virent910I-DCA(225485),           --System control, switching and timing board, with 4GE(o),4GE/FE(o),4GE/FE(e),DC POWER
               virent910I-DCB(225486),           --System control, switching and timing board, with 16E1,4GE(o),4GE/FE(o),4GE/FE(e),DC POWER
               virent910I-C-ACA(225487),         --System control, switching and timing board, with 16E1,4GE(o),4GE/FE(o),4GE/FE(e),AC POWER,support 1588ACR
               virent910I-TC-DC(225488),        --System control, switching and timing board, with 16E1,4GE(o),4GE/FE(o),4GE/FE(e),DC POWER,support 1588ACR,heat box
               virent910I-DCC(225489),           --System control, switching and timing board, with 16E1,4GE(o),4GE/FE(o),4GE/FE(e),4FE,DC POWER
               virent910I-C-ACB(225498),         --System control, switching and timing board, with 16E1,2GE(o),4GE/FE(o),4GE/FE(e),AC POWER,support 1588ACR
               virent910I-DCD(225499),           --System control, switching and timing board, with 16E1,2GE(o),4GE/FE(o),4GE/FE(e),DC POWER
               virent910I-C-ACC(225502),         --System control, switching and timing board, with 16E1,4GE(o),4FE(o),2GE/FE(e),2FE(e),AC POWER,support 1588ACR
               virent910I-DCE(225503),           --System control, switching and timing board, with 16E1,4GE(o),4FE(o),2GE/FE(e),2FE(e),4FE(e),DC POWER
               virent910I-P-AC(225511),         --System control, switching and timing board, with 4GE(o),4GE/FE(o),4GE/FE(e),poe
               virentANP1CXPC(225512),           --System control, switching and timing board, with 2Combo,2GE/FE (o),2GE/FE(e)
               virentANP1CXPD(225513),         --System control, switching and timing board, with 2Combo,2GE(o),2GE/FE(o)
               virentANP1CXPE(225514),           --System control, switching and timing board, with 1Combo,1GE/FE (o),2GE/FE(e),poe
               virent905A-V(225524),             --ATN 905,ANP1CXPF,System Control,Cross-connect and Multi-protocol Process Unit,2*1
               bnameATND2CXPA(225525),           --ATN 950B,AND2CXPA, System Control,Cross-connect and Multi-protocol Process Unit,1*1
               virentATN910BCXPA(225526),        --Manufactured Board,ATN 910B,ANG1CXPA,1*1
               virentATN910BCXPB(225527),        --Manufactured Board,ATN 910B,ANG1CXPB,1*1
               bnameATND2CXPB(225531),           --Manufactured Board,ATN 950B,AND2CXPB,1*1
               bnameATND2CXPE(225532),           --Manufactured Board,ATN 950B,AND2CXPE,1*1
               virent910I-D-AC(225536),          --System control,switching and timing board,with 2Combo,2GE/FE(o),2GE/FE(e),AC POWER
               virent910I-D-DC(225537),          --System control,switching and timing board,with 2Combo,2GE/FE(o),2GE/FE(e),DC POWER
               virentANF1CXPF(225538),           --ATN 910I,ANF1CXPF,System Control,Cross-connect and Multi-protocol Process Unit,1*1
               virentANF1CXPG(225539),           --ATN 910I,ANF1CXPG,System Control,Cross-connect and Multi-protocol Process Unit,1*1
               virentANP1CXPH(225546),           --ATN 905,ANP1CXPH,System Control,Cross-connect and Multi-protocol Process Unit-1*1
               virentANP1CXPG(225547),           --ATN 905,ANP1CXPG,System Control,Cross-connect and Multi-protocol Process Unit-1*1
               bnameANP1CXPE(225550),            --ATN 950B,AND1CXPE,System Control,Cross-connect and Multi-protocol Process Unit
               bnameANP1CXPF(225551),            --ATN 950B,AND1CXPF,System Control,Cross-connect and Multi-protocol Process Unit
               virentATN910B-2DC(225548),        --ATN 910B,ANGM1HSCD,ATN 910B 2 channel DC System,with 24*GE/FE(o),4*10GE(o)
               virentATN910B-2AC(225549),        --ATN 910B,ANGM2HSCA,ATN 910B 2 channel AC System,with 24*GE/FE(o),4*10GE(o)
               virentATNANP1CXPK-DC(225552),     --System control,switching and timing board,with 5GE/FE(e),DC POWER
               virentATNANP1CXPE-DC(225553),     --System control,switching and timing board,with 2GE/FE(e),1Combo,1GE/FE(o),DC POWER
               virentATN910B-EAC(225554),              --ATN 910B,ANGM1HSCA,ATN 910B AC System,with 24*GE/FE(o),4*10GE(o)
               virentATNANP1CXPJ-AC(225555),      --System control,switching and timing board,with 2GE/FE(o)+2GE/FE(e)+4E1,DC POWER
               virentANJ1CXP01(225556),                  --ATN 980B,ANJ1CXP01,System Control,Cross-connect and Multi-protocol Process Unit
               virentATN910BANG1CXPD-DC(225560),   --ATN 910B 2 channel DC System,with 8*GE/FE(e),16*GE/FE(o),4*10GE(o)
               virentATN910BANG1CXPD-AC(225561),   --ATN 910B 2 channel AC System,with 8*GE/FE(e),16*GE/FE(o),4*10GE(o)
               virentANKD00CXPB00(225569),         --ATN950C, System Control,Cross-connect and Multi-protocol Process Unit with 360G
               virentANKD00CXPA00(225570),         --ATN950C, system Control,Cross-connect and Multi-protocol Process Unit
               virentANGMHSTA0111(225571),         --ATN 910C 2 channel DC System,with 4*10GE(o), 8*10GE /GE/FE(o),16*GE/FE(o)
               virentANGMHSTB0111(225572),         --ATN 910C 2 channel AC System,with 4*10GE(o), 8*10GE /GE/FE(o),16*GE/FE(o)
               virentANGMHSTA0211(225573),         --ATN 910C 2 channel DC System,with 4*10GE(o), 8*10GE /GE/FE(o),8*GE/FE(o),8*GE/FE(e)
               virentANGMHSTB0211(225574),         --ATN 910C 2 channel AC System,with 4*10GE(o), 8*10GE /GE/FE(o),8*GE/FE(o),8*GE/FE(e)
               virentANGMHSTD0100(225575),         --ATN 910C 2 channel DC System,with 4*10GE(o), 8*10GE /GE/FE(o),8*GE/FE(e),16E1
               virentANGMHSTD0200(225576),         --ATN 910C 2 channel AC System,with 4*10GE(o), 8*10GE /GE/FE(o),8*GE/FE(e),16E1
               virentANGMHSTA0311(225592),        --ATN 910C-A,ANGM13HSTA,ATN 910C-A AC+DC system, with 4*10GE(o), 8*10GE/GE/FE(o), 16*GE/FE(o)
               virentANGMHSTB0311(225593),        --ATN 910C-B,ANGM13HSTB,ATN 910C-B AC+DC system,with 4*10GE(o), 8*10GE/GE/FE(o), 8*GE/FE(o), 8*GE/FE(e)
               virentANGMHSTD0311(225594),        --ATN 910C-D,ANGM13HSTD,ATN 910C-D AC+DC system,with 4*10GE(o),8*10GE/GE/FE(o),8*GE/FE(e),16E1
               virentANJ0002CXP00(225595),        --ATN 980B,ANJ2CXP,System Control,Cross-connect and Multi-protocol Process Unit with 360G,1*1
               virentANK200CXPA00(225596),        --ATN 950C,ANK2CXPA,System Control,Cross-connect and Multi-protocol Process Unit with 360G,1*1
               virentANPM001AICF0(225601),       -- ATN905-F System,AC,2*GE/FE Combo,2*GE/FE(o),2*GE/FE(e)
               virentANPM001DICF0(225603),       -- ATN905-F System,DC,2*GE/FE Combo,2*GE/FE(o),2*GE/FE(e)
               virentANPM001AICG0(225661),       -- ATN 905-G,ANP2CXPD,ATN 905-G System,AC,2*GE/FE Combo,2*GE/FE(o),2*GE/FE(e)
               virentANKD01CXPA00(225345),       --ATN 950C,ANK3CXPA0,System Control,Cross-connect and Multi-protocol Process Unit with 480G
               virentANDD03CXPA00(225604),       -- ATN950B, System Control, Cross-connect and Multi-protocol Process Unit
               virentANKD00CXPB02(225605),       -- ATN950C, System Control,Cross-connect and Multi-protocol Process Unit B
               virentANGMHSTF0110(225606),       -- ATN 910C-F,ANGMHSTF0110,ATN 910C-F DC system,with 6*10GE(o),20*GE/FE(o),4*GE/FE
               virentANGMHSTE0110(225608),       -- ATN 910C-E,ANGMHSTE0110,ATN 910C-E DC system,with 4*25GE/2*50GE combo,8*10GE+8*GE,2*25GE+2*10GE+12*GE
               virentANGMHSTH0100(225610),         -- ATN 910C-H,ANGMHSTH0100,ATN 910C-H DC Basic Configuration(Includes Fixed Enable Interface (4*10GE/GE/FE(o)+ 4*GE/FE(o)+4*GE/FE(e))/Dual Power/FAN/Chassis)
               virentANGMHSTS0100(225611),         -- ATN 910C-S,ANGMHSTS0100,ATN 910C-S DC Basic Configuration(Includes Fixed Enable Interface (5*10GE/GE/FE(o)+3*GE/FE(o)+4*GE/FE(e))/Dual Power/FAN/Chassis)
               virentANND00CXPA00(225612),         -- ATN 980C,ANN1CXPA00,System Control,Cross-connect and Multi-protocol Process Unit with 800G
               virentANGMHSTG0100(225613),         -- ATN 910C-G,ANGMHSTG0100,ATN 910C-G, DC Power, Port Capacity 16*10GE+12*GE(o)+4*GE(e), Default 2*10GE+8*GE
               virentANGMHSTG0200(225614),         -- ATN 910C-G,ANGMHSTG0200,ATN 910C-G, AC Power, Port Capacity 16*10GE+12*GE(o)+4*GE(e), Default 2*10GE+8*GE
               virentANRD00CXPA00(225336),         --ATN 950D,ANR1CXPA00,System Control, Cross-connect and Multi-protocol Process Unit with 160G
               virentANRD00CXPA01(225337),         --ATN 950D,ANR1CXPA10,System Control, Cross-connect and Multi-protocol Process Unit with 160G
               virentANRD01CXPA00(225338),         --ATN 950D,ANR2CXPA0,System Control, Cross-connect and Multi-protocol Process Unit with 400G
               virentANRD01CXPB00(225339),         --ATN 950D,ANR2CXPB0,System Control, Cross-connect and Multi-protocol Process Unit with 800G
               virentANRD01CXPC00(225344),         --ATN 950D,ANR2CXPC0,System Control, Cross-connect and Multi-protocol Process Unit with 480G
               virentCR8DCXP160C0(225350),         -- V800R012C00 for CR8DCXP160C0(SBOM) NetEngine 8000 M6,CR81CXP160AS,System Control,Cross-connect and Multi-protocol Process Unit (CXP-160)
               virentCR8DCXP160C1(225351),         -- V800R012C00 for CR8DCXP160C1(SBOM) NetEngine 8000 M6,CR81CXP160A,System Control,Cross-connect and Multi-protocol Process Unit (CXPA-160)
               virentCR8DCXP160K0(226353),             -- V800R012C10 for CR8DCXP160K0(SBOM) NetEngine 8000 M6K,CR81CXP160C,System Control,Cross-connect and Multi-protocol Process Unit (CXP-160-K)
               virentCR8DCXP160K1(226354),             -- V800R012C10 for CR8DCXP160K1(SBOM) NetEngine 8000 M6K,CR81CXP160D,System Control,Cross-connect and Multi-protocol Process Unit (CXP-160-K1)
               virentANND00CXPA02(229580),         -- V800R012C10 for ANND00CXPA02  ATN 980C,ANN2CXPA20,System Control,Cross-connect and Multi-protocol Process Unit with 360G
               virentANND01CXPA03(229581),         -- V800R012C10 for ANND01CXPA03  ATN 980C,ANN1CXPA21,System Control,Cross-connect and Multi-protocol Process Unit with 360G
               virentANHMHSTA0100(229582),         -- V800R012C10 for ANHMHSTA0100  ATN 910D-A, DC Power, Port Capacity 4*100GE/50GE + 16*25GE/10GE/GE/FE + 8*10GE/GE/FE, default all the GE/FE ports is enabled
               virentANHMHSTA0200(229583),         -- V800R012C10 for ANHMHSTA0200  ATN 910D-A, AC Power, Port Capacity 4*100GE/50GE + 16*25GE/10GE/GE/FE + 8*10GE/GE/FE, default all the GE/FE ports is enabled
               virentANRD00CXPB00(229584),         -- V800R012C10 for ANRD00CXPB00 ATN 950D,ANR1CXPB00,System Control, Cross-connect and Multi-protocol Process Unit with 160G
               virentANRD00CXPB01(229585),         -- V800R012C10 for ANRD00CXPB01 ATN 950D,ANR1CXPB10,System Control, Cross-connect and Multi-protocol Process Unit with 160G
               virentTPND02CXPA00(229586),         -- V800R012C10 for TPND02CXPA00  OptiX PTN 980,TPN2CXPA0,System Control,Cross-connect and Multi-protocol Process Unit
               virentTPQD01CXPA00(229587),         -- V800R012C10 for TPQD01CXPA00  OptiX PTN 990E,TPQ1CXPA0,System Control,Cross-connect and Multi-protocol Process Unit
               virentTPRD01CXPA00(229588),         -- V800R012C10 for TPRD01CXPA00  Optix PTN 970C,TPR1CXPA0,System Control,Cross-connect and Multi-protocol Process Unit
               virentTPSD01CXPA00(229589),         -- V800R012C10 for TPSD01CXPA00  Optix PTN 916F,TPS1CXPA0,System Control,Cross-connect and Multi-protocol Process Unit
               virentTPRD01CXPA02(229597),         -- OptiX PTN 970C,TPR1CXPA1,System Control,Cross-connect and Multi-protocol Process Unit
               virentTPQD01CXPA01(229590),         -- OptiX PTN 990E,TPQ1CXPA0,System Control,Cross-connect and Multi-protocol Process Unit
               virentTPQD01CXPA02(229591),         -- OptiX PTN 990E,TPQ1CXPA1,System Control,Cross-connect and Multi-protocol Process Unit
               virentTPSM0HOSTB01(229592),         -- PTN 916-F - 2 channels AC entries,with 6*10GE(o),14*GE/FE(o),4*GE/FE(e),16*E1
               virentTPSM0HOSTA02(229593),         -- PTN 916-F - 2 channels DC entries,with 6*10GE(o),14*GE/FE(o),4*GE/FE(e),16*E1
               virentTPSM0HOSTB02(229594),         -- PTN 916-F - 2 channels AC entries,with 6*10GE(o),14*GE/FE(o),4*GE/FE(e),16*E1
               virentTPSM0HOSTA03(229595),         -- PTN 916-F - 2 channels DC entries,with 6*10GE(o),14*GE/FE(o),4*GE/FE(e),16*E1
               virentTPSM0HOSTB03(229596),         -- PTN 916-F - 2 channels AC entries,with 6*10GE(o),14*GE/FE(o),4*GE/FE(e),16*E1
               virentCR8PM1DBASC1(226361),         -- NetEngine 8000 M1D,CR8PM1DBASC1,NetEngine 8000 M1D Basic Configuration, DC Power (Port Capacity 4*100GE/50GE+16*25GE/10GE/GE/FE+8*10GE/GE/FE,exclude auxiliary materials)
              virentCR8PM1DBASCA(226367),         -- NetEngine 8000 M1D,CR8PM1DBASCA,NetEngine 8000 M1D Basic Configuration, AC Power (Port Capacity 4*100GE/50GE+16*25GE/10GE/GE/FE+8*10GE/GE/FE,exclude auxiliary materials)
               virentCR8PM1DBASCC(226368),         -- NetEngine 8000 M1D,CR8PM1DBASCC,NetEngine 8000 M1D Basic Configuration, AC Power (Port Capacity 4*100GE/50GE+16*25GE/10GE/GE/FE+8*10GE/GE/FE,exclude auxiliary materials)
               virentCR8PM1DBASC3(226365),         -- NetEngine 8000 M1D,CR8PM1DBASC3,NetEngine 8000 M1D Basic Configuration, DC Power (Port Capacity 4*100GE/50GE+16*25GE/10GE/GE/FE+8*10GE/GE/FE,exclude auxiliary materials)

               virentTPQD02CXPA03(229670),          -- OptiX PTN 990E,TPQ2CXPA2,System Control,Cross-connect and Multi-protocol Process Unit
               virentTPQD01CXPA03(229671),          -- OptiX PTN 990E,TPQ1CXPA2,System Control,Cross-connect and Multi-protocol Process Unit
               virentTPQD01CXPA04(229672),          -- OptiX PTN 990E,TPQ1CXPA3,System Control,Cross-connect and Multi-protocol Process Unit
               virentTPTD01CXPA03(229673),          -- OptiX PTN 980B,TPT1CXPA03,System Control,Cross-connect and Multi-protocol Process Unit
               virentTPRD01CXPA03(229674),          -- OptiX PTN 970C,TPR1CXPA2,System Control,Cross-connect and Multi-protocol Process Unit
               virentTPRD01CXPA04(229675),          -- OptiX PTN 970C,TPR1CXPA3,System Control,Cross-connect and Multi-protocol Process Unit
               
               virentANSD00CXPB00(226103),         -- V800R012C10 for ANSD00CXPB00 ATN-950C,ANS1CXPA00,System Control, Cross-connect and Multi-protocol Process Unit with 160G
               virentANSD01CXPA00(226104),         -- V800R012C10 for ANSD01CXPA00 ATN-950C,ANS2CXPA00,System Control, Cross-connect and Multi-protocol Process Unit with 400G
               virentANSD01CXPB00(226105),         -- V800R012C10 for ANSD01CXPB00 ATN-950C,ANS2CXPB00,System Control, Cross-connect and Multi-protocol Process Unit with 800G
               virentCR8DCXP160C2(226106),             -- V800R012C10 for CR8DCXP160C2(SBOM) NetEngine 8000 M6,System Control,Cross-connect and Multi-protocol Process Unit (CXP-160-A)
               virentCR8DCXP160C3(226107),             -- V800R012C10 for CR8DCXP160C3(SBOM) NetEngine 8000 M6,System Control,Cross-connect and Multi-protocol Process Unit (CXPA-160-A)
               virentANGMHSTK0100(229789),         --ATN 910C-K, DC Power, Port Capacity 16*10GE/GE/FE+8*GE/FE(o)+4*GE/FE(e)+16*E1
               virentANGMHSTK0200(229790),         --ATN 910C-K, AC Power, Port Capacity 16*10GE/GE/FE+8*GE/FE(o)+4*GE/FE(e)+16*E1
               virentANGMHSTM0100(229791),         --ATN 910C-M, DC Power, Port Capacity 16*10GE/GE/FE+8*GE/FE(o)+4*GE/FE(e)
               virentANGMHSTM0200(229792),         --ATN 910C-M, AC Power, Port Capacity 16*10GE/GE/FE+8*GE/FE(o)+4*GE/FE(e)
               virentANGMHSTK0300(229793),         --ATN 910C-K, AC+DC Power, Port Capacity 16*10GE/GE/FE+8*GE/FE(o)+4*GE/FE(e)+16*E1
               virentANGMHSTM0300(229794),         --ATN 910C-M, AC+DC Power, Port Capacity 16*10GE/GE/FE+8*GE/FE(o)+4*GE/FE(e)
               virentANND00CXPA01(225301),         -- V800R012C10 for ANND00CXPA01  ATN 980C,ANN1CXPA10,System Control,Cross-connect and Multi-protocol Process Unit with 320G
               virentANHMHSTA0120(225302),         -- V800R012C11 for ANHMHSTA0120  ATN 910D-A, DC Power, Port Capacity 4*100GE/50GE + 16*25GE/10GE/GE/FE + 8*10GE/GE/FE, default all the GE/FE ports is enabled 
               virentANHMHSTA0220(225303),         -- V800R012C11 for ANHMHSTA0220  ATN 910D-A, AC Power, Port Capacity 4*100GE/50GE + 16*25GE/10GE/GE/FE + 8*10GE/GE/FE, default all the GE/FE ports is enabled 
               virentANHMHSTA0330(225306),            --V800R013C00 for ANHMHSTA0330  ATN 910D-A, AC+DC Power, Port Capacity 4*100GE/50GE + 16*25GE/10GE/GE/FE + 8*10GE/GE/FE, default all the GE/FE ports is enabled
               virentANHMHSTA4800(225307),         -- V800R022C00 for ANHMHSTA4800  ATN 910D-A, DC Power, Port Capacity 2*100GE/50GE+4*25GE/10GE/GE/FE+16*10GE/GE/FE+4*GE/FE, default all the GE/FE ports is enabled
               virentANHMHSTA4801(225308),         -- V800R022C00 for ANHMHSTA4801  ATN 910D-A, AC Power, Port Capacity 2*100GE/50GE+4*25GE/10GE/GE/FE+16*10GE/GE/FE+4*GE/FE, default all the GE/FE ports is enabled
               virentANND00CXPB00(225304),         -- V800R013C00 for ANND00CXPB00  ATN 980C,ANN2CXPB0,System Control,Cross-connect and Multi-protocol Process Unit with 800G
               virentANND00CXPB03(225305),         -- V800R013C00 for ANND00CXPB03  ATN 980C,ANN2CXPB3,System Control,Cross-connect and Multi-protocol Process Unit with 360G
               virentANTD00CXPA00(227797),         --ATN 980D,ANT1CXPA00,System Control,Cross-connect and Multi-protocol Process Unit with 800G
               virentANTD00CXPA03(227897),         --ATN 980D,ANT1CXPA00,System Control,Cross-connect and Multi-protocol Process Unit with 360G
               virentANTD00CXPA01(227997),         --ATN 980D,ANT1CXPA00,System Control,Cross-connect and Multi-protocol Process Unit with 320G
               virentANTD00CXPA02(227998),         --ATN 980D,ANT1CXPA20,System Control,Cross-connect and Multi-protocol Process Unit with 360G
               virentANPM001AICG1(225662),         --ATN 905-G System,AC,2*GE/FE Combo,2*GE/FE(o),2*GE/FE(e)
               virentANGMHSTH0200(225615),         -- ATN 910C-H,ANGMHSTH0200,ATN 910C-H AC Basic Configuration(Includes Fixed Enable Interface (4*10GE/GE/FE(o)+4*GE/FE(o)+4*GE/FE(e))/Dual Power/FAN/Chassis)
               virentANGMHSTS0200(225616),         -- ATN 910C-S,ANGMHSTS0200,ATN 910C-S AC Basic Configuration(Includes Fixed Enable Interface (5*10GE/GE/FE(o)+3*GE/FE(o)+4*GE/FE(e))/Dual Power/FAN/Chassis)
               virentANND01CXPA01(225663),         -- V8R13C00 for ANND01CXPA01(SBOM) ATN 980C,ANN2CXPA10,System Control,Cross-connect and Multi-protocol Process Unit with 800G
               virent8090DEVANGMHSTH0101(226375),  -- V8R22C00 for ANGMHSTH0101(SBOM) ATN 910C,ANG1CXPQ,ATN 910C-H DC Basic Configuration(Includes Fixed Enable Interface (4*10GE/GE/FE(o)+4*GE/FE(o)+4*GE/FE(e))/Dual Power/FAN/Chassis)
               virent8090DEVANGMHSTS0101(226376),  -- V8R22C00 for ANGMHSTS0101(SBOM) ATN 910C,ANG1CXPQ,ATN 910C-S DC Basic Configuration(Includes Fixed Enable Interface (5*10GE/GE/FE(o)+3*GE/FE(o)+4*GE/FE(e))/Dual Power/FAN/Chassis)
               virent8090DEVANGMHSTH0201(226377),  -- V8R22C00 for ANGMHSTH0201(SBOM) ATN 910C,ANG1CXPQ,ATN 910C-H AC Basic Configuration(Includes Fixed Enable Interface (4*10GE/GE/FE(o)+4*GE/FE(o)+4*GE/FE(e))/Power/FAN/Chassis)
               virent8090DEVANGMHSTS0201(226378),  -- V8R22C00 for ANGMHSTS0201(SBOM) ATN 910C,ANG1CXPQ,ATN 910C-S AC Basic Configuration(Includes Fixed Enable Interface (5*10GE/GE/FE(o)+3*GE/FE(o)+4*GE/FE(e))/Power/FAN/Chassis)
 --etn :      0x000ad000~0x000adfff(708608~712703)
              virentETN500-A(708608),                 --ETN500-A System,2GE/FE(O)+2GE/FE(E)+2GE/FE(Combo),AC
              virentETN500-B(708609),                 --ETN500-B System,2GE/FE(O)+2GE/FE(E)+2GE/FE(Combo),DC
              virentETN500-C(708610),                 --ETN500-C System,GE/FE(O)+2GE/FE(E)+4E1,AC
              virentLND1MXUA(708611),                 --Cross-connect and Multi-protocol Process Unit
              virentLNPM001AICF0(708625),             --ETN500-F System,AC,2*GE/FE Combo,2*GE/FE(o),2*GE/FE(e)
              virentCP8PHST20A00(226372),         -- V8R21C00 for CP8PHST20A00(SBOM) NetEngine A820 AC System (6*10GE/GE/FE+4*GE/FE(o), 8*GE/FE(e), Default 2*10GE/GE/FE+8*GE/FE(o)+8*GE/FE(e))
              virentCP8PHST10A00(226374),         -- V8R21C00 for CP8PHST10A00(SBOM) NetEngine A810 AC System (2*GE/FE Combo, 2*GE/FE(o), 2*GE/FE(e))
              virentCP8PHST2MA00(229515),           -- V8R21C00 for CP8PHST2MA00(SBOM) NetEngine A820 M AC System (2*10GE+8*GE/FE(o)+8*GE/FE(e))
              virent8090DEVANND00CXPA02(227999),  -- V8R22C10 ATN 980C,ANN1CXPA29,System Control,Cross-connect and Multi-protocol Process Unit with 360G
              virent8090DEVANND02CXPAU4(228000),  -- V8R22C10 ATN 980C,ANN3CXPA00,System Control,Cross-connect and Multi-protocol Process Unit with 400G
              virent8090DEVANND02CXPAE1(228005),  -- V8R23C00 ATN 980C,ANN3CXPA20,System Control,Cross-connect and Multi-protocol Process Unit with 800G
              virent8090DEVANND02CXPAQ1(228006),  -- V8R24C10 ATN 980C,ANN3CXPA21,System Control,Cross-connect and Multi-protocol Process Unit with 800G
              virent8090DEVANND02CXPAQ2(228007),  -- V8R24C10 ATN 980C,ANN3CXPA11,System Control,Cross-connect and Multi-protocol Process Unit with 360G
              virent8090DEVIG2D0MPUAXCA(165919),   -- V8R24C10 for IG2D0MPUAXCA(SBOM) SIG16000 Main Processing Unit A10A(MPUA10A)
              virent8090DEVIG2DSFUI2TD1(165920),   -- V8R24C10 for IG2DSFUI2TD1(SBOM) SIG16000 X4 2Tbps Switch Fabric Unit(SFUIA-2T-A)
              virent8090DEVIG2D8SFU9TD0(165921),   -- V8R24C10 for IG2D8SFU9TD0(SBOM) SIG16000 X4 9.6Tbps Switch Fabric Unit(SFUIA-9T6-D)
              virent8090DEVIG2DSFUI2TD2(165922),   -- V8R24C10 for IG2DSFUI2TD2(SBOM) SIG16000 X8 2Tbps Switch Fabric Unit(SFUIA-2T-B)
              virent8090DEVIG2DSFUI9TB1(165923),   -- V8R24C10 for IG2DSFUI9TB1(SBOM) SIG16000 X8 9.6Tbps Switch Fabric Unit(SFUIA-9T6-B)
              virent8090DEVIG2DLPUFT072(165924),   -- V8R24C10 for IG2DLPUFT072(SBOM) Flexible Card Line Processing Unit (LPUF-1TA)
              virent8090DEVIG2DLPUFT6TA(165936),   -- V8R24C10 for IG2DLPUFT6TA(SBOM) Flexible Card Line Processing Unit(LPUF-6T4A)
              virent8090DEVIG2D8LPU3TC1(165925),   -- V8R24C10 for IG2D8LPU3TC1(SBOM) Flexible Card Line Processing Unit(LPUF-3T2)
              virent8090DEVCP8PHST1MA00(229514),           -- V8R21C00 for CP8PHST1MA00(SBOM) NetEngine A811 M AC System (10*GE/FE(o), 8*GE/FE(e))
              virent8090DEVCP8PHST10A03(229520),           -- V8R21C00 for CP8PHST10A03(SBOM) NetEngine A811 AC System (10*GE/FE(o), 8*GE/FE(e))
              virent8090DEVCP8PHST10A06(229524),           -- V8R21C10 for CP8PHST10A06(SBOM) NetEngine A811 AC System (10*GE/FE(o)+8*GE/FE(e))
              virent8090DEVHGFM0HOSTB00(229522),           -- V8R21C00 for HGFM0HOSTB00(SBOM) HG-FM CPE-02 AC Power,with 6*GE/FE(o),8*GE/FE(e)
              virent8090DEVHGFM0HOSTB02(229568),           -- V8R23C10 for HGFM0HOSTB02(SBOM) HG-FM CPE-02 AC Power,with 6*GE/FE(o),8*GE/FE(e)
              virent8090DEVCP8PHST1MA02(229523),           -- V8R21C00 for CP8PHST1MA02(SBOM) NetEngine A810 M AC System (10*GE/FE(o), 8*GE/FE(e))
              virent8090DEVHGFM0HOSTC00(229529),           -- V8R22C00 for HGFM0HOSTC00(SBOM) HG-FM CPE-03 AC Power,with 2*10GE Fine Granularity Unit(o),4*10GE/GE/FE(o),4*GE/FE(o),8*GE/FE(e)
              virent8090DEVCP8PHST5MA01(229530),           -- V8R22C00 for CP8PHST5MA01(SBOM) NetEngine A850 M AC System (4*GE/FE(o)+2*GE(o)+8*GE/FE(e)+5G(dual SIM))
              virent8090DEVHGFM0HOSTA00(229531),           -- V8R22C00 for HGFM0HOSTA00(SBOM) HG-FM CPE-01 AC Power,with 5G module ,6*GE/FE(o),8*GE/FE(e)
              virent8090DEVHGFM0HOSTA02(229567),           -- V8R23C10 for HGFM0HOSTA02(SBOM) HG-FM CPE-01 AC Power,with 5G module ,4*GE/FE(o),2*GE(o),8*GE/FE(e)
              virent8090DEVCP8PHST1MA04(229532),           -- V8R22C00 for CP8PHST1MA04(SBOM) NetEngine A813 M AC System (6*GE/FE(o)+8*GE/FE(e))
              virent8090DEVTPXM0HOSTA00(229533),           -- V8R22C00 for TPXM0HOSTA00(SBOM) PTN 91A-F DC Power,with 3*10G/GE/FE(o),7*GE/FE(o),4*GE/FE(e)
              virent8090DEVTPWM0HOSTA02(229534),           -- V8R22C00 for TPWM0HOSTA02(SBOM) PTN 910D-F AC Power,with 2*50GE(o),6*10GE/GE/FE(o),10*GE/FE(o),4*GE/FE(e)
              virent8090DEVTPWM0HOSTB02(229535),           -- V8R22C00 for TPWM0HOSTB02(SBOM) PTN 910D-F DC Power,with 2*50GE(o),6*10GE/GE/FE(o),10*GE/FE(o),4*GE/FE(e)
              virent8090DEVTPXM01HSTA01(229536),           -- V8R22C00 for TPXM01HSTA01(SBOM) PTN 91A-F,3*10G/GE/FE(o)+7*GE/FE(o)+4*GE/FE(e)
              virent8090DEVTPXM0HOSTA01(229543),           -- V8R22C00 for TPXM0HOSTA01(SBOM) PTN 91A-F,3*10G/GE/FE(o)+7*GE/FE(o)+4*GE/FE(e)
               virent8090DEVTPZM0HOSTA00(229537),           -- V8R22C10 for TPZM0HOSTA00(SBOM) SPN 907 - AC Power,with 4*GE/FE(o),4*GE/FE(e)
               virent8090DEVTPZM0HOSTA02(229538),           -- V8R22C10 for TPZM0HOSTA02(SBOM) SPN 907 - AC Power,with 4*GE/FE(o),4*GE/FE(e)
               virent8090DEVTPIM0HOSTA00(221266),           -- V8R24C10 for TPIM0HOSTA00(SBOM) SPN A907-I - AC Power,with 6*GE/FE(o),8*GE/FE(e) Natural heat dissipation without fans
              virent8090DEVHGFM0HOSTD00(229539),           -- V8R23C00 for HGFM0HOSTD00(SBOM) HG-FM CPE-03-A AC Power,with 2*10GE Fine Granularity Unit(o),6*GE/FE(o),4*GE/FE(e)
              virent8090DEVHGFM0HOSTE00(229553),           -- V8R23C00 for HGFM0HOSTE00(SBOM) HG-FM CPE-02-E AC Power,with 4*GE/FE(o),4*GE/FE(e),4*E1
              virent8090DEVCR8PM4BASDC2(468761),   -- V8R21C10 for CR8PM4BASDC2(SBOM) NetEngine 8000 M4 Integrated DC Chassis Components(Including DC Power,Fan Box)
              virent8090DEVCR8PM4BASDC3(468762),   -- V8R21C10 for CR8PM4BASDC3(SBOM) NetEngine 8000 M4 Integrated AC Chassis Components(Including AC Power,Fan Box)
              virent8090DEVCR8PM4BASAC2(468764),   -- V8R21C10 for CR8PM4BASAC2(SBOM) NetEngine 8000 M4 Integrated DC Chassis Components(Including DC Power,Fan Box)
              virent8090DEVCR8PM4BASAC3(468765),   -- V8R21C10 for CR8PM4BASAC3(SBOM) NetEngine 8000 M4 Integrated AC Chassis Components(Including AC Power,Fan Box)
              virent8090DEVHGFM0HOSTF01(564547),           -- V8R24C00 for HGFM0HOSTF01(SBOM) HG-FM CPE-02-S AC Power,with 4*GE/FE(o),4*GE/FE(e),includes auxiliary materials"
              virent8090DEVTPYM0HOSTA00(564557),    -- V8R25C10 for TPYM0HOSTA00(SBOM) SPN A907-S AC Power,with 4*GE/FE(o),4*GE/FE(e)
              virent8090DEVTPVM0HOSTA02(229544),           -- V8R22C00 for TPVM0HOSTA02(SBOM) PTN 917-F - AC Power,with 2*10GE Fine Granularity Unit(o),8*GE/FE(o),8*GE/FE(e)
			  
-- NE0508E:    0x000AC000~0x000Acfff (704512 ~ 708607)
               bnameNE08ECXPB(704512),              --System Control,Cross-connect and Multi-protocol Process Unit
               bnameNE08ECXPE(704513),              --System Control,Cross-connect and Multi-protocol Process Unit
               bnameNE05ECXPL(704514),              --System Control,Cross-connect and Multi-protocol Process Unit
               virentNE05E-SE(704515),              --44G System
               virentNE05E-SF(704516),              --44G System, with 16E1
               virentNE05E-SG(704517),              --12G DC Systemsupport Temperature Harden,natural heat dissipation
               virentNE05E-SH(704518),              --12G DC System with 16 Channels E1,support Temperature Harden,natural heat dissipation
               virentNE05E-SI(704519),                --12G System,AC,4GE/FE combo enabled,Support 4*PoE+
               virentNE05E-SJ(704520),               --NE05E-SJ System,Indoor,AC,2*GE/FE Combo,2*GE/FE(o),2*GE/FE(e)
               virentNE05E-SK(704521),              --NE05E-SK System,Indoor,DC,2*GE/FE Combo,2*GE/FE(o),2*GE/FE(e)
               virentNE05E-SL(704522),              --NE05E-SL System,Outdoor,AC,2*GE/FE Combo,2*GE/FE(o),2*GE(o)
               virentNE05E-SM(704523),              --NE05E-SM System,Outdoor,AC,1*GE/FE(o),1*GE/FE Combo with POE+ ,2*GE/FE(e) with PoE+
               virentNE05E-SN(704526),              --12G AC System with 16 Channels E1,support Temperature Harden,natural heat dissipation
               bnameNE08ETNF1APIU(704527),          --AC Power Interface Board
               virentNEDD00CXPA00(704535),          --NE08E, system Control,Cross-connect and Multi-protocol Process Unit
               virentNECMHSTA0100(704536),          --NE05E-SP 2 channel DC System,with 4*10GE(o), 8*10GE /GE/FE(o),16*GE/FE(o)
               virentNECMHSTB0100(704537),          --NE05E-SP 2 channel AC System,with 4*10GE(o), 8*10GE /GE/FE(o),16*GE/FE(o)
               virentNECMHSTA0211(704538),          --NE05E-SQ 2 channel DC System,with 4*10GE(o), 8*10GE /GE/FE(o),8*GE/FE(o),8*GE/FE(e)
               virentNECMHSTB0211(704539),          --NE05E-SQ 2 channel AC System,with 4*10GE(o), 8*10GE /GE/FE(o),8*GE/FE(o),8*GE/FE(e)
               virentNECM000AIC01(704572),          -- NE05E-SR System,Indoor,AC,2*GE/FE Combo,2*GE/FE(o),2*GE/FE(e)
               virentNEJD00CXPA00(704574),          -- System Control,Cross-connect and Multi-protocol Process Unit A For S9
               virentNEDD00CXPB00(704575),          -- NE08E-S6E, System Control,Cross-connect and Multi-protocol Process Unit B for S6E
               vrientNECD00CXPL00(704576),           -- NE05E-S2


 -- PTN:
               virentPTN6900DEVTNR1SCAB(229376),    --Main Processing Unit B4(Including 1*2G Memory and 1*1G CF Card)

               virentPTN6900DEVTNR1XCS40B(229377),  --40Gbps Switch Fabric Unit B
               virentPTN6900DEVTNR1XCS200B(229378), --200Gbps Switch Fabric Unit B
               virentPTN6900DEVTNR1XCS40C(229379),  --40Gbps Switch Fabric Unit C
               virentPTN6900DEVTNR1XCS200C(229380), --200Gbps Switch Fabric Unit C
               virentPTN6900DEVTNR1SCA40C(229381),    --Switch and Route Processing Unit A2(Supporting 1588v2)
               virentPTN6900DEVTNR1EX8B(229382),    --8-Port 10GBase LAN/WAN-XFP Integrated Service Unit
               virentPTN6900DEVTNR1EX4(229383),     --4-Port 10GBase LAN/WAN-XFP Integrated Service Unit (Supporting 1588v2)
               virentPTN6900DEVTNR1EX4B(229384),    --4-Port 10GBase LAN/WAN-XFP Integrated Service Unit
               virentPTN6900DEVTNR1EG48B(229385),   --48-Port 100/1000Base-X-SFP Integrated Service Unit
               virentPTN6900DEVTNR1EM40(229386),    --2-Port 10GBase LAN/WAN-XFP+24-Port 100/1000Base-X-SFP Integrated Service Unit
               virentPTN6900DEVTNR1EM40B(229387),   --2-Port 10GBase LAN/WAN-XFP+24-Port 100/1000Base-X-SFP Integrated Service Unit
               virentPTN6900DEVTNR1EG40(229388),    --40-Port 100/1000Base-X-SFP Integrated Service Unit (Supporting 1588v2)
               virentPTN6900DEVTNR1MEPF40(229389),  --Flexible Card Integrated Service Unit(four sub-slots)
               virentPTN6900DEVTNR1MEPF10(229390),  --Flexible Card Integrated Service Unit(two sub-slots)
               --for PTN6900-ChinaMobile
               virentPTN6900DEVTNRD00EX1000(229391), --10 Ports 10 Gigabit Ethernet Processing Board (Supporting 1588V2)
               virentPTN6900DEVTNRD0EX16B00(229392),    --16 Ports 10 Gigabit Ethernet Processing Board
               virentPTN6900DEVTNR1SCA200C(229393),   --200G System Control,Communication and Auxiliary Process Unit C (Including 1*2G Memory and 2*1G CF Card)
               virentPTN6900DEVTNR1CMUA(229394),    --Centralized Monitor Unit

               --for VFD
               virentPTN6900DEVTNR1SFU40B0(229395),    --40Gbps Switch Fabric Unit B
               virentPTN6900DEVTNR1SRU40A4(229396),    --Switch and Route Processing Unit A4(Including 1*2G Memory and 2*1G CF Card)
               virentPTN6900DEVTNR1SFU40C0(229397),    --40Gbps Switch Fabric Unit C
               virentPTN6900DEVTNR1MPUD0(229398),      --Main Processing Unit D(Including 1*2G Memory and 2*1G CF Card)
               virentPTN6900DEVTNR1MPUB4(229399),      --Main Processing Unit B4(Including 1*2G Memory and 2*1G CF Card)
               virentPTN6900DEVTNRD0SRUA570(229400),   --Switch and Route Processing Unit A6(Including 1*2G Memory and 2*1G CF Card)
               virentPTN6900DEVTNR1SFU100C0(229401),   --100Gbps Switch Fabric Unit C(SFUI-100-C)
               virentPTN6900DEVTNR1SFU100B0(229402),   --100Gbps Switch Fabric Unit B(SFUI-100-B)
               virentPTN6900DEVTNR1MPUG0(229403),    --Main Processing Unit G(Including 1*1G CF Card)
               virentPTN6900DEVTNR1NPUI20(229404),    --Network Processing Unit Integrated with 2-Port 10GBase LAN/WAN-XFP
               virentPTN6900DEVTNRD0MPUD270(229450),    --for V600R006C00 TNRD0MPUD270(SBOM),Main Processing Unit D2

               --for V6R6 PTN6900 packing board
               virentPTN6900DEVTNRDMEPF0600(229423),    --Multi-Protocol Ethernet Processing Flexible Card Unit-06
               virentPTN6900DEVTNRDMEPF5000(229424),    --Multi-Protocol Ethernet Processing Flexible Card Unit-50
               virentPTN6900DEVTNRDMEPFA000(229425),    --Multi-Protocol Ethernet Processing Flexible Card Unit-100
               virentPTN6900DEVTNRD000EX800(229427),    --8 Ports 10 Gigabit Ethernet Processing Board (Supporting 1588v2)
               virentPTN6900DEVTNRD00EG2400(229429),    --24 Ports FE/GE Ethernet Processing Board (Supporting 1588v2)
               virentPTN6900DEVTNRD000EX501(229436),    --5 Ports 10 Gigabit Ethernet Processing Board (Supporting 1588v2)
               virentPTN6900DEVTNRD00EG4800(229437),    --48 Ports FE/GE Ethernet Processing Board (Supporting 1588v2)
               virentPTN6900DEVTNRD00EXL200(229439),    --2 Ports 40 Gigabit Base-CFP Ethernet Processing board (Supporting 1588v2)
                  virentPTN6900DEVTNRD00EX1001(229442),    --10 Ports 10 Gigabit Ethernet Processing Board (Supporting 1588v2)

               -- V6R7 PTN packing 2012-10-11 begin
               virentPTN6900DEVTNRDMEPFA200(229443),    --for V600R007C00 TNRDMEPFA200(SBOM),Multi-Protocol Ethernet Processing Flexible Card Unit-120
               virentPTN6900DEVTNRDMEPFB400(229444),    --for V600R007C00 TNRDMEPFB400(SBOM),Multi-Protocol Ethernet Processing Flexible Card Unit-240
               virentPTN6900DEVTNRD00EX1201(229445),    --for V600R007C00 TNRD00EX1201(SBOM),12 Ports 10 Gigabit Ethernet Processing Board (Supporting 1588v2)
               virentPTN6900DEVTNRD00EXL201(229446),    --for V600R007C00 TNRD00EXL201(SBOM),2 Ports 40 Gigabit Base-CFP Ethernet Processing board (Supporting 1588v2)
               virentPTN6900DEVTNRD000EH100(229447),    --for V600R007C00 TNRD000EH100(SBOM),1 Ports 100GBase-CFP Ethernet Processing Board (Supporting 1588v2)
               virentPTN6900DEVTNRD00EX2400(229448),    --for V600R007C00 TNRD00EX2400(SBOM),24 Ports 10 Gigabit Ethernet Processing Board (Supporting 1588v2)
               virentPTN6900DEVTNRD000EH200(229449),    --for V600R007C00 TNRD000EH200(SBOM),2 Ports 100GBase-CFP Ethernet Processing Board (Supporting 1588v2)
               -- V6R7 PTN packing 2012-10-11 end

               virentPTN7900VPICTPA1EX12(229474),   --VPICTPA1EX12,12ch 10 Gigabit Ethernet Switching Processing Board-1*1
               virentPTN7900VPICTPA1EG24(229451),   --VPICTPA1EG24,24-Port Gigabit Ethernet Processing Board,1*1
               virentPTN7900VPICTPA1EXL2(229452),   --VPICTPA1EXL2,2ch 40 Gigabit Ethernet Switching Processing Board,1*1
               virentPTN7900VPICTPA1EH1(229453),    --VPICTPA1EH1,1 Ports 100GE Ethernet Processing Board
               virentPTN7900VPICTPA1EX8(229454),    --VPICTPA1EX8,8ch 10 Gigabit Ethernet Switching Processing Board-1*1
               virentPTN7900VPICTPA1CH1(229455),    --VPICTPA1CH1,16 Channels STM-1 CES Optical Interface board ,1*1
               virentPTN7900VPICTPA1CQ4(229456),    --VPICTPA1CQ4,4 Channels STM-4 CES Optical Interface board ,1*1
               virentPTN7900EfiRelay(229457),       --EfiRelay
               virentPTN7900EfiSwitch(229458),      --EfiSwitch
               -- FOR package board
               virentPTN7900VPICTPA1EX4(229459),   --VPICTPA1EX4,4ch 10 Gigabit Ethernet Switching Processing Board-1*1
               virentPTN7900VPICTPA1EXL1(229460),  --VPICTPA1EXL1,1ch 40 Gigabit Ethernet Switching Processing Board,1*1
               virentPTN7900VPICTPA1CO1(229461),   --VPICTPA1CO1,8ch Channels STM-1 CES Optical Interface board ,1*1
               virentPTN7900VPICTPA1EG16(229462),  --VPICTPA1EG16, 16-Port Gigabit Ethernet Processing Board,1*1
               virentPTN7900TPB1VXCS(229463),      --TPB1VXCS, Switch Fabric Unit Board,1*1
               --PTN7900 2013-8-8 by lishaobin end
               -- FOR PTN POTN&100G 80KM
               virentPTN7900VPICTPA1EH1A(229464),   --VPICTPA1EH1A,1-port WAN 80km 100 Gigabit Ethernet Switching Processing Board,1*1
               virentPTN7900VPICTPA1UH1(229465),    --VPICTPA1UH1,1-port 100 Gigabit Ethernet and OTN Hybrid Line Card,1*1
               virentPTN7900VPICTPA1UX10(229466),   --VPICTPA1UX10,10-port 10 Gigabit Ethernet and OTN Hybrid Line Card,1*1
               virentPTN7900VPICTPA1UH1A(229467),   --VPICTPA1UH1A,1-port 100 Gigabit Ethernet and OTN PIC Hybrid Line Card,1*1
               virentPTN7900VPICTPA1TG30(229468),   --VPICTPA1TG30,30-port 1 Gigabit Ethernet OTN Tributary Card,1*1
               virentPTN7900VPICTPA1TX10(229469),   --VPICTPA1TX10,10-port 10 Gigabit Ethernet OTN Tributary Card,1*1
               virentPTN6900DEVTNRD00EXL600(229470),    --for V600R008C10 TNRD00EXL600(SBOM),6 Ports 40 Gigabit Ethernet Processing board (Supporting 1588v2)
               virentPTN6900DEVTNRD00SNCA70(229471),    --for V600R008C10 TNRD00SNCA70(SBOM),SNC Service Flexible Card Unit A(SNC-A)
               virentPTN7900TPB2VXCS(229472),      --TPB2VXCS, Switch Fabric Unit Board,1*1
               virentPTN7900TPC1VXCS(229473),      --TPC1VXCS, Switch Fabric Unit Board,1*1
               --229474 has been used. virentPTN7900VPICTPA1EX12(229474)
              virentPTN6900DEVTNRD0SRUB570(229481),  --TNRD0SRUB570,Enhanced Switch and Route Processing Unit A5
               virentPTN7900TPB3VXCS(229484),      --TPB3VXCS, Switch Fabric Unit Board,1*1
               virentPTN7900TPC2VXCS(229485),      --TPC2VXCS, Switch Fabric Unit Board,1*1
               virentPTN6900DEVTNRDIPU1T2C1(229486),    -- V8R11C10 for PTN6900DEVTNRDIPU1T2C1(SBOM) Integrated Network Processing Unit (IPU-1T2)

-- NE20E-X6:
               virentNE20EX6LPUF10(675840),          --Flexible Card Line Processing Unit(NE20E LPUF-10,four slots)
               virentNE20EX6LPUF20(675841),          --Flexible Card Line Processing Unit(NE20E LPUF-20,2 sub-slots)
               virentNE20EX6LPUS(675842) ,           --40-Port 10/100/1000Base-RJ45 Line Processing Unit S(NE20E LPUS-20)
               virentNE20EX6SPU10(675843),           --Versatile Service Process Unit
               virentNE20EX6VSUI20A(675844),         --Integrated Versatile Service Unit(VSUI-20-A)
               virentNE20EX6MPUD0(675845),           --Main Processing Unit(Including 1*2G Memory and 1*1G CF Card)
               virentNE20EX6CR21EKFEB(675846),       --NE20E-X6 40-Port 10/100Base-RJ45 Line Processing Unit
               virentNE20EX6CR21LPUFC1(675847),      --NE20E-X6 FIC Service Processing Engine(NE20E-X6,four slots), 03053808 xiaoshouhe fen pei SBOM CR2DLPUF1000
               virentNE20EX6MPUH0(675848),            --NE20E-X6-NEW Main Processing Unit (Including 1*2G Memory )
               -- add NE20E for CX600 X1/X2  2012-09-17
               virentNE20ECR2D00MPUE10(675849),       --Main Processing Unit E
               virentNE20ECR2D0NSP5010(675850),       --Network Service Processor -50 (NSP-50)
               virentNE20ECR2DNSPE5010(675851),       --Network Service Processor -50-E (NSP-50-E, Apply for - 40~ 65 degree centigrade scene)
               virentNE20ECR2D00L2XF11(675852),       --2-Port 10GBase LAN/WAN-SFP+  Physical Interface Card
               virentNE20ECR2D00E8GF11(675853),          --8-Port 100/1000Base-X-SFP Physical Interface Card
               virentNE20ECR2D00E8GE11(675854),          --8-Port 10/100/1000Base-RJ45 Physical Interface Card
               virentNE20ECR2D00C4CF11(675855),          --4-Port Channelized OC-3c/STM-1c POS-SFP  Physical Interface Card
               virentNE20ECR2D000IE111(675856),          --32-Port E1 Physical Interface Card(120ohm)
               virentNE20ECR2D000IE110(675857),       --32-Port E1 Physical Interface Card(75ohm)
               virentNE20ECR2DNSP12010(675858),       --Network Service Processor -120 (NSP-120)
               virentNE20ECR2DNSP1201E(675859),        --Network Service Processor -120-E (NSP-120-E)
               virentNE20EX6VSUI20B(675860),          --Integrated Versatile Service Unit(VSUI-20-B)
               virent8090DEVCR2DNSPB0010(675861),    -- V8R7 for SBOM ,CR2DNSPB0010, Network Service Processor(NSP-B)
               virent8090DEVCR2DNSPA0010(675862),    -- V8R7 for SBOM ,CR2DNSPA0010, Network Service Processor(NSP-A)
               virent8090DEVCR5DNPU24070(675863),    -- V8R7 for SBOM ,CR5DNPU24070, Network Processing Unit (NPU-240), NE40E
               virent8090DEVCR5DNPU24071(675864),     -- V8R7 for SBOM ,CR5DNPU24071, Network Processing Unit (NPU-240), NE40E
               virent8090DEVCR5DNPU48070(675865),     -- V8R9C00 for SBOM ,CR5DNPU48070, Network Processing Unit (NPU-480)
               virent8090DEVCR2DNSPC0010(675866),     -- V8R9C00 for SBOM ,CR2DNSPC0010, Network Service Processor (NSP-C)

         --BEGIN: for V8R9C00 by z00291230
               virentME60DEVME0DBSUFM070(161593),     -- for V800R009C00 ME0DBSUFM070(SBOM),Flexible Card Broadband Service Unit(BSUF-480,2 sub-slots)
               virentME60DEVME0DMSUFM070(161594),     -- for V800R009C00 ME0DMSUFM070(SBOM),Flexible Card Broadband Service Unit(MSUF-480,2 sub-slots)
               virent8090DEVCR5DLPUFME70(564864),     -- for V800R009C00 CR5DLPUFME70,Flexible Card Line Processing Unit E(LPUF-480-E)
               virent8090DEVCR5DMPUX8670(564865),      --for V800R009C00 CR5DMPUX8670(SBOM),Main Processing Unit B6
               virent8090DEVCX6DMPUX8670(564866),      --for V800R009C00 CX6DMPUX8670(SBOM),Main Processing Unit B6
               virentME60DEVME0DMPUX8670(159767),      --for V800R009C00 ME0DMPUX8670(SBOM),Main Processing Unit B6
               virent8090DEVCR5DLPUF5071(675899),      --V8R9C00 for SBOM, CR5DLPUF5071, Flexible Card Line Processing Unit(LPUF-50,four sub-slots,4G Memory)
               virent8090DEVCR5DLPUF507M(675900),      --V8R9C00 for SBOM, CR5DLPUF507M, Flexible Card Line Processing Unit L(LPUF-50-L,four sub-slots,4G Memory)
               virent8090DEVCX6DISUF5011(675901),       --V8R9C00 for SBOM, CX6DISUF5011, Flexible Card Integrated Service Unit(ISUF-50,four sub-slots,4G Memory)
         --END: for V8R9C00 by z00291230
	           virent8090DEVTNRDMPUX8670(570059),      --for V800R010C00 TNRDMPUX8670(SBOM),Main Processing Unit B6
         --BEGIN: for V8R9C10 by z00291230
               virentME60DEVME0D0E4NCM70(161595),   -- for V800R009C10 ME0D0E4NCM70(SBOM),4-Port 100GBase-CFP2 Multi Service Unit Integrated(MSUI-400)
               virentME60DEVME0D0LKXFB70(161596),   -- for V800R009C10 ME0D0LKXFB70(SBOM),40-Port 10GBase LAN/WAN-SFP+ Broadband Service Unit Integrated(BSUI-400)
               virentME60DEVME0DE2NLEX7B(161597),   -- for V800R009C10 ME0DE2NLEX7B(SBOM),2-Port 100GBase-CFP2+20-Port 10GBase LAN/WAN-SFP+ Broadband Service Unit Integrated(BSUI-400)
               virentME60DEVME0D0LEXFB71(161583),   -- for V800R009C10 ME0D0LEXFB71(SBOM),20-Port 10GBase LAN/WAN-SFP+ Multi Service Unit Integrated(MSUI-200)
               virentME60DEVME0D0LEXFB70(161584),   -- for V800R009C10 ME0D0LEXFB70(SBOM),20-Port 10GBase LAN/WAN-SFP+ Broadband Service Unit Integrated(BSUI-200)
               virentME60DEVME0D0E2NCB70(161585),   -- for V800R009C10 ME0D0E2NCB70(SBOM),2-Port 100GBase-CFP Multi Service Unit Integrated(MSUI-200)
         --END: for V8R9C10 by z00291230


	 --BEGIN: for V8R9C10 by c00169360
		 virentME60DEVME0DBSUFA071(161600),   -- for ME0DBSUFA071(SBOM),Flexible Card Broadband Service Unit(BSUF-120,2 sub-slots)
		 virentME60DEVME0DBSUFF071(161599),   -- for ME0DBSUFF071(SBOM),Flexible Card Broadband Service Unit(BSUF-200,2 sub-slots)
		 virentME60DEVME0DBSUFK070(161601),   -- for ME0DBSUFK070(SBOM),Flexible Card Broadband Service Unit(BSUF-400,2 sub-slots)
		 virent8090DEVCR5DLPUFK070(161602),   -- for CR5DLPUFK070(SBOM),Flexible Card Line Processing Unit E(LPUF-400-E)
	 --END: for V8R9C10 by c00169360

        --V8R9C10 2016.12.01 added by jwx378168
        --BEGIN
         virentME60DEVME0DVSUF8071(161603),   -- for V800R009C10 ME0DVSUF8071(SBOM),Flexible Card Versatile Service Unit 80(VSUF-80-M) 1.3.6.1.4.1.2011.20021210.15.161603
         virentME60DEVME0DVSUFD071(161604),   -- for V800R009C10 ME0DVSUFD071(SBOM),Flexible Card Versatile Service Unit 160(VSUF-160-M) 1.3.6.1.4.1.2011.20021210.15.161604
         virent8090DEVCR5D0SRUB571(675918),   -- for V800R009C10 CR5D0SRUB571 ,Switch and Route Processing Unit B5(16G Memory) 1.3.6.1.4.1.2011.20021210.15.675918
        --END: for V8R9C10 by jwx378168
        -- for V600R009C30,vsuf
            virentME60DEVME0DVSUF8072(161605),   -- for V600R009C30 ME0DVSUF8072(SBOM),Flexible Card Versatile Service Unit 80(VSUF-80-T)
        --V8R9C00 2017.01.16 added by jwx378168
        --BEGIN
        virentME60DEVME0D0L8NCA70(161606),   -- for V800R009C00 ME0D0L8NCA70(SBOM),8-Port 100GBase-CFP2 Multi Service Unit Integrated(MSUI-1T) 1.3.6.1.4.1.2011.20021210.15.161606
        virentME60DEVME0D0L4NCB70(161607),   -- for V800R009C00 ME0D0LKXFB70(SBOM),4-Port 100GBase-CFP2 Broadband Service Unit Integrated(BSUI-400) 1.3.6.1.4.1.2011.20021210.15.161607
        virentME60DEVME0D0L2NCB70(161608),   -- for V800R009C00 ME0DE2NLEX7B(SBOM),2-Port 100GBase-CFP2 Broadband Service Unit Integrated(BSUI-200) 1.3.6.1.4.1.2011.20021210.15.161608
        virentME60DEVME0D0LFXFA70(161610),   -- for V800R009C00 ME0D0LEXFB70(SBOM),24-Port 10GBase LAN/WAN-SFP+ Multi Service Unit Integrated(MSUI-240) 1.3.6.1.4.1.2011.20021210.15.161610
        virentME60DEVME0D0LMXFA70(161611),   -- for V800R009C00 ME0D0E2NCB70(SBOM),48-Port 10GBase LAN/WAN-SFP+ Multi Service Unit Integrated(MSUI-480) 1.3.6.1.4.1.2011.20021210.15.161611
        --END: for V8R9C00 by jwx378168
        virentME60DEVME0DVSUF8073(161612),    -- for V600R009C10 ME0DVSUF8073(SBOM),Flexible Card Versatile Service Unit 80(VSUF-80-J)
        virent8090DEVCR5DVSUF8011(161613),    -- for V600R009C10 CR5DVSUF8011(SBOM),Flexible Card Versatile Service Unit 80(VSUF-80-J)
        --V8R9C10 2017.02.28 added by jwx378168
        --BEGIN
        virent8090DEVCR5D00D4NT70(564824),   -- for V800R009C10 CR5D00D4NT70 ,4-Port 100GBase-CFP2 DWDM Integrated Line Processing Unit (LPUI-480) 1.3.6.1.4.1.2011.20021210.15.564824
        virent8090DEVCR5D0EMGFA7P(564910),   -- for V800R009C10 CR5D0EMGFA7P(SBOM),48-Port 100/1000Base-X-SFP Integrated Line Processing Unit PC(LPUI-51-PC))
        virent8090DEVCR5D00LBXF7P(564911),   -- for V800R009C10 CR5D00LBXF7P(SBOM),12-Port 10GBase LAN/WAN-SFP+ Integrated Line Processing Unit PC(LPUI-120-PC)
        virent8090DEVCR5DL6XEFG7P(564912),   -- for V800R009C10 CR5DL6XEFG7P(SBOM),6-Port 10GBase LAN/WAN-SFP+ + 24-Port 100/1000Base-X-SFP Integrated Line Processing Unit PC(LPUI-120-PC)
        virent8090DEVCR5D00LFXF7P(564913),   -- for V800R009C10 CR5D00LFXF7P(SBOM),24-Port 10GBase LAN/WAN-SFP+ Integrated Line Processing Unit PC(LPUI-240-PC)
        virent8090DEVCR5D00E8NC7P(564914),   -- for V800R009C10 CR5D00E8NC7P(SBOM),8-Port 100GBase-CFP2 Integrated Line Processing Unit PC(LPUI-1T-PC)
        --END: for V8R9C10 by jwx378168
        --V8R9C10 2017.03.28 added by jwx378168
        --BEGIN
        virent8090DEVCR5DLPUFE07B(564915),    -- for V800R009C10 CR5DLPUFE07B(SBOM),Flexible Card Line Processing Unit B(LPUF-200-B)
               virent8090DEVCR5DLPUFE071(675945),    -- for V800R010C10 CR5DLPUFE071(SBOM),Flexible Card Line Processing Unit(LPUF-200)
               virent8090DEVCR5DLPUFE07C(675946),    -- for V800R010C10 CR5DLPUFE07C(SBOM),Flexible Card Line Processing Unit(LPUF-200-B)
               virent8090DEVCX6DISUFE013(675948),    -- for V800R010C10 CX6DISUFE013(SBOM),Flexible Card Integrated Service Unit(ISUF-201)
        --END: for V8R9C10 by jwx378168
        --V8R10C00 2017.04.06 added by jwx378168
               virent8090DEVCX6D00MPUD30(675947),  --Main Processing Unit D3(4G Memory)
        --BEGIN
        virent8090DEVCR5DNPU1TM71(675868),   -- for V800R010C00 CR5DNPU1TM71(SBOM),Network Processing Unit (NPU-1T)
        virent8090DEVCR5DNPU1TM70(675867),   -- for V800R010C00 CR5DNPU1TM70(SBOM),Network Processing Unit (NPU-1T)
        --END: for V8R10C00 by jwx378168
        --V8R10C00 2017.06.16 added by xwx385897
        --BEGIN
        virent8090DEVCR5D0SRUA872(566111),    -- for V800R010C00 CR5D0SRUA872(SBOM),Switch and Route Processing Unit A8(16G Memory) 1.3.6.1.4.1.2011.20021210.15.566111
        virent8090DEVCR5DSFUIM17C(566112),    -- for V800R010C00 CR5DSFUIM17C(SBOM),480Gbps Switch Fabric Unit C(SFUI-480-C) 1.3.6.1.4.1.2011.20021210.15.566112
        virent8090DEVCR5DSFUIM17B(566113),    -- for V800R010C00 CR5DSFUIM17B(SBOM),480Gbps Switch Fabric Unit B(SFUI-480-B) 1.3.6.1.4.1.2011.20021210.15.566113)

        virent8090DEVCR5DLPUFME71(565001),      -- for V800R10C00 CR5DLPUFME71(SBOM)	Flexible Card Line Processing Unit E(LPUF-480-E)
        virent8090DEVCR5DLPUFK071(565002),      -- for V800R10C00 CR5DLPUFK071(SBOM)	Flexible Card Line Processing Unit E(LPUF-400-E)
        virent8090DEVCR5DLPUFM071(565003),      -- for V800R10C00 CR5DLPUFM071(SBOM)	Flexible Card Line Processing Unit(LPUF-480)
        virent8090DEVCR5DLPUFM17B(565004),      -- for V800R10C00 CR5DLPUFM17B(SBOM)	Flexible Card Line Processing Unit B(LPUF-480-B)
        virent8090DEVCR5D00LMXF71(565005),      -- for V800R10C00 CR5D00LMXF71(SBOM)	48-Port 10GBase LAN/WAN-SFP+ Integrated Line Processing Unit (LPUI-480)
        virent8090DEVCR5DE2NLFX74(565006),      -- for V800R10C00 CR5DE2NLFX74(SBOM)	2-Port 100GBase-CFP2 + 24-Port 10GBase LAN/WAN-SFP+ Integrated Line Processing Unit (LPUI-480)
        virent8090DEVCR5D00E4NC71(565007),      -- for V800R10C00 CR5D00E4NC71(SBOM)	4-Port 100GBase-CFP2 Integrated Line Processing Unit (LPUI-480)
        virent8090DEVCR5D01LMXF7B(565008),      -- for V800R10C00 CR5D01LMXF7B(SBOM)	48-Port 10GBase LAN/WAN-SFP+ Integrated Line Processing Unit B(LPUI-480-B)
        virent8090DEVCR5DE2NLFX75(565009),      -- for V800R10C00 CR5DE2NLFX75(SBOM)	2-Port 100GBase-CFP2 + 24-Port 10GBase LAN/WAN-SFP+ Integrated Line Processing Unit B(LPUI-480-B)
        virent8090DEVCR5D01E4NC7B(565010),      -- for V800R10C00 CR5D01E4NC7B(SBOM)	4-Port 100GBase-CFP2 Integrated Line Processing Unit B(LPUI-480-B)
        virent8090DEVCR5D01LMXF7C(565011),      -- for V800R10C00 CR5D01LMXF7C(SBOM)	48-Port 10GBase LAN/WAN-SFP+ Integrated Line Processing Unit L(LPUI-480-L)
        virent8090DEVCR5DE2NLFX76(565012),      -- for V800R10C00 CR5DE2NLFX76(SBOM)	2-Port 100GBase-CFP2 + 24-Port 10GBase LAN/WAN-SFP+ Integrated Line Processing Unit L(LPUI-480-L)
        virent8090DEVCR5D01E4NC7C(565013),      -- for V800R10C00 CR5D01E4NC7C(SBOM)	4-Port 100GBase-CFP2 Integrated Line Processing Unit L(LPUI-480-L)
        virent8090DEVCR5D00D4NC71(565014),      -- for V800R10C00 CR5D00D4NC71(SBOM)	4-Port 100GBase-CFP2 DWDM Integrated Line Processing Unit(LPUI-480)
        virent8090DEVCR5D00E4NC7Q(565015),      -- for V800R10C00 CR5D00E4NC7Q(SBOM)	4-Port 100G ETH/DWDM-CFP2 Integrated Line Processing Unit CM(LPUI-480-CM)

        virent8090DEVCR5D00E2NB70(566121),    -- for V800R010C00 CR5D00E2NB70(SBOM),2-Port 100GBase-QSFP28 Integrated Line Processing Unit(LPUI-200)
        virent8090DEVCR5DE1NLAX78(566122),    -- for V800R010C00 CR5DE1NLAX78(SBOM),1-Port 100GBase-QSFP28 + 10-Port 10GBase LAN/WAN-SFP+ Integrated Line Processing Unit(LPUI-200)
        virent8090DEVCR5D0E2NBL70(566123),    -- for V800R010C00 CR5D0E2NBL70(SBOM),2-Port 100GBase-QSFP28 Integrated Line Processing Unit L(LPUI-200-L)
        virent8090DEVCR5DE1NLAX7A(566124),    -- for V800R010C00 CR5DE1NLAX7A(SBOM),1-Port 100GBase-QSFP28 + 10-Port 10GBase LAN/WAN-SFP+ Integrated Line Processing Unit L(LPUI-200-L)
        virent8090DEVME0D0E2NBB70(566125),    -- for V800R010C00 ME0D0E2NBB70(SBOM),2-Port 100GBase-QSFP28 Multi Service Unit Integrated(MSUI-200)
        virent8090DEVME0D0E4NBM70(566126),    -- for V800R010C00 ME0D0E4NBM70(SBOM),4-Port 100GBase-QSFP28 Multi Service Unit Integrated(MSUI-400)

         virent8090DEVCX6DSFUIM17B(565016),      -- for V800R10C00 CX6DSFUIM17B(SBOM)	480Gbps Switch Fabric Unit B(SFUI-480-B)
         virent8090DEVCX6DSFUIT27B(565017),      -- for V800R10C00 CX6DSFUIT27B(SBOM)	2Tbps Switch Fabric Unit B(SFUI-2T-B)
         virent8090DEVCX6D0SRUA872(565018),      -- for V800R10C00 CX6D0SRUA872(SBOM)	Switch and Route Processing Unit A8(16G Memory)
         virent8090DEVCX6DSFUIM17C(565019),      -- for V800R10C00 CX6DSFUIM17C(SBOM)	480Gbps Switch Fabric Unit C(SFUI-480-C)
         virent8090DEVTNRDSFUIM17B(565020),      -- for V800R10C00 TNRDSFUIM17B(SBOM)	480Gbps Switch Fabric Unit B(SFUI-480-B)
         virent8090DEVTNRDSFUIT27B(565021),      -- for V800R10C00 TNRDSFUIT27B(SBOM)	2Tbps Switch Fabric Unit B(SFUI-2T-B)
         virent8090DEVTNRD0SRUA872(565022),      -- for V800R10C00 TNRD0SRUA872(SBOM)	Switch and Route Processing Unit A8(16G Memory)
         virent8090DEVTNRDSFUIM17C(565023),      -- for V800R10C00 TNRDSFUIM17C(SBOM)	480Gbps Switch Fabric Unit C(SFUI-480-C)
         virent8090DEVCX6DSFUIM11B(565024),      -- for V800R10C00 CX6DSFUIM11B(SBOM)	480Gbps Switch Fabric Unit B(SFUI-480-B)
         virent8090DEVCX6DSFUIT21B(565025),      -- for V800R10C00 CX6DSFUIT21B(SBOM)	2Tbps Switch Fabric Unit B(SFUI-2T-B)
         virent8090DEVCX6D0SRUA812(565026),      -- for V800R10C00 CX6D0SRUA812(SBOM)	Switch and Route Processing Unit A8(16G Memory)
         virent8090DEVCX6DSFUIM11C(565027),      -- for V800R10C00 CX6DSFUIM11C(SBOM)	480Gbps Switch Fabric Unit C(SFUI-480-C)
         virent8090DEVME0DSFUIM17B(565028),      -- for V800R10C00 ME0DSFUIM17B(SBOM)	480Gbps Switch Fabric Unit B(SFUI-480-B)
         virent8090DEVME0D0SRUA872(565029),      -- for V800R10C00 ME0D0SRUA872(SBOM)	Switch and Route Processing Unit A8(16G Memory)
         virent8090DEVME0DSFUIM17C(565030),      -- for V800R10C00 ME0DSFUIM17C(SBOM)	480Gbps Switch Fabric Unit C(SFUI-480-C)

         virent8090DEVCR5D00EENB70(675922),      -- for V800R10C00 CR5D00EENB70(SBOM) 20-Port 100GBase-QSFP28 Integrated Line Processing Unit (LPUI-2T)
         virent8090DEVCR5D00EENB7B(565031),      -- for V800R10C00 CR5D00EENB7B(SBOM) 20-Port 100GBase-QSFP28 Integrated Line Processing Unit B(LPUI-2T-B)
         virent8090DEVCR5D00EENB7P(565032),      -- for V800R10C00 CR5D00EENB7P(SBOM) 20-Port 100GBase-QSFP28 Integrated Line Processing Unit CM(LPUI-2T-CM)
         virent8090DEVCX6D00EENB10(565033),      -- for V800R10C00 CX6D00EENB10(SBOM) 20-Port 100GBase-QSFP28 Integrated Line Processing Unit (ISUI-2T)

         virent8090DEVCX6DISUFM011(565034),      -- for V800R10C00 CX6DISUFM011(SBOM) Flexible Card Integrated Service Unit(ISUF-480)
         virent8090DEVME0DBSUFM071(565035),      -- for V800R10C00 ME0DBSUFM071(SBOM) Flexible Card Broadband Service Unit(BSUF-480,2 sub-slots)
         virent8090DEVME0DBSUFK071(565036),      -- for V800R10C00 ME0DBSUFK071(SBOM) Flexible Card Broadband Service Unit(BSUF-400,2 sub-slots)
         virent8090DEVME0DMSUFM071(565037),      -- for V800R10C00 ME0DMSUFM071(SBOM) Flexible Card Multi Service Unit(MSUF-480,2 sub-slots)
         virent8090DEVME0D0L4NCB71(565038),      -- for V800R10C00 ME0D0L4NCB71(SBOM) 4-Port 100GBase-CFP2 Broadband Service Unit Integrated(BSUI-400)
         virent8090DEVME0D0LKXFB71(565039),      -- for V800R10C00 ME0D0LKXFB71(SBOM) 40-Port 10GBase LAN/WAN-SFP+ Broadband Service Unit Integrated(BSUI-400)
         virent8090DEVME0D0E4NCM71(565040),      -- for V800R10C00 ME0D0E4NCM71(SBOM) 4-Port 100GBase-CFP2 Multi Service Unit Integrated(MSUI-400)
         virent8090DEVME0D0LMXFA71(565041),    -- for V800R010C00 ME0D0LMXFA71(SBOM),48-Port 10GBase LAN/WAN-SFP+ Multi Service Unit Integrated(MSUI-480)

        virentME60DEVME0DL6XE8G70(161614),    -- for V800R010C00 ME0DL6XE8G70(SBOM),6-Port 10GBase LAN/WAN-SFP+ + 8-Port 100/1000Base-X-SFP Broadband Service Unit Integrated(BSUI-120)
        virent8090DEVCR5DL6XE8G70(161615),    -- for V800R010C00 CR5DL6XE8G70(SBOM),6-Port 10GBase LAN/WAN-SFP+ + 8-Port 100/1000Base-X-SFP Integrated Line Processing Unit (LPUI-120)
        virent8090DEVCR5D000VSE70(161616),    -- for V800R010C00 CR5D000VSE70(SBOM),Value-added Service Engine Unit(VSE-A)

        virent8090DEVCR9D00EKNB80(562055), -- 40-Port 100GBase QSFP28 Integrated Line Process Unit(NE9000 LPUI-4T)
        virent8090DEVCR9D00EKNB8P(562056), -- 40-Port 100GBase QSFP28 Integrated Line Process Unit CM(NE9000 LPUI-4T-CM)
        virent8090DEVCR9D00E8KC8P(562096),  -- for V800R011C00 CR9D00E8KC8P ,8-Port 400GBase-CFP8 Integrated Line Process Unit CM(NE9000 LPUI-4T-CM) 1.3.6.1.4.1.2011.20021210.15.562096
        virent8090DEVCR9DE8KE8N8R(562099),  -- for V800R011C10 CR9DE8KE8N8R ,8-Port 400GBase-QSFP-DD + 8-Port 100GBase-QSFP28 Integrated Line Process Unit CM(NE9000 LPUI-4T-CM)
        virent8090DEVCX6D00EKNBA1(562098),  -- for V800R011C10 CX6D00EKNBA1 ,8-Port 400GBase-QSFP-DD + 8-Port 100GBase-QSFP28 Integrated Line Process Unit CM(LPUI-4T)
        virent8090DEVCR9D00EKNB8L(562057),  -- 40-Port 100GBase QSFP28 Integrated Line Process Unit L(NE9000 LPUI-4T-L)
        virent8090DEVCR9DLPUFT280(675926),  -- 2T Flexible Card Line Processing Unit(NE9000E LPUF-2T,2 sub-slots)
        virent8090DEVCR9D00DDNC80(675927),  -- 16-Port 100G ETH/DWDM CFP2 Integrated Line Process Unit(NE9000 LPUI-2T)
        virent8090DEVCR9D00DDNC8P(675928),  -- 16-Port 100G ETH/DWDM CFP2 Integrated Line Process Unit CM(NE9000 LPUI-2T-CM)
        virent8090DEVCR9D00EENB80(675923),  -- 20-Port 100GBase-QSFP28 Integrated Line Process Unit (NE9000 LPUI-2T)
        virent8090DEVCR9D00EENB8P(675929),  -- 20-Port 100GBase-QSFP28 Integrated Line Process Unit CM(NE9000 LPUI-2T-CM)
        virent8090DEVCR9D00DDNC8L(675930),  -- 16-Port 100GBase ETH/DWDM-CFP2 Integrated Line Process Unit L(NE9000 LPUI-2T-L)
        virent8090DEVCR9D00EENB8L(675931),  -- 20-Port 100GBase-QSFP28 Integrated Line Process Unit L(NE9000 LPUI-2T-L)
        --END:

         --V8R10C00 2017.09.14 added by l00421975
        --BEGIN:
        virent8090DEVCX6D00DDNCA0(570054),    -- V8R10C00 for CX6D00DDNCA0(SBOM) 16-Port 100G ETH/DWDM CFP2 Integrated Line Processing Unit (LPUI-2T)
        virent8090DEVCX6D00EENBA0(570055),    -- V8R10C00 for CX6D00EENBA0(SBOM) 20-Port 100GBase-QSFP28 Integrated Line Processing Unit (LPUI-2T)
        virent8090DEVCX6D00EKNBA0(570056),    -- V8R10C00 for CX6D00EKNBA0(SBOM) 40-Port 100GBase-QSFP28 Integrated Line Processing Unit (LPUI-4T)
        virent8090DEVCX6D00EPXFA0(570057),    -- V8R10C00 for CX6D00EPXFA0(SBOM) 60-Port 10GBase LAN/WAN-SFP+ Integrated Line Process Unit (LPUI-1T)
        virent8090DEVCR9D00EDNB8L(562076),    -- V8R10C00 for CR9D00EDNB8L(SBOM) 16-Port 100GBase-QSFP28 Integrated Line Process Unit L(NE9000 LPUI-2T-L)
        virent8090DEVCR5DSFUIT260(562081),     
        virent8090DEVCR5D0MPUB760(562164),   -- v8r10c10 NE5000-20 Main Processing Unit N1(MPUN1)
        virent8090DEVCR9DLPUFK081(570060) ,    -- V8R10C10 for CR9DLPUFK081(SBOM) 480G Flexible Card Line Processing Unit C(NE9000 LPUF-480C,2 sub-slots)
        --END:

        --V8R11C10 2019.03.18 added by lwx354721
        --BEGIN:
        virent8090DEVCR9D00MPUS80(562165),   -- v8r11c10 NE9000-20 Main Processing Unit S(MPUS)
        --END:
       --BEGIN: 
        virent8090DEVCR5D0MPUA850(567022),   -- V8R12C00 NE5000E CCC-A Cluster Central Main Processing Unit A8
        virent8090DEVCR5D0MPUA851(567023),   -- V8R12C00 NE5000E CCC-A Cluster Central Main Processing Unit A8
	virent8090DEVCR5D0MPUA950(567024),   --NE5000E V8R21C00 for NetEngine5000E CCC-A Cluster Central Main Processing Unit A9
        virent8090DEVCR5D0MPUA951(567025),   --NE5000E V8R21C00 for NetEngine5000E CCC-A Cluster Central Main Processing Unit A9
        --END:

		--V8R11C10 2019.04.10 added by lwx354721
        --BEGIN:
		virent8090DEVCR9D00EPXF81(675997),    -- V8R11C10 for CR9D00EPXF81(SBOM) 60-Port 10GBase LAN/WAN-SFP+ MACSec Integrated Line Process Unit CM(LPUI-1T-CM)
       	virent8090DEVCR9D000CMU61(675994),    -- V8R11C10 for CR9D000CMU61(SBOM) Finished Board,CR58CMUBA03,Centralized Monitoring Module
       	virent8090DEVCR9D000CMU62(675996),    -- V8R11C10 for CR9D000CMU62(SBOM) Finished Board,CR58CMUBA02,Centralized Monitoring Module
        --END:

        virent8090DEVCR5D0MPUKA90(565042),      -- for V800R010C00 CR5D0MPUKA90(SBOM) Main Processing Unit KA
        virent8090DEVCX6D0MPUKA90(565043),      -- for V800R010C00 CX6D0MPUKA90(SBOM) Main Processing Unit KA
        virent8090DEVTNUD0MPUKA90(565044),      -- for V800R010C00 TNUD0MPUKA90(SBOM) Main Processing Unit KA
        virent8090DEVCR2D0MPUEA00(565045),      -- for V800R010C00 CR2D0MPUEA00(SBOM),Main Processing Unit EA
        virent8090DEVCR5DSFUIT27B(675921),    -- V8R10C00 for CR5DSFUIT27B(SBOM) 2Tbps Switch Fabric Unit B(SFUI-2T-B)
        virent8090DEVCR2DNSPD0010(562078),    -- V8R10C00 for CR2DNSPD0010(SBOM) Network Service Processor(NSP-D)

        --BEGIN: for CX6600
        virent8090DEVCX6D0MPUP1A0(570050),    -- V8R10C00 for CX6D0MPUP1A0(SBOM) Main Processing Unit P1
        virent8090DEVCX6D0MPUP2A0(570036),    -- V8R11C00 for CX6D0MPUP2A0(SBOM) Main Processing Unit P2
        virent8090DEVCX6DSFUIT4AA(570051),    -- V8R10C00 for CX6DSFUIT4AA(SBOM) 4Tbps Switch Fabric Unit A(SFUI-4T-A)
        virent8090DEVCX6D0MPUN1A0(570052),    -- V8R10C00 for CX6D0MPUN1A0(SBOM) Main Processing Unit N1
        virent8090DEVCX6DSFUIT4AB(570053),    -- V8R10C00 for CX6DSFUIT4AB(SBOM) 4Tbps Switch Fabric Unit B(SFUI-4T-B)
         --END: for CX6600
               --BEGIN
               virent8090DEVCR5D0SRUAA70(567001),    -- V8R10C10 for CR5D0SRUAA70(SBOM) Switch and Route Processing Unit A10(32G Memory)
               virent8090DEVCR5DSFUIU07D(567002),    -- V8R10C10 for CR5DSFUIU07D(SBOM) 2Tbps Switch Fabric Unit D(SFUI-2T-D)
               virent8090DEVCX6D0SRUAA70(567003),    -- V8R10C10 for CX6D0SRUAA70(SBOM) Switch and Route Processing Unit A10(32G Memory)
               virent8090DEVCX6DSFUIU07D(567004),    -- V8R10C10 for CX6DSFUIU07D(SBOM) 2Tbps Switch Fabric Unit D(SFUI-2T-D)
               virent8090DEVTNRD0SRUAA70(567005),    -- V8R10C10 for TNRD0SRUAA70(SBOM) Switch and Route Processing Unit A10(32G Memory)
               virent8090DEVTNRDSFUIU07D(567006),     -- V8R10C10 for TNRDSFUIU07D(SBOM) 2Tbps Switch Fabric Unit D(SFUI-2T-D)
               --END: for V8R10C10 by xwx385897
               virent8090DEVCX6D60T220A0(675755),     -- V8R10C10 for CX6D60T220A0(SBOM) 20-Port 100GBase-MACsec Integrated Line Processing Unit (LPUI-2T)
               virent8090DEVCR5D0MPUK570(675954),   -- for V800R010C10 CR5D0MPUK570(SBOM), Main Processing Unit K1A
               virent600DEVCX6B0BKP0392(675950),    --V8R11C00 CX600-F1A-14H24Q CX6B0BKP0392(SBOM), F1A-14H24Q
               virent600DEVCR5B0BKP0392(675951),    --V8R11C00 NE40E-F1A-14H24Q CR5B0BKP0392(SBOM), F1A-14H24Q
			   virent600DEVCR5B0BKP0382(675717),    --V8R11C00 NE40E-F1A-14H24Q CR5B0BKP0382(SBOM), F1A-14H24Q
               virent600DEVTNRB0BKP0391(675952),    --V8R11C00 PTN6900-F1A-14H24Q TNRB0BKP0391(SBOM), F1A-14H24Q
               virent600DEVCX6P010BKP90(675953),     --V8R11C00 CX6601-14H24Q CX6P010BKP90(SBOM), F1A-14H24Q
               virent600DEVPDC1K2S12(675961),       --V8R11C00 PDC1K2S12, F1A-14H24Q-POWER
               virent600DEVPAC1K2S12(675962),       --V8R11C00 PAC1K2S12, F1A-14H24Q-POWER
               virent600DEVFANF1A-14H24Q(675963),          --V8R11C00 FAN-F1A-14H24Q
               virent600DEVCX6B0BKP0394(675964),    --V8R11C10 CX600-F1A-8H20Q CX6B0BKP0394(SBOM), F1A-8H20Q
               virent600DEVCR5B0BKP0394(675965),    --V8R11C10 NE40E-F1A-8H20Q CR5B0BKP0394(SBOM), F1A-8H20Q
               virent600DEVTNRB0BKP0394(675966),    --V8R11C10 PTN6900-F1A-8H20Q TNRB0BKP0394(SBOM), F1A-8H20Q
               -- M2K-B
               virent600DEVCX6P020BKP01(675811),    --CX6602-B Integrated Chassis Components, CX6P020BKP01
               virent600DEVCR5B0BKP0393(675812),    --NE40E-M2K-B Integrated Chassis Components, CR5B0BKP0393
               virent600DEVCX6B0BKP0393(675813),    --CX600-M2K-B Integrated Chassis Components, CX6B0BKP0393
               virent600DEVTNRB0BKP0374(675814),    --PTN6900-M2K-B Integrated Chassis Components, TNRB0BKP0374
			   virent600DEVCR5B0BKP0383(675723),    --NE40E-M2K-B Integrated Chassis Components, CR5B0BKP0383

               virent8090DEVCR9DLPUFT281(675808),     -- V8R10C10 2T for CR9DLPUFT281(SBOM) Flexible Card Line Processing Unit B(LPUF-2T-B,2 sub-slots)
               subbname8090DEVCR5D00LMXF7P(154895),    --V8R10C10 for CR5D00LMXF7P(SBOM) 48-Port 10GBase LAN/WAN-SFP+ Integrated Line Processing Unit CM(LPUI-480-CM)
               subbname8090DEVCR5DE2NLFX7P(154896),    --V8R10C10 for  CR5DE2NLFX7P(SBOM) 2-Port 100GBase-CFP2 + 24-Port 10GBase LAN/WAN-SFP+ Integrated Line Processing Unit CM(LPUI-480-CM)
               virent8090DEVCR5D0SRUAB73(570062),     -- V8R11C00 for CR5D0SRUAB73(SBOM) Switch and Route Processing Unit A11
               virent8090DEVME0D0SRUAB70(570063),     -- V8R11C00 for ME0D0SRUAB70(SBOM) Switch and Route Processing Unit A11
               virent8090DEVCR5DEKBEBX7B(675776),    -- V8R11C00 for  CR5DEKBEBX7B(SBOM) 1-Port 100GBase-QSFP28 + 12-Port 10GBase LAN/WAN-SFP+ Integrated Line Processing Unit B(LPUI-241-B)
               virent8090DEVCX6DISUFF110(675777),    -- V8R11C00 for  CX6DISUFF110(SBOM) Flexible Card Line Processing Unit(ISUF-241)
               virent8090DEVCX6DISUFF11R(675778),    -- V8R11C00 for  CX6DISUFF11R(SBOM) Flexible Card Line Processing Unit(ISUF-241-R)
               virent8090DEVCX6DF1E2NC10(675779),    -- V8R11C00 for  CX6DF1E2NC10(SBOM) 2-Port 100GBase-CFP2 Integrated Line Processing Unit (ISUI-241)
               virent8090DEVCX6DF1E2NB10(675780),    -- V8R11C00 for  CX6DF1E2NB10(SBOM) 2-Port 100GBase-QSFP28 Integrated Line Processing Unit (ISUI-241)
               virent8090DEVCX6DF1EFXC10(675781),    -- V8R11C00 for  CX6DF1EFXC10(SBOM) 24-Port 10GBase LAN/WAN-SFP+ Integrated Line Processing Unit (ISUI-241)
               virent8090DEVCX6DE1KEBX10(675782),    -- V8R11C00 for  CX6DE1KEBX10(SBOM) 1-Port 100GBase-CFP2 + 12-Port 10GBase LAN/WAN-SFP+ Integrated Line Processing Unit (ISUI-241)
               virent8090DEVCX6DEKBEBX10(675783),    -- V8R11C00 for  CX6DEKBEBX10(SBOM) 1-Port 100GBase-QSFP28 + 12-Port 10GBase LAN/WAN-SFP+ Integrated Line Processing Unit (ISUI-241)
               virent8090DEVCX6DF1E2NC1B(675784),     -- V8R11C00 for  CX6DF1E2NC1B(SBOM) 2-Port 100GBase-CFP2 Integrated Line Processing Unit B(ISUI-241-B)
               virent8090DEVCR5DLPUFF170(675785),    -- V8R11C00 for  CR5DLPUFF170(SBOM) Flexible Card Line Processing Unit(LPUF-241)
               virent8090DEVCR5DLPUFF17R(675786),    -- V8R11C00 for  CR5DLPUFF17R(SBOM) Flexible Card Line Processing Unit(LPUF-241-R)
               virent8090DEVCR5DL5XEFG7L(675805),    -- for V800R011C00 CR5DL5XEFG7L(SBOM),5-Port 10GBase LAN/WAN-SFP+ + 24-Port 100/1000Base-X-SFP Integrated Line Processing Unit L(LPUI-120-L)
               virent8090DEVCR5DLPUFF17E(564928),     --V8R11C00 for CR5DLPUFF17E  Flexible Card Line Processing Unit(LPUF-241-E)
               virent8090DEVCR5DLPUFF17Q(564929),     --V8R11C00 for CR5DLPUFF17Q  Flexible Card Line Processing Unit(LPUF-241-ER)
               virent8090DEVME0DBSUFF073(675806),     --V8R11C00 for ME0DBSUFF073  Flexible Card Multi Service Unit(BSUF-241,2 sub-slots)
               virent8090DEVME0DBSUFF072(675807),     --V8R11C00 for ME0DBSUFF072  Flexible Card Multi Service Unit(BSUF-241-R,2 sub-slots)
               virent8090DEVCX6D0SRUA910(564932),    -- V8R11C00 for CX6D0SRUA910(SBOM), Switch and Route Processing Unit A9(16G Memory)
               virent8090DEVCX6DSFUIT01C(564933),    -- V8R11C00 for CX6DSFUIT01C(SBOM) 1Tbps Switch Fabric Unit C(SFUI-1T-C)
               virent8090DEVCX6DSFUIT01B(564934),    -- V8R11C00 for CX6DSFUIT01B(SBOM), 1Tbps Switch Fabric Unit B(SFUI-1T-B)
               virent8090DEVCR5D0SRUAC7A(675766),    -- V8R11C00 for  CR5D0SRUAC7A(SBOM) Switch and Route Processing Unit A12
               virent8090DEVCX6D0SRUAC7A(675767),    -- V8R11C00 for  CX6D0SRUAC7A(SBOM) Switch and Route Processing Unit A12
               virent8090DEVTNRD0SRUAC70(675768),    -- V8R11C00 for  TNRD0SRUAC70(SBOM) Switch and Route Processing Unit A12
               virent8090DEVCX6D0SRUAC10(675769),    -- V8R11C00 for  CX6D0SRUAC10(SBOM) Switch and Route Processing Unit A12
               virent8090DEVME0D0SRUAC7A(675770),    -- V8R11C00 for  ME0D0SRUAC7A(SBOM) Switch and Route Processing Unit A12
               virent8090DEVCR5DSFUFK070(675771),    -- V8R11C00 for  CR5DSFUFK070(SBOM) 400Gbps Switch Fabric Unit F(SFUI-400-F)
               virent8090DEVCX6D0SFUF870(675772),    -- V8R11C00 for  CX6D0SFUF870(SBOM) 400Gbps Switch Fabric Unit F(SFUI-400-F)
               virent8090DEVTNRDSFUFK070(675773),    -- V8R11C00 for  TNRDSFUFK070(SBOM) 400Gbps Switch Fabric Unit F(SFUI-400-F)
               virent8090DEVCX6DSFUIF070(675774),    -- V8R11C00 for  CX6DSFUIF070(SBOM) 400Gbps Switch Fabric Unit F(SFUI-400-F)
               virent8090DEVME0DSFUIF070(675775),    -- V8R11C00 for  ME0DSFUIF070(SBOM) 400Gbps Switch Fabric Unit F(SFUI-400-F)
               virent8090DEVCR5DF1E2NC70(675796),    -- V8R11C00 for  CR5DF1E2NC70(SBOM) 2-Port 100GBase-CFP2 Integrated Line Processing Unit (LPUI-241)
               virent8090DEVCR5DF1E2NB70(675797),    -- V8R11C00 for  CR5DF1E2NB70(SBOM) 2-Port 100GBase-QSFP28 Integrated Line Processing Unit (LPUI-241)
               virent8090DEVCR5DF1EFXC70(675798),    -- V8R11C00 for  CR5DF1EFXC70(SBOM) 24-Port 10GBase LAN/WAN-SFP+ Integrated Line Processing Unit (LPUI-241)
               virent8090DEVCR5DE1KEBX70(675799),    -- V8R11C00 for  CR5DE1KEBX70(SBOM) 1-Port 100GBase-CFP2 + 12-Port 10GBase LAN/WAN-SFP+ Integrated Line Processing Unit (LPUI-241)
               virent8090DEVCR5DEKBEBX70(675800),    -- V8R11C00 for  CR5DEKBEBX70(SBOM) 1-Port 100GBase-QSFP28 + 12-Port 10GBase LAN/WAN-SFP+ Integrated Line Processing Unit (LPUI-241)
               virent8090DEVCR5DF1E2NC7B(675801),    -- V8R11C00 for  CR5DF1E2NC7B(SBOM) 2-Port 100GBase-CFP2 Integrated Line Processing Unit B(LPUI-241-B)
               virent8090DEVCR5DF1E2NB7B(675802),    -- V8R11C00 for  CR5DF1E2NB7B(SBOM) 2-Port 100GBase-QSFP28 Integrated Line Processing Unit B(LPUI-241-B)
               virent8090DEVCR5DF1EFXC7B(675803),    -- V8R11C00 for  CR5DF1EFXC7B(SBOM) 24-Port 10GBase LAN/WAN-SFP+ Integrated Line Processing Unit B(LPUI-241-B)
               virent8090DEVCR5DE1KEBX7B(675804),    -- V8R11C00 for  CR5DE1KEBX7B(SBOM) 1-Port 100GBase-CFP2 + 12-Port 10GBase LAN/WAN-SFP+ Integrated Line Processing Unit B(LPUI-241-B)
               virent8090DEVCX6DF1E2NB1B(675787),    -- V8R11C00 for  CX6DF1E2NB1B(SBOM) 2-Port 100GBase-QSFP28 Integrated Line Processing Unit B(ISUI-241-B)
               virent8090DEVCX6DF1EFXC1B(675788),    -- V8R11C00 for  CX6DF1EFXC1B(SBOM) 24-Port 10GBase LAN/WAN-SFP+ Integrated Line Processing Unit B(ISUI-241-B)
               virent8090DEVCX6DE1KEBX1B(675789),    -- V8R11C00 for  CX6DE1KEBX1B(SBOM) 1-Port 100GBase-CFP2 + 12-Port 10GBase LAN/WAN-SFP+ Integrated Line Processing Unit B(ISUI-241-B)
               virent8090DEVCX6DEKBEBX1B(675790),    -- V8R11C00 for  CX6DEKBEBX1B(SBOM) 1-Port 100GBase-QSFP28 + 12-Port 10GBase LAN/WAN-SFP+ Integrated Line Processing Unit B(ISUI-241-B)
               virent8090DEVCR5DLPUFF273(675791),    -- V8R11C00 for  CR5DLPUFF273(SBOM) Flexible Card Line Processing Unit(LPUF-481)
               virent8090DEVCR5DLPUFF272(675792),    -- V8R11C00 for  CR5DLPUFF272(SBOM) Flexible Card Line Processing Unit(LPUF-481-E)
               virent8090DEVCX6DISUFF210(675793),    -- V8R11C00 for  CX6DISUFF210(SBOM) Flexible Card Line Processing Unit(ISUF-481)
               virent8090DEVME0DBSUFM072(675794),    -- V8R11C00 for  ME0DBSUFM072(SBOM) Flexible Card Broadband Service Unit(BSUF-481,2 sub-slots)
               virent8090DEVCR5DBSUIM070(675795),    -- V8R11C00 for  CR5DBSUIM070(SBOM) Integrated Broadband Service Unit(BSUI-481-E)
               virent8090DEVCR5D0MPUB772(675756),    -- V8R11C00 for  CR5D0MPUB772(SBOM) Main Processing Unit B7
               virent8090DEVCX6D0MPUB772(675757),    -- V8R11C00 for  CX6D0MPUB772(SBOM) Main Processing Unit B7
               virent8090DEVTNRD0MPUB770(675758),    -- V8R11C00 for  TNRD0MPUB770(SBOM) Main Processing Unit B7
               virent8090DEVCX6D0MPUB710(675759),    -- V8R11C00 for  CX6D0MPUB710(SBOM) Main Processing Unit B7
               virent8090DEVME0D0MPUB770(675760),    -- V8R11C00 for  ME0D0MPUB770(SBOM) Main Processing Unit B7
               virent8090DEVCR5DSFUGK070(675761),    -- V8R11C00 for  CR5DSFUGK070(SBOM) 400Gbps Switch Fabric Unit G(SFUI-400-G)
               virent8090DEVCX6DSFUGK070(675762),    -- V8R11C00 for  CX6DSFUGK070(SBOM) 400Gbps Switch Fabric Unit G(SFUI-400-G)
               virent8090DEVTNRDSFUGK070(675763),    -- V8R11C00 for  TNRDSFUGK070(SBOM) 400Gbps Switch Fabric Unit G(SFUI-400-G)
               virent8090DEVCX6DSFUIG010(675764),    -- V8R11C00 for  CX6DSFUIG010(SBOM) 400Gbps Switch Fabric Unit G(SFUI-400-G)
               virent8090DEVME0DSFUGK070(675765),   -- V8R11C00 for  ME0DSFUGK070(SBOM) 400Gbps Switch Fabric Unit G(SFUI-400-G)
               virent8090DEVCX6D00E8NC70(675809),    -- V8R10C10 for  8-Port 100GBase-CFP2 Integrated Integrated Service Unit(ISUI-1T)
               --MSE
               virent8090DEVCR5DLPUFD07E(675819),    -- V8R11C10 for  CR5DLPUFD07E(SBOM) Flexible Card Line Processing Unit(LPUF-242-E)
               virent8090DEVCX6DISUFM012(675810),    -- V8R10C10 for  Flexible Card Integrated Service Unit(ISUF-400)
               virent8090DEVCR5D0SRUAC70(570042),    -- V8R11C00 for  CR5D0SRUAC70(SBOM) Switch and Route Processing Unit A12
               virent8090DEVCR5D0MPUB870(570041),    -- V8R11C00 for  CR5D0MPUB870(SBOM) Main Processing Unit B8
               virent8090DEVCX6DNPU1TM70(675869),    -- V8R11C00 for  CX6DNPU1TM70(SBOM) Network Processing Unit (NPU-1T)
			   virent8090DEVME0DBSUFT070(675980),     -- V8R11C10 for ME0DBSUFT070(SBOM) Flexible Card Broadband Service Unit(BSUF-1T,2 sub-slots)
		       virent8090DEVME0DMSUFT070(675981),     -- V8R11C10 for ME0DMSUFT070(SBOM) Flexible Card Multi Service Unit(MSUF-1T,2 sub-slots)
               --V8R11C00 for CR57LPUF1TH
               virent8090DEVCR5DLPUFT070(675815),    -- V8R11C00 for  CR5DLPUFT070(SBOM) Flexible Card Line Processing Unit T(LPUF-1T-T)
			   virent8090DEVCX6DISUFT010(675982),     -- V8R11C10 for CX6DISUFT010(SBOM) Flexible Card Integrated Service Unit(ISUF-1T)
               virent8090DEVCR5D00E8NB70(675816),     -- V8R11C00 for  CR5D00E8NB70(SBOM) 8-Port 100GBase-QSFP28 Integrated Line Processing Unit(LPUI-1T-T)
               --BEGIN for V8R11C00 by lwx354721
               virent8090DEVCR5D00LRXF60(567007),    -- V8R11C00 for CR5D00LRXF60(SBOM) 72-Port 10GBase LAN/WAN-SFP+ Integrated Line Process Unit(NE5000E LPUI-1T6)
               virent8090DEVCR5D00EDNB62(567008),    -- V8R11C00 for CR5D00EDNB62(SBOM) 16-Port 100GBase QSFP28 Integrated Line Process Unit(NE5000E LPUI-1T6)
               virent8090DEVCR5D00E4KC60(567009),    -- V8R11C00 for CR5D00E4KC60(SBOM) 4-Port 400GBase CFP8 Integrated Line Process Unit(NE5000E LPUI-1T6)
               --END
               --BEGIN for V8R11C10 by lwx354721
               virent8090DEVCR9D0SFUT48D(562082),    -- V8R11C10 for CR58SFU4TD(SBOM) NE9000-20 Switch Fabric Unit F for Single Chassis(SFU4T-D)
               virent8090DEVCR9D0SFUT48E(562080),    -- V8R11C10 for CR58SFU4TE(SBOM) NE9000-8 Switch Fabric Unit for Single Chassis(SFU4T-E)
               virent8090DEVCR5D00EDNB63(561793),    -- V8R12C00 for CR5D00EDNB63(SBOM) 16-Port 100GBase QSFP28 Integrated Line Process Unit CM(NE5000E LPUI-1T6-CM)(4 ports enable)
               virent8090DEVCR5D00E4KB61(561794),    -- V8R11C10 for CR5D00E4KB61(SBOM) 4-Port 400GBase QSFP-DD Integrated Line Process Unit CM(NE5000E LPUI-1T6-CM)
               virent8090DEVCR5D00NDNC61(561795),    -- V8R11C10 for CR5D00NDNC61(SBOM) 16-Port 100G OTN/ETH QSFP28 Integrated Line Process Unit(NE5000E LPUI-1T6-CM)
               virent8090DEVCR5D00LRXF61(561792),    -- V8R11C10 for CR5D00LRXF61(SBOM) 72-Port 10GBase LAN/WAN-SFP+ Integrated Line Process Unit CM(NE5000E LPUI-1T6-CM
               --END
               --BEGIN for V8R12C10 by wx706053
               virent8090DEVCR5DSFUIT252(561840),    -- V8R12C10 for CR5DSFUIT252(SBOM) NE5000E CCC-A 1.6T Cluster Central Switch Fabric Unit G-C(SFUI-1T6-G)
               virent8090DEVCR5DSFUIT253(561841),    -- V8R12C10 for CR5DSFUIT253(SBOM) NE5000E CCC-A 1.6T Cluster Central Switch Fabric Unit G-C(SFUI-1T6-G)
               virent8090DEVCR5DSFUIT2DH(561842),    -- V8R12C10 for CR5DSFUIT2DH(SBOM) NE5000E CCC-A 1.6T Cluster Central Switch Fabric Unit H-C(SFUI-1T6-H)
               virent8090DEVCR5DSFUIT2DJ(561844),    -- V8R12C10 for CR5DSFUIT2DJ(SBOM) NE5000E CCC-A 1.6T Cluster Central Switch Fabric Unit H-C(SFUI-1T6-H)
               virent8090DEVCR5DSFUIT2D0(561843),    -- V8R12C10 for CR5DSFUIT2D0(SBOM) NE5000E CCC-A 1.6T Cluster Central Switch Fabric Unit D-C(SFUI-1T6-D)
               virent8090DEVCR5DSFUIT2D1(561845),    -- V8R12C10 for CR5DSFUIT2D1(SBOM) NE5000E CCC-A 1.6T Cluster Central Switch Fabric Unit D-C(SFUI-1T6-D)
               virent8090DEVCR5D000CMU63(675999),    -- V8R12C10 for CR5D000CMU63(SBOM) Centralized Monitoring Module 2.0
               virent8090DEVCR5D0MPUQ2D1(567016),   -- v8r12c10 NE5000E-20 Main Processing Unit Q2(MPUQ2)
               virent8090DEVCR5D0MPUQ2D0(567015),   -- v8r12c10 NE5000E-20 Main Processing Unit Q2(MPUQ2)
               virent8090DEVCR9D0MPUQ280(561800),   -- v8r12c10 NE9000-20 Main Processing Unit Q2(MPUQ2)
               --END
               --BEGIN for V8R11C10 by zwx637795
               virent8090DEVCR9D0MPUR180(561790), -- v8r12c00 NE9000-8 Main Processing Unit R1(MPUR1)
               virent8090DEVCR5D0MPUQ1D1(567013), -- v8r12c00 NE5000E-20 Main Processing Unit Q1(MPUQ1)
               virent8090DEVCR5D0MPUQ1D0(567014), -- v8r12c00 NE5000E-20 Main Processing Unit Q1(MPUQ1)
               virent8090DEVCR9D0MPUQ180(561789), -- v8r12c00 NE9000-20 Main Processing Unit Q1(MPUQ1)
               --END:
               --BEGIN for V8R11C10 by zwx637795
               virent8090DEVCR5D0SFUT2D1(561796),    -- V8R11C10 for CR5D0SFUT2D1(SBOM) NE5000E-20 2T CLC Switch Fabric Unit S for Single Chassis(SFU-2T-S)
               virent8090DEVCR5D0SFUT2D2(561797),    -- V8R11C10 for CR5D0SFUT2D2(SBOM) NE5000E-20 2T CLC Switch Fabric Unit S for Single Chassis(SFU-2T-S)
               virent8090DEVCR5D00EENBD0(561798),    -- V8R11C10 for CR5D00EENBD0(SBOM) 20-Port 100GEQSFP28 Integrated Line Process Unit(NE5000E LPUI-2T)
               virent8090DEVCR5D00EENBD1(561799),    -- V8R11C10 for CR5D00EENBD1(SBOM) 20-Port 100GEQSFP28 Integrated Line Process Unit(NE5000E LPUI-2T)
               virent8090DEVCR5D00EPXFD0(561802),    -- V8R11C10 for CR5D00EPXFD0(SBOM) 60-Port 10GBase LAN/WAN-SFP+  Integrated Line Process Unit(NE5000E LPUI-2T)
               virent8090DEVCR5D00EPXFD1(561803),    -- V8R11C10 for CR5D00EPXFD1(SBOM) 60-Port 10GBase LAN/WAN-SFP+  Integrated Line Process Unit(NE5000E LPUI-2T)
               virent8090DEVCR5D0MPUB661(561806),    -- V8R11C10 for CR5D0MPUB661(SBOM) NE5000E Main Processing Unit B6
               virent8090DEVCR5D00EDNB64(561807),    -- for CR5D00EDNB64(SBOM) 16-Port 100GBase QSFP28 Integrated Line Process Unit CM(NE5000E LPUI-1T6-CM)
               virent8090DEVCR5D00E4KB60(561784),     -- V8R11C10 for CR5D00E4KB60(SBOM) 4-Port 400GBase QSFP-DD Integrated Line Process Unit(NE5000E LPUI-1T6)
               virent8090DEVCR5D00E4KB62(561817),    -- CR5D00E4KB62(SBOM) 4-Port 400GBase QSFP-DD Integrated Line Process Unit CM(NE5000E LPUI-1T6-CM) (1 port enable)
               virent8090DEVCR5D00LRXF62(561818),    -- CR5D00LRXF62(SBOM) 72-Port 10GBase LAN/WAN-SFP+ Integrated Line Process Unit CM(NE5000E LPUI-1T6-CM) (24 ports enable)
               --END
               --BEGIN for V8R11C00 by swx305268
               virent8090DEVCR5DSFUIT27E(567056),    -- V8R10C10 for CR5DSFUIT27E(SBOM) 2Tbps Switch Fabric Unit E(SFUI-2T-E)
               virent8090DEVCR5DSFUIU07F(567055),    -- V8R10C10 for CR5DSFUIU07F(SBOM) 2Tbps Switch Fabric Unit F(SFUI-2T-F)
               --END
			   --BEGIN for V8R11C10 by zwx694669
			   virent8090DEVCX6DSFUIT27E(675983), 	 -- V8R11C10 for CX6DSFUIT27E(SBOM)  2Tbps Switch Fabric Unit E(SFUI-2T-E)
			   virent8090DEVTNRDSFUIT27E(675984),	 -- V8R11C10 for TNRDSFUIT27E(SBOM)  2Tbps Switch Fabric Unit E(SFUI-2T-E)
			   virent8090DEVCX6DSFUIU07F(675985), 	 -- V8R11C10 for CX6DSFUIU07F(SBOM)  2Tbps Switch Fabric Unit F(SFUI-2T-F)
			   virent8090DEVTNRDSFUIU07F(675986), 	 -- V8R11C10 for TNRDSFUIU07F(SBOM)  2Tbps Switch Fabric Unit F(SFUI-2T-F)
			   --END

               --BEGIN for V8R11C00 TPM by swx305268
               virent8090DEVME0D0MPUB771(675480),    -- V8R11C00 for ME0D0MPUB771(SBOM) Main Processing Unit B7
               virent8090DEVCR5D0MPUB773(675481),    -- V8R11C00 for CR5D0MPUB773(SBOM) Main Processing Unit B7
               virent8090DEVCR5D0SRUAC7B(675482),    -- V8R11C00 for CR5D0SRUAC7B(SBOM) Switch and Route Processing Unit A12
               virent8090DEVME0D0SRUAC7B(675483),    -- V8R11C00 for ME0D0SRUAC7B(SBOM) Switch and Route Processing Unit A12
               virent8090DEVCR5D0SRUAC71(675484),    -- V8R11C00 for CR5D0SRUAC71(SBOM) Switch and Route Processing Unit A16
               virent8090DEVCR5D0MPUB871(675485),    -- V8R11C00 for CR5D0MPUB871(SBOM) Main Processing Unit B8
               virent8090DEVCR5DMPUX8671(675486),    -- V8R11C00 for CR5DMPUX8671(SBOM) Main Processing Unit B6
               virent8090DEVME0DMPUX8671(675487),    -- V8R11C00 for ME0DMPUX8671(SBOM) Main Processing Unit B6
               --END
			   --BEGIN for V8R11C10 by zwx694669
			   virent8090DEVCX6D0MPUB871(675989),    -- V8R11C10 for CX6D0MPUB871(SBOM) Main Processing Unit B8
			   virent8090DEVCX6D0SRUAC71(675990),    -- V8R11C10 for CX6D0SRUAC71(SBOM) Switch and Route Processing Unit A16
			   virent8090DEVTNRD0MPUB871(675991),    -- V8R11C10 for TNRD0MPUB871(SBOM) Main Processing Unit B8
			   virent8090DEVTNRD0SRUAC71(675992),    -- V8R11C10 for TNRD0SRUAC71(SBOM) Switch and Route Processing Unit A16
			   --END
			   virent8090DEVCX6DLPUFK0A0(570064),     -- V8R11C00 for CX6DLPUFK0A0(SBOM) 480G Flexible Card Line Processing Unit C(CX6600 LPUF-480C,2 sub-slots)
               virent8090DEVCR5DF1EFXC7P(675821),    -- V8R11C00 for  CR5DF1EFXC7P(SBOM) 24-Port 10GBase LAN/WAN-SFP+ Integrated Line Processing Unit CM(LPUI-241-CM)
               --BEGIN for V8R11C00 by lwx444598
               virent8090DEVCR5DLPUF5270(675820),  -- V8R11C00 for CR5DLPUF5270(SBOM) Flexible Card Line Processing Unit(LPUF-52,2 sub-slots)
               --END
               --BEGIN for V8R11C10 by lwx658302
               virent8090DEVCR5D00EENB7Q(675970),     -- V8R11C10 for CR5D00EENB7Q(SBOM) 20-Port 100GBase-QSFP28 FlexE/MACsec Integrated Line Processing Unit CM(LPUI-2T-CM)

               virent8090DEVCR5DMPUX8670-VMPU(577001),       -- for V800R011C10 CR5DMPUX8670-VMPU, VMPU In Main Processing Unit B6
               virent8090DEVCR5D0SRUAA70-VMPU(577002),       -- for V800R011C10 CR5D0SRUAA70-VMPU, VMPU In Switch and Route Processing Unit A10(32G Memory)
               virent8090DEVCR5D0SRUAB73-VMPU(577003),        -- for V800R011C10 CR5D0SRUAB73-VMPU, VMPU In Switch and Route Processing Unit A11
               --END
			   --BEGIN for V8R11C10 by lwx658299
               virent8090DEVCR5DNKFEDY70(675988),     -- V8R11C10 for CR5DNKFEDY70(SBOM) 40-Port 10Gase LAN/WAN-SFP+ MACsec Integrated Line Processing Unit (LPUI-400)
			   virent8090DEVCR5DNKFEDY71(675993),     -- V8R11C10 for CR5DNKFEDY71(SBOM) 40-Port 10Gase LAN/WAN-SFP+ MACsec Integrated Line Processing Unit (LPUI-400A)
               --END
                --BEGIN for V8R11C10 by lwx658302
               virent8090DEVCR9D00EENB83(675971),    -- V8R11C10 for CR9D00EENB83(SBOM) 20-Port 100GE-QSFP28 FlexE/MACSec Integrated Line Process Unit CM(LPUI-2T-CM)
			   virent8090DEVCR9D00EKNB8M(675972),    -- V8R11C10 for CR9D00EKNB8M(SBOM) 40-Port 40GE/100GE QSFP28 Integrated Line Process Unit L(LPUI-4T-L)
               --END
               --BEGIN for V8R11C00 TPM by ywx658300
               virent8090DEVCX6D0MPUB810(675973),    -- V8R11C00 for CX6D0MPUB810(SBOM) Main Processing Unit B8A(32G Memory)
               virent8090DEVCX6DSFUIT27C(675974),    -- V8R11C00 for CX6DSFUIT27C(SBOM) 2Tbps Switch Fabric Unit E(SFUI-2T-E)
               virent8090DEVCX6D0SRUAG10(675975),    -- V8R11C00 for CX6D0SRUAG10(SBOM) Switch and Route Processing Unit A16A(32G Memory)
               virent8090DEVCX6DSFUIU01F(675976),    -- V8R11C00 for CX6DSFUIU01F(SBOM) 2Tbps Switch Fabric Unit F(SFUI-2T-F)
               virent8090DEVCX6D00E8NB70(675977),    -- V8R11C00 for CX6D00E8NB70(SBOM) 8-Port 100GBase-QSFP28 Integrated Integrated Service Unit(ISUI-1T)
               --END
               --BEGIN for V8R11C10 TPM by WX694669
               virent8090DEVCR5DEDVE8N7P(675978),    -- V8R11C10 for CR5DEDVE8N7P(SBOM) 16-Port 50G/8-Port 100GBase-QSFP28 FlexE/MACsec Integrated Line Processing Unit CM(LPUI-1T-CM)
               virent8090DEVCR5D00EIYB7P(675979),    -- V8R11C10 for CR5D00EIYB7P(SBOM) 32-Port 25GBase-SFP28 MACsec Integrated Line Processing Unit CM(LPUI-1T-CM)
               virent8090DEVCR5D00EENB73(675987),     -- V8R11C10 for CR5D00EENB73(SBOM) 20-Port 100GBase-QSFP28 Integrated Line Processing Unit (LPUI-2TA)
			   --END
               --BEGIN for V8R11C10 400A by lWX658299
               virent8090DEVCX6D0E2NBF10(675998),     -- V8R11C10 for CX6D0E2NBF10(SBOM) 2-Port 100GBase-QSFP28 FlexE/MACsec Integrated Integrated Service Unit (ISUI-201)
               virent8090DEVCX6D0E4NBF10(675995),     -- V8R11C10 for CX6D0E4NBF10(SBOM) 4-Port 100GBase-QSFP28 FlexE/MACsec Integrated Integrated Service Unit(ISUI-401)
               virent8090DEVCX6D0E8YFA10(675831),     -- v8r11c10 for CX6D0E8YFA10(SBOM) 8-Port 25GBase-SFP28 Integrated Integrated Service Unit (ISUI-201)
               virent8090DEVCR5DEDVE8N70(676991),     -- V8R11C10 for CR5DEDVE8N70(SBOM) 16-Port 50G/8-Port 100GBase-QSFP28 Integrated Line Processing Unit L(LPUI-1T-L)
               virent8090DEVCR5D00EENB72(676992),     -- V8R11C10 for CR5D00EENB72(SBOM) 20-Port 100GBase-QSFP28 Integrated Line Processing Unit L(LPUI-2T-L)
               virent8090DEVCR5D0MPUB970(567800),    -- V8R12C00 for CR5D0MPUB970(SBOM) Main Processing Unit B9(32G Memory)
               virent8090DEVCX6D0MPUB970(567801),    -- V8R12C00 for CX6D0MPUB970(SBOM) Main Processing Unit B9(32G Memory)
               virent8090DEVTNRD0MPUB970(567802),    -- V8R12C00 for TNRD0MPUB970(SBOM) Main Processing Unit B9(32G Memory)
               virent8090DEVME0DMPUX8970(567803),    -- V8R12C00 for ME0DMPUX8970(SBOM) Main Processing Unit B9(32G Memory)
               virent8090DEVCX6D0MPUB910(567804),    -- V8R12C00 for CX6D0MPUB910(SBOM) Main Processing Unit B9(32G Memory)
               virent8090DEVCR5D0SRUAF70(567805),    -- V8R12C00 for CR5D0SRUAF70(SBOM) Switch and Route Processing Unit A15(32G Memory)
               virent8090DEVCX6D0SRUAF70(567806),    -- V8R12C00 for CX6D0SRUAF70(SBOM) Switch and Route Processing Unit A15(32G Memory)
               virent8090DEVTNRD0SRUAF70(567807),    -- V8R12C00 for TNRD0SRUAF70(SBOM) Switch and Route Processing Unit A15(32G Memory)
               virent8090DEVME0D0SRUAF71(567808),    -- V8R12C00 for ME0D0SRUAF71(SBOM) Switch and Route Processing Unit A15(32G Memory)
               virent8090DEVCX6D0SRUAF10(567809),    -- V8R12C00 for CX6D0SRUAF10(SBOM) Switch and Route Processing Unit A15(32G Memory)
               virent8090DEVCR5D0SRUAE70(567810),    -- V8R12C00 for CR5D0SRUAE70(SBOM) Switch and Route Processing Unit A14(32G Memory)
               virent8090DEVCX6D0SRUAE70(567811),    -- V8R12C00 for CX6D0SRUAE70(SBOM) Switch and Route Processing Unit A14(32G Memory)
               virent8090DEVTNRD0SRUAE70(567812),    -- V8R12C00 for TNRD0SRUAE70(SBOM) Switch and Route Processing Unit A14(32G Memory)
               virent8090DEVME0D0SRUAD70(567813),    -- V8R12C00 for ME0D0SRUAD70(SBOM) Switch and Route Processing Unit A14(32G Memory)
               virent8090DEVCX6D0SRUAE10(567814),    -- V8R12C00 for CX6D0SRUAE10(SBOM) Switch and Route Processing Unit A14(32G Memory)
               virent8090DEVCR5D0SRUAD70(567815),    -- V8R12C00 for CR5D0SRUAD70(SBOM) Switch and Route Processing Unit A13(32G Memory)
               virent8090DEVCX6D0SRUAD70(567816),    -- V8R12C00 for CX6D0SRUAD70(SBOM) Switch and Route Processing Unit A13(32G Memory)
               virent8090DEVTNRD0SRUAD70(567817),    -- V8R12C00 for TNRD0SRUAD70(SBOM) Switch and Route Processing Unit A13(32G Memory)
               virent8090DEVCR5D0MPUB971(567818),   -- V8R12C00 for CR5D0MPUB971(SBOM) Main Processing Unit B9A(32G Memory)
               virent8090DEVME0DMPUX8971(567819),    -- V8R12C00 for ME0DMPUX8971(SBOM) Main Processing Unit B9A(32G Memory)
               virent8090DEVCR5D0SRUAD71(567820),    -- V8R12C00 for CR5D0SRUAD71(SBOM) Switch and Route Processing Unit A13A(32G Memory)
               virent8090DEVCR5DSFUIT27G(688300),     -- V8R11C10 for CR5DSFUIT27G(SBOM) 2Tbps Switch Fabric Unit E1(SFUI-2T-E)
               virent8090DEVCR5DSFUIT27H(688301),     -- V8R11C10 for CR5DSFUIT27H(SBOM) 2Tbps Switch Fabric Unit E1(SFUI-2TA-E)
               virent8090DEVCR5DSFUIT27I(688302),     -- V8R11C10 for CR5DSFUIT27I(SBOM) 2Tbps Switch Fabric Unit F1(SFUI-2T-F)
               virent8090DEVCR5DSFUIT27J(688303),     -- V8R11C10 for CR5DSFUIT27J(SBOM) 2Tbps Switch Fabric Unit F1(SFUI-2TA-F)
               virent8090DEVCR5D0EKGFA71(688304),     -- V8R11C10 for CR5D0EKGFA71(SBOM) 40-Port 100/1000Base-X-SFP MACsec Integrated Line Processing Unit (LPUI-52)
               virent8090DEVCR5D0EKGFA72(688305),     -- V8R11C10 for CR5D0EKGFA72(SBOM) 40-Port 100/1000Base-X-SFP MACsec Integrated Line Processing Unit (LPUI-52A)
               virent8090DEVCR5D0E2NBA70(688306),     -- V8R11C10 for CR5D0E2NBA70(SBOM) 4-Port 50G/2-Port 100GBase-QSFP28 FlexE/MACsec Integrated Line Processing Unit(LPUI-242)
               virent8090DEVCR5D0EEXFA70(688307),     -- V8R11C10 for CR5D0EEXFA70(SBOM) 24-Port 10GBase LAN/WAN-SFP+ MACsec Integrated Line Processing Unit(LPUI-242)
               virent8090DEVCR5D0E8YFA70(688308),     -- V8R11C10 for CR5D0E8YFA70(SBOM) 8-Port 25GBase-SFP28 MACsec Integrated Line Processing Unit(LPUI-242)
               virent8090DEVCR5D0E2NBA71(688309),     -- V8R11C10 for CR5D0E2NBA71(SBOM) 4-Port 50G/2-Port 100GBase-QSFP28 FlexE/MACsec Integrated Line Processing Unit(LPUI-242A)
               virent8090DEVCR5D0EEXFA71(688310),     -- V8R11C10 for CR5D0EEXFA71(SBOM) 24-Port 10GBase LAN/WAN-SFP+ MACsec Integrated Line Processing Unit(LPUI-242A)
               virent8090DEVCR5D0E2NBA72(688311),     -- V8R11C10 for CR5D0E2NBA72(SBOM) 4-Port 50G/2-Port 100GBase-QSFP28 FlexE/MACsec Integrated Line Processing Unit(LPUI-242-G)
               virent8090DEVCR5D0E4NBA70(688312),     -- V8R11C10 for CR5D0E4NBA70(SBOM) 4-Port 100GBase-QSFP28 FlexE/MACsec Integrated Line Processing Unit (LPUI-402)
               virent8090DEVCR5D0E4NBA71(688313),     -- V8R11C10 for CR5D0E4NBA71(SBOM) 4-Port 100GBase-QSFP28 FlexE/MACsec Integrated Line Processing Unit (LPUI-402A)
               virent8090DEVCR5D0E4NBA72(676921),     -- V800R012C00 for CR5D0E4NBA72(SBOM) 4-Port 100GBase-QSFP28 FlexE/MACsec Integrated Line Processing Unit CM(LPUI-402-CM)
               virent8090DEVCR5DNKFEDY72(676922),     -- V800R012C00 for CR5DNKFEDY72(SBOM) 40-Port 10Gase LAN/WAN-SFP+ MACsec Integrated Line Processing Unit CM(LPUI-402-CM)
               virent8090DEVCR5D0EEXFA72(676923),     -- V800R012C00 for CR5D0EEXFA72(SBOM) 24-Port 10GBase LAN/WAN-SFP+ MACsec Integrated Line Processing Unit CM(LPUI-242-CM)
               virent8090DEVCR5DVSUIK071(676951),    -- V8R12C00 for CR5DVSUIK071(SBOM) Integrated Versatile Service Unit 400(VSUI-400-E)
               virent8090DEVCR5DVSUIK073(676952),    -- V8R12C00 for CR5DVSUIK073(SBOM) Integrated Versatile Service Unit 400(VSUI-400A-E)
               virent8090DEVME0DVSUIK071(676953),    -- V8R12C00 for ME0DVSUIK071(SBOM) Integrated Versatile Service Unit(VSUI-400-E)
               virent8090DEVME0DVSUIK073(676954),    -- V8R12C00 for ME0DVSUIK073(SBOM) Integrated Versatile Service Unit(VSUI-400A-E)
               virent8090DEVCR5DVSUIK070(676955),    -- V8R12C00 for CR5DVSUIK070(SBOM) Integrated Service Unit 400(VSUI-400)
               virent8090DEVCR5DVSUIK072(676956),    -- V8R12C00 for CR5DVSUIK072(SBOM) Integrated Service Unit 400A(VSUI-400A)
               virent8090DEVCR5DJYSUK072(676957),    -- V8R12C00 for CR5DJYSUK072(SBOM) Public Security Service Unit(PSSU-A)
               virent8090DEVME0DVSUIK070(676958),    -- V8R12C00 for ME0DVSUIK070(SBOM) Integrated Service Unit 400(VSUI-400)
               virent8090DEVME0DVSUIK072(676959),    -- V8R12C00 for ME0DVSUIK072(SBOM) Integrated Versatile Service Unit(VSUI-400A)
               virent8090DEVME0DJYSUK070(676960),    -- V8R12C00 for ME0DJYSUK070(SBOM) Public Security Service Unit(PSSU-A)
               --END
               --BEGIN for V8R11C10 TR6
               virent8090DEVCX6D00EKGF10(676924),    -- V8R11C10 for CX6D00EKGF10(SBOM) 40-Port 100/1000Base-X-SFP Integrated Line Processing Unit (LPUI-52A)
               virent8090DEVCX6DE4VE2N10(676925),    -- V8R11C10 for CX6DE4VE2N10(SBOM) 4-Port 50G/2-Port 100GBase-QSFP28 Integrated Line Processing Unit(LPUI-242A)
               virent8090DEVCX6D00EFXF10(676926),    -- V8R11C10 for CX6D00EFXF10(SBOM) 24-Port 10GBase LAN/WAN-SFP+ Integrated Line Processing Unit(LPUI-242A)
               virent8090DEVCX6D00E4NB10(676927),    -- V8R11C10 for CX6D00E4NB10(SBOM) 4-Port 100GBase-QSFP28 Integrated Line Processing Unit (LPUI-402A)
               virent8090DEVCX6D00EKXF10(676928),    -- V8R11C10 for CX6D00EKXF10(SBOM) 40-Port 10GBase LAN/WAN-SFP+ Integrated Line Processing Unit (LPUI-402A)
               virent8090DEVCX6DLPUFT010(676929),    -- V8R11C10 for CX6DLPUFT010(SBOM) Flexible Card Line Processing Unit (LPUF-1T1)
               virent8090DEVCX6DE4VE2N11(676930),    -- V8R11C10 for CX6DE4VE2N11(SBOM) 4-Port 50G/2-Port 100GBase-QSFP28 Integrated Integrated Service Unit (ISUI-242)
               virent8090DEVCX6D00E4NB11(676931),    -- V8R11C10 for CX6D00E4NB11(SBOM) 4-Port 100GBase-QSFP28 Integrated Integrated Service Unit(ISUI-402)
               virent8090DEVCR5DLEXEEG70(676932),    --V8R11C10 for CR5DLEXEEG70(SBOM) 20-Port 10Gase LAN/WAN-SFP+ and 20-Port 100/1000Base-X-SFP Integrated Line Processing Unit(LPUI-242)
               virent8090DEVCX6DSFUIT21G(676935),    -- V8R11C10 for CX6DSFUIT21G(SBOM) Switch Fabric Unit E1(SFUI-1T-E)
               virent8090DEVCX6D0SRUAG12(676936),    -- V8R11C10 for CX6D0SRUAG12(SBOM) Switch and Route Processing Unit A81(16G Memory)
               virent8090DEVCX6DSFUIT21F(676937),    -- V8R11C10 for CX6DSFUIT21F(SBOM) Switch Fabric Unit C1(SFUI-480-C)
               virent8090DEVCX6D0E4VBF10(676938),    -- V8R11C10 for CX6D0E4VBF10(SBOM) 4-Port 50G/2-Port 100GBase-QSFP28 FlexE/MACsec Integrated Integrated Service Unit (ISUI-242)
               virent8090DEVCX6D0EFXFA10(676939),    -- V8R11C10 for CX6D0EFXFA10(SBOM) 24-Port 10GBase LAN/WAN-SFP+ MACsec Integrated Integrated Service Unit (ISUI-242)
               virent8090DEVCX6D0E2NBF11(676940),    -- V8R11C10 for CX6D0E2NBF11(SBOM) 2-Port 100GBase-QSFP28 FlexE Integrated Integrated Service Unit (ISUI-242)
               virent8090DEVCR2DNSP24010(562079),    -- V8R11C10 for CR2DNSP24010(SBOM) Network Service Processor (NSP-240)
               virent8090DEVME0D0E4NBB71(564942),    -- ME0D0E4NBB71 4-Port 100GBase-QSFP28 Broadband Service Unit Integrated (BSUI-402A)
               virent8090DEVME0D0EKXFB70(564943),    -- ME0D0EKXFB70 40-Port 10GBase LAN/WAN-SFP+ Broadband Service Unit Integrated (BSUI-402)
               virent8090DEVME0D0EKXFB71(564944),    -- ME0D0EKXFB71 40-Port 10GBase LAN/WAN-SFP+ Broadband Service Unit Integrated (BSUI-402A)
               virent8090DEVME0DE2NEEX70(564945),    -- ME0DE2NEEX70 2-Port 100GBase-QSFP28 + 20-Port 10GBase LAN/WAN-SFP+ Broadband Service Unit Integrated (BSUI-402A)
               virent8090DEVCX6DNKFEDY70(564935),    -- CX6DNKFEDY70 40-Port 10GBase LAN/WAN-SFP+ MACsec Integrated Integrated Service Unit(ISUI-402)
               virent8090DEVCX6D0EKGFA71(564919),    -- CX6D0EKGFA71 40-Port 100/1000Base-X-SFP MACsec Integrated Integrated Service Unit(ISUI-52)
               virent8090DEVME0DE4VE2N70(564938),    -- ME0DE4VE2N70 4-Port 50G/2-Port 100GBase-QSFP28 Broadband Service Unit Integrated (BSUI-242)
               virent8090DEVME0DE4VE2N71(564940),    -- ME0DE4VE2N71 4-Port 50G/2-Port 100GBase-QSFP28 Broadband Service Unit Integrated(BSUI-242A)
               virent8090DEVME0D0EFXFB70(564939),    -- ME0D0EFXFB70 24-Port 10GBase LAN/WAN-SFP+ Broadband Service Unit Integrated (BSUI-242)
               virent8090DEVME0D0EFXFB71(564941),    -- ME0D0EFXFB71 24-Port 10GBase LAN/WAN-SFP+ Broadband Service Unit Integrated (BSUI-242A)
               virent8090DEVME0D0EKGFB70(564936),    -- ME0D0EKGFB70 40-Port 100/1000Base-X-SFP Broadband Service Unit Integrated (BSUI-52)
               virent8090DEVME0D0EKGFB71(564937),    -- ME0D0EKGFB71 40-Port 100/1000Base-X-SFP Broadband Service Unit Integrated (BSUI-52A)
               virent8090DEVCX6D0E2NBA72(564931),    -- CX6D0E2NBA72 4-Port 50G/2-Port 100GBase-QSFP28 FlexE/MACsec Integrated Integrated Service Unit(ISUI-242-G)
               virent8090DEVCX6D0EEXFA70(564927),    -- CX6D0EEXFA70 20-Port 10GBase LAN/WAN-SFP+ Integrated Integrated Service Unit (ISUI-242)
               virent8090DEVCR5D00E4NC7P(564917),    -- CR5D00E4NC7P 4-Port 100G ETH/DWDM-CFP2 Integrated Line Processing Unit CM(LPUI-480-CM)
               virent8090DEVCR5D00D8NC70(564916),    -- CR5D00D8NC70 8-Port 100G ETH/DWDM-CFP2 Integrated Line Processing Unit(LPUI-1T)
               --END
			   --BEGIN for V8R12C00 TR6
			   virent8090DEVCR9D0MPUR181(688406),    -- V8R12C00 for CR9D0MPUR181(SBOM) NE9000-8 Main Processing Unit R1(MPUR1A)
			   virent8090DEVCR9D0SFUT48G(688407),    -- V8R12C00 for CR9D0SFUT48G(SBOM) NE9000-8 Switch Fabric Unit E for Single Chassis(SFU4T-EA)
			   --END
			   --BEGIN for V8R12C11 TR5
			   virent8090DEVCR9D0MPUR280(688408),    -- V8R12C11 for CR9D0MPUR280(SBOM) NE9000-8 Main Processing Unit R2(MPUR2)
			   virent8090DEVCR9D0MPUR281(688409),    -- V8R12C11 for CR9D0MPUR281(SBOM) NE9000-8 Main Processing Unit R2A(MPUR2A)
			   virent8090DEVCR9D0SFUTG80(688410),    -- V8R12C11 for CR9D0SFUTG80(SBOM) NE9000-20 Switch Fabric Unit G for Single Chassis(SFU4T-G)
			   virent8090DEVCR9D0SFUTH80(688420),    -- V8R12C11 for CR9D0SFUTH80(SBOM) NE9000-8 Switch Fabric Unit H for Single Chassis(SFU4T-H)
			   virent8090DEVCR9D0SFUTH81(688421),    -- V8R12C11 for CR9D0SFUTH81(SBOM) NE9000-8 Switch Fabric Unit HA for Single Chassis(SFU4T-HA)
			   --END
               -- CR57LPUF1TQ
               virent8090DEVCR5DLPUFT071(688314),     -- V8R12C20 for CR5DLPUFT071(SBOM) Finished Board Unit,NetEngine40E,CR57LPUF1TQ00,Flexible Card Line Processing Unit(LPUF-1T2)
               virent8090DEVCR5DLPUFT072(688315),     -- V8R12C20 for CR5DLPUFT072(SBOM) Finished Board Unit,NetEngine40E,CR57LPUF1TQ01,Flexible Card Line Processing Unit(LPUF-1T2A)
               virent8090DEVCX6DISUFT011(688316),     -- V8R12C00 for CX6DISUFT011(SBOM) Finished Board Unit,CX600,CR57LPUF1TQ02,Flexible Card Integrated Service Unit(ISUF-1T) A
               virent8090DEVME0DBSUFT072(598601),     -- V8R12C20 for ME0DBSUFT072(SBOM) Finished Board Unit,ME60,CR57LPUF1TQ03,Flexible Card Broadband Service Unit(BSUF-1T,2 sub-slots)
               virent8090DEVME0DMSUFT073(598602),     -- V8R12C20 for ME0DMSUFT073(SBOM) Finished Board Unit,ME60,CR57LPUF1TQ04,Flexible Card Multi Service Unit(MSUF-1T,2 sub-slots)
               virent8090DEVME0DBSUFT074(598603),     -- V8R12C20 for ME0DBSUFT074(SBOM) Finished Board Unit,ME60,CR57LPUF1TQ05,Flexible Card Broadband Service Unit(BSUF-1TA,2 sub-slots)
               virent8090DEVME0DMSUFT075(598604),     -- V8R12C20 for ME0DMSUFT075(SBOM) Finished Board Unit,ME60,CR57LPUF1TQ06,Flexible Card Multi Service Unit(MSUF-1TA,2 sub-slots)
               virentDEVCR8DIPU1T2C1(800000),           -- V8R11C10 for DEVCR8DIPU1T2C1(SBOM) Integrated Network Processing Unit (IPU-1T2)
               virentDEVCR8DIPU1T2C2(800001),           -- V8R11C10 for DEVCR8DIPU1T2C2(SBOM) Integrated Network Processing Unit (IPU-1T2)
               --BEGIN for V8R12C00 F1A and V8R11C10 1T&2T bundle
               virent600DEVCR8B0BKP03C0(688332),    --V8R12C00 NetEngine-8000-F1A CR8B0BKP03C0(SBOM), F1A-8H20Q
               virent600DEVCR8B0BKP03C1(688333),    --V8R12C00 NetEngine-8000-F1A CR8B0BKP03C1(SBOM), F1A-8H20Q
               virent600DEVCR8B0BKP03C2(688334),    --V8R12C00 NetEngine-8000-F1A CR8B0BKP03C2(SBOM), F1A-8H20Q
               virent600DEVCR8B0BKP03C3(688335),    --V8R12C00 NetEngine-8000-F1A CR8B0BKP03C3(SBOM), F1A-8H20Q
               virent600DEVCR8B0BKP03C4(676976),    --V8R12C11 NetEngine-8000-F1A CR8B0BKP03C4(SBOM), F1A-8H20Q
               virent600DEVCR8B0BKP03C5(676977),    --V8R12C11 NetEngine-8000-F1A CR8B0BKP03C5(SBOM), F1A-8H20Q
			   virent8090DEVCR8B0BKP03D4(689110),  --NetEngine 8000 F1A-8H20Q Intergrated Chassis Components(Port-side Intake)
               virent8090DEVCR8B0BKP03D5(689111),  --NetEngine 8000 F1A-8H20Q Intergrated Chassis Components(Port-side Exhaust)
               virent8090DEVCR8B0BKP03D0(689112),  --NetEngine 8000 F1A-8H20Q Intergrated Chassis Components(Port-side Intake)
               virent8090DEVCR8B0BKP03D2(689113),  --NetEngine 8000 F1A-8H20Q Intergrated Chassis Components(Port-side Exhaust)
               virent8090DEVCR8B0BKP03D6(689114),  --NetEngine 8000 F1A-8H20Q Intergrated Chassis Components(Port-side Intake)
               virent8090DEVCR8B0BKP03D7(689115),  --NetEngine 8000 F1A-8H20Q Intergrated Chassis Components(Port-side Exhaust)
               virent8090DEVCR8B0BKP03D1(689116),  --NetEngine 8000 F1A-8H20Q Intergrated Chassis Components(Port-side Intake)
               virent8090DEVCR8B0BKP03D3(689117),  --NetEngine 8000 F1A-8H20Q Intergrated Chassis Components(Port-side Exhaust)
               virent600DEVCR8PM1ABASC5(688336),    --V8R12C00 NetEngine-8000-M1A CR8PM1ABASC5(SBOM), M1A-8H20Q
               virent600DEVCR8PM1ABASC4(688337),    --V8R12C00 NetEngine-8000-M1A CR8PM1ABASC4(SBOM), M1A-8H20Q
               virent600DEVCR8PM1ABASC0(688338),    --V8R12C00 NetEngine-8000-M1A CR8PM1ABASC0(SBOM), M1A-8H20Q
               virent600DEVCR8PM1ABASC1(688339),    --V8R12C00 NetEngine-8000-M1A CR8PM1ABASC1(SBOM), M1A-8H20Q
               virent600DEVCR8PM1ABASC2(688340),    --V8R12C00 NetEngine-8000-M1A CR8PM1ABASC2(SBOM), M1A-8H20Q
               virent600DEVCR8PM1ABASC3(688345),    --V8R12C00 NetEngine-8000-M1A CR8PM1ABASC3(SBOM), M1A-8H20Q
               virentCR8PM1CBASC6(688350),          --NetEngine 8000 M1C, 2*DC Power, Port Capacity 16*10GE+8*GE(o)+4*GE(e), Default 2*10GE+8*GE
               virentCR8PM1CBASC7(688351),          --NetEngine 8000 M1C, 2*AC Power, Port Capacity 16*10GE+8*GE(o)+4*GE(e), Default 2*10GE+8*GE
               virentCR8PM1CBASA6(688352),          --NetEngine 8000 M1C(A), 2*DC Power, Port Capacity 16*10GE+8*GE(o)+4*GE(e), Default 2*10GE+8*GE
               virentCR8PM1CBASA7(688353),          --NetEngine 8000 M1C(A), 2*AC Power, Port Capacity 16*10GE+8*GE(o)+4*GE(e), Default 2*10GE+8*GE
               virent8090DEVCR5D0SRUAC73(676900),    -- V8R11C10 for CR5D0SRUAC73(SBOM) Switch and Route Processing Unit A161
               virent8090DEVCR5D0SRUAC72(676901),    -- V8R11C10 for CR5D0SRUAC72(SBOM) Switch and Route Processing Unit A16A1
               virent8090DEVCX6D0SRUAG11(676902),    -- V8R11C10 for CX6D0SRUAG11(SBOM) Switch and Route Processing Unit A15
               virent8090DEVCR5DSFUIT070(676903),    -- V8R11C10 for CR5DSFUIT070(SBOM) 1Tbps Switch Fabric Unit E1(SFUI-1T-E)
               virent8090DEVCR5DSFUIT071(676904),    -- V8R11C10 for CR5DSFUIT071(SBOM) 1Tbps Switch Fabric Unit E1(SFUI-1TA-E)
               virent8090DEVCX6DSFUIT070(676907),    -- V8R11C10 for CX6DSFUIT070(SBOM) 1Tbps Switch Fabric Unit E1(SFUI-1T-E))
               virent8090DEVTNRDSFUIT070(676908),    -- V8R11C10 for TNRDSFUIT070(SBOM) 1Tbps Switch Fabric Unit E1(SFUI-1T-E)
               virent8090DEVCX6DSFUIT21D(676909),    -- V8R11C10 for CX6DSFUIT21D(SBOM) Switch Fabric Unit E1(SFUI-1T-E)
               virent8090DEVCR5DSFUIT072(676910),    -- V8R11C10 for CR5DSFUIT072(SBOM) 1Tbps Switch Fabric Unit F1(SFUI-1T-F)
               virent8090DEVCR5DSFUIT073(676911),    -- V8R11C10 for CR5DSFUIT073(SBOM) 1Tbps Switch Fabric Unit F1(SFUI-1TA-F)
               virent8090DEVCX6DSFUIT071(676914),    -- V8R11C10 for CX6DSFUIT071(SBOM) 1Tbps Switch Fabric Unit F1(SFUI-1T-F)
               virent8090DEVTNRDSFUIT071(676915),    -- V8R11C10 for TNRDSFUIT071(SBOM) 1Tbps Switch Fabric Unit F1(SFUI-1T-F)
               virent8090DEVCX6DSFUIT21E(676916),    -- V8R11C10 for CX6DSFUIT21E(SBOM) Switch Fabric Unit F1(SFUI-1T-F)
               virent8090DEVCR5D0SRUAC74(676917),    -- V8R11C10 for CR5D0SRUAC74(SBOM) Switch and Route Processing Unit A15A
               virent8090DEVCR5D0SRUAC75(676918),    -- V8R11C10 for CR5D0SRUAC75(SBOM) Switch and Route Processing Unit A15
               virent8090DEVCX6D0SRUAC72(676919),    -- V8R11C10 for CX6D0SRUAC72(SBOM) Switch and Route Processing Unit A15
               virent8090DEVTNRD0SRUAC72(676920),    -- V8R11C10 for TNRD0SRUAC72(SBOM) Switch and Route Processing Unit A15
               virent600DEVCR8D0IPU2TC1(688341),    --V8R12C00 NetEngine-8000-M14 CR8D0IPU2TC1(SBOM), M14
               virent600DEVCR8D0IPU2TC2(688342),    --V8R12C00 NetEngine-8000-M14 CR8D0IPU2TC2(SBOM), M14
               virent600DEVCR8DIPU1T2C3(688343),    --V8R12C00 NetEngine-8000-M14 CR8DIPU1T2C3(SBOM), M14
               virent600DEVCR8DIPU1T2C4(688344),    --V8R12C00 NetEngine-8000-M14 CR8DIPU1T2C4(SBOM), M14
               virent600DEVCR5D0IPU2TC1(688478),    --V8R12C00 NE40E-X2-M14 CR5D0IPU2TC1(SBOM), M14
               virent600DEVCR5D0IPU2TC2(688479),    --V8R12C00 NE40E-X2-M14 CR5D0IPU2TC2(SBOM), M14
               virent600DEVCR5DIPU1T2C3(688480),    --V8R12C00 NE40E-X2-M14 CR5DIPU1T2C3(SBOM), M14
               virent600DEVCR5DIPU1T2C4(688481),    --V8R12C00 NE40E-X2-M14 CR5DIPU1T2C4(SBOM), M14
               virent600DEVTNRD0IPU2TC1(688482),    --V8R12C00 PTN6900-2-M14 TNRD0IPU2TC1(SBOM), M14
               virent600DEVTNRDIPU1T2C3(688483),    --V8R12C00 PTN6900-2-M14 TNRDIPU1T2C3(SBOM), M14
               virent600DEVCR8DIPU1T2C5(688503),    --V8R12C10 NetEngine-8000-M14 CR8DIPU1T2C5(SBOM), M14
               virent600DEVCR8DIPU1T2C6(688504),    --V8R12C10 NetEngine-8000-M14 CR8DIPU1T2C6(SBOM), M14
               virent600DEVCR8DE8KE8NCP(688505),    --V8R12C10 CR8DE8KE8NCP 8-Port 400GBase-QSFP-DD + 8-Port 100GBase-QSFP28 Integrated Line Processing Unit CM(LPUI-4T-CM,Enable 8*100GE by default)
               virent600DEVCR8DE8KE8NCQ(688506),    --V8R12C10 CR8DE8KE8NCQ 8-Port 400GBase-QSFP-DD + 8-Port 100GBase-QSFP28 Integrated Line Processing Unit L(LPUI-4T-L-CM,Enable 8*100GE by default)
               virent600DEVCR8DE8KE8NCR(688507),    --V8R12C10 CR8DE8KE8NCR 8-Port 400GBase-QSFP-DD + 8-Port 100GBase-QSFP28 Integrated Line Processing Unit CM(LPUI-4TA-CM,Enable 8*100GE by default)
               virent600DEVCR8DE8KE8NCS(688508),    --V8R12C10 CR8DE8KE8NCS 8-Port 400GBase-QSFP-DD + 8-Port 100GBase-QSFP28 Integrated Line Processing Unit L(LPUI-4TA-L-CM,Enable 8*100GE by default)
               virent600DEVCR8D00EKNBC1(688509),    --V8R12C10 CR8D00EKNBC1 40-Port 100GBase-QSFP28 Integrated Line Processing Unit CM(LPUI-4T-CM)
               virent600DEVCR8D00EKNBC5(688510),    --V8R12C10 CR8D00EKNBC5 40-Port 100GBase-QSFP28 Integrated Line Processing Unit CM(LPUI-4TA-CM)
               virent600DEVCR8D00EKNBC2(688511),    --V8R12C10 CR8D00EKNBC2 40-Port 100GBase-QSFP28 Integrated Line Processing Unit L CM(LPUI-4T-L-CM)
               virent600DEVCR8D00EKNBC3(688512),    --V8R12C10 NCR8D00EKNBC3 40-Port 100GBase-QSFP28 Integrated Line Processing Unit L CM(LPUI-4TA-L-CM)
               virent600DEVCR8DIPU480C3(688513),    --V8R12C10 NetEngine-8000-M14 CR8DIPU480C3(SBOM), M14
               virent600DEVCR8DIPU480C4(688514),    --V8R12C10 NetEngine-8000-M14 CR8DIPU480C4(SBOM), M14
               virentDEVCR8DIPU480C1(800002),           -- V8R12C00 for DEVCR8DIPU480C1(SBOM) Integrated Network Processing Unit (IPU-480)
               virentDEVCR8DIPU480C2(800003),           -- V8R12C00 for DEVCR8DIPU480C2(SBOM) Integrated Network Processing Unit (IPUA-480)
               virent600DEVCR8DIPU240C1(800004),    --V8R12C00 NetEngine-8000-M8 CR8DIPU240C1(SBOM), M8
               virent600DEVCR8DIPU240C2(800005),    --V8R12C00 NetEngine-8000-M8 CR8DIPU240C2(SBOM), M8
               virent600DEVCR8DIPU480CT(800006),    --V8R12C11 NetEngine-8000-M8 CR8DIPU480CT(SBOM), M8
               virentDEVTNRDIPU480C1(229555),           -- V8R12C00 for DEVTNRDIPU480C1(SBOM) Integrated Network Processing Unit (IPU-480)
               virent600DEVCR8D0MPUA1C0(688359),    --V8R12C00 NetEngine 8000 Main Processing Unit A1(MPUA1)
               virent600DEVCR8D0MPUA1C1(688373),    --V8R12C00 NetEngine 8000 Main Processing Unit A1A(MPUA1A)
               virent600DEVCR8DSFUI4TC1(688361),    --V8R12C00 NetEngine 8000 X8 4Tbps Switch Fabric Unit(SFUI-4T-B)
               virent600DEVCR8DSFUI4TC3(688362),    --V8R12C00 NetEngine 8000 X8 4Tbps Switch Fabric Unit(SFUIA-4T-B)
               virent600DEVCR8DSFUI4TC0(688363),    --V8R12C00 NetEngine 8000 X4 4Tbps Switch Fabric Unit(SFUI-4T-A)
               virent600DEVCR8DSFUI4TC2(688364),    --V8R12C00 NetEngine 8000 X4 4Tbps Switch Fabric Unit(SFUIA-4T-A)
               virent600DEVCR8D00EKNBCP(688365),    --V8R12C00 40-Port 100GBase-QSFP28 Integrated Line Processing Unit CM(LPUI-4T-CM)
               virent600DEVCR8D00EKNBCR(688366),    --V8R12C00 40-Port 100GBase-QSFP28 Integrated Line Processing Unit CM(LPUIA-4T-CM)
               virent600DEVCR8D00EKNBCQ(688367),    --V8R12C00 40-Port 100GBase-QSFP28 Integrated Line Processing Unit L(LPUI-4T-L)
               virent600DEVCR8D00EKNBC0(688375),    --V8R12C00 40-Port 100GBase-QSFP28 Integrated Line Processing Unit(LPUIA-4T)
               virent600DEVCR8D00LRXFCP(688369),    --V8R12C00 72-Port 25GE(SFP28)/10GE(SFP+)/GE(SFP) Integrated Line Processing Unit CM(LPUI-2T-CM)
               virent600DEVCR8D00LRXFCR(688370),    --V8R12C00 72-Port 25GE(SFP28)/10GE(SFP+)/GE(SFP) Integrated Line Processing Unit CM(LPUIA-2T-CM)
               virent600DEVCR8D00LRXFCQ(688371),    --V8R12C00 72-Port 25GE(SFP28)/10GE(SFP+)/GE(SFP) Integrated Line Processing Unit L(LPUI-2T-L)
               virent600DEVCR8D00LRXFC0(688376),    --V8R12C00 72-Port 25G(SFP28)/10GE(SFP+)/GE(SFP) Integrated Line Processing Unit(LPUIA-2T)
               virentDEVCR8DIPU1T2K0(688500),          -- V8R12C10 for DEVCR8DIPU1T2K0(SBOM) Integrated Network Processing Unit ((IPU-1T2-K))
               virentDEVCR8DIPU1T2K1(688501) ,         -- V8R12C10 for DEVCR8DIPU1T2K1(SBOM) Integrated Network Processing Unit (IPU-1T2-K1)
               virentDEVCR8DIPU480K0(688502),          -- V8R12C10 for DEVCR8DIPU480K0(SBOM) Integrated Network Processing Unit (IPU-480-K)
               virent8090DEVCR8D00EENBC5(688419),   -- 20-Port 100GBase-QSFP28 Integrated Line Processing Unit E CM(LPUI-2TA-E-CM)
               virent8090DEVCR8D00EENBC2(688416),   -- 20-Port 100GBase-QSFP28 Integrated Line Processing Unit CM(LPUI-2TA-CM)
               virent8090DEVCR8D00EENBC4(688418),   -- 20-Port 100GBase-QSFP28 Integrated Line Processing Unit L CM(LPUI-2TA-L-CM)
               virent8090DEVCR8D00EENBC1(688415),   -- 20-Port 100GBase-QSFP28 20-Port 100GBase-QSFP28 Integrated Line Processing Unit CM(LPUI-2T-CM)
               virent8090DEVCR8D00EENBC3(688423),   -- 20-Port 100GBase-QSFP28 Integrated Line Processing Unit L CM(LPUI-2T-L-CM)
               virent8090DEVCR8D00LRXFCU(688412),   -- 72-Port 25GE(SFP28)/10GE(SFP+)/GE(SFP) Integrated Line Processing Unit CM(LPUI-2TA-CM)
               virent8090DEVCR8D00LRXFCT(688411),   -- 72-Port 25GE(SFP28)/10GE(SFP+)/GE(SFP) Integrated Line Processing Unit CM(LPUI-2T-CM)
               virent8090DEVCR8D00LRXFC1(688414),   -- 72-Port 10GE(SFP+)/GE(SFP) Integrated Line Processing Unit(LPUIA-2T)
               virent8090DEVCR8D00LRXFCV(688413),   -- 72-Port 25GE(SFP28)/10GE(SFP+)/GE(SFP) Integrated Line Processing Unit L(LPUI-2T-L-CM)
               virent8090DEVCR8D00LRXFCW(688430),   -- V8R12C11 CR8D00LRXFCW 72-Port 10GE-SFP+ Integrated Line Processing Unit(LPUI-1TA-CM)
               virent8090DEVCR8D0MPUA1C2(688431),   -- V8R12C11 CR8D0MPUA1C2 NetEngine 8000 Main Processing Unit A2(MPUA2)
               virent8090DEVCR8D0MPUA1C3(688432),   -- V8R12C11 CR8D0MPUA1C3 NetEngine 8000 Main Processing Unit A2A(MPUA2A)
               virent600DEVCR8DIPU1T2CB(800007),    --V8R13C00 NetEngine-8000-M8 CR8DIPU1T2CB(SBOM), M8
               virent600DEVCR8DIPU1T2CC(800008),    --V8R13C00 NetEngine-8000-M8 CR8DIPU1T2CC(SBOM), M8
               virent600DEVCR8DIPU240C3(800011),    --V8R13C00 NetEngine-8000-M8 CR8DIPU240C3(SBOM), M8
               virent600DEVCR8DIPU240C4(800012),    --V8R13C00 NetEngine-8000-M8 CR8DIPU240C4(SBOM), M8
               virent600DEVCR8DIPU1T2CG(326481),    --V8R21C10 NetEngine-8000-M8 CR8DIPU1T2CG(SBOM), M8
               virent600DEVCR8DIPU1T2CH(326417),    --V8R21C10 NetEngine-8000-M8 CR8DIPU1T2CH(SBOM), M8
               virent600DEVCR8DIPU480C7(326102),    --V8R21C10 NetEngine-8000-M8 CR8DIPU480C7(SBOM), M8
               virent600DEVTNRDIPU1T2C2(800013),    --V8R13C00 PTN6900-2-M8C TNRDIPU1T2C2(SBOM), M8
               virent600DEVTNRDIPU480C2(800014),    --V8R13C00 PTN6900-2-M8C TNRDIPU480C2(SBOM), M8
               virent600DEVTNRDIPU1T2C7(426587),    --V8R21C10 PTN6900-2-M8C TNRDIPU1T2C7(SBOM), M8
               virent600DEVTNRDIPU480C3(426512),    --V8R21C10 PTN6900-2-M8C TNRDIPU480C3(SBOM), M8
               virent600DEVCR8D0IPU2TC3(800015),    --V8R13C00 NetEngine-8000-M14 CR8D0IPU2TC3(SBOM), M14
               virent600DEVCR8D0IPU2TC4(800016),    --V8R13C00 NetEngine-8000-M14 CR8D0IPU2TC4(SBOM), M14
               virent600DEVCR8DIPU1T2C7(800017),    --V8R13C00 NetEngine-8000-M14 CR8DIPU1T2C7(SBOM), M14
               virent600DEVCR8DIPU1T2C8(800018),    --V8R13C00 NetEngine-8000-M14 CR8DIPU1T2C8(SBOM), M14
               virent600DEVCR8DIPU1T2C9(800019),    --V8R13C00 NetEngine-8000-M14 CR8DIPU1T2C9(SBOM), M14
               virent600DEVCR8DIPU1T2CA(800020),    --V8R13C00 NetEngine-8000-M14 CR8DIPU1T2CA(SBOM), M14
               virent600DEVTNRD0IPU2TC2(800021),    --V8R13C00 PTN6900-M14 TNRD0IPU2TC2(SBOM), M14
               virent600DEVTNRDIPU1T2C4(800022),    --V8R13C00 PTN6900-M14 TNRDIPU1T2C4(SBOM), M14
               virent600DEVCR5DIPU1T2CA(800023),    --V8R13C00 NE40E-X2-M14 CR5DIPU1T2CA(SBOM), M14
               virent600DEVCR5D0IPU2TC3(800024),    --V8R13C00 NE40E-X2-M14 CR5D0IPU2TC3(SBOM), M14
               virent600DEVCR5DIPU1T2C1(800025),    --V8R13C00 NE40E-X2-M14 CR5DIPU1T2C1(SBOM), M14
               --R12C00 CR58LPUF1TM
               virent8090DEVCR9D00EPYF8P(688360),    -- V800R012C00 for CR9D00EPYF8P(SBOM) 60-Port 25GE-SFP28/10GE-SFP+ LAN/WAN MACSec Integrated Line Process Unit CM(LPUI-1T5-CM)
	       --END
               --X8CX16C
               virent8090DEVCR5D0MPUB872(676941),    -- V800R012C00 for CR5D0MPUB872(SBOM) Main Processing Unit B8C
               virent8090DEVCR5DSFUIT074(676943),    -- V800R012C00 for CR5DSFUIT074(SBOM) 1Tbps Switch Fabric Unit E1(SFUI-1TC-E)
               virent8090DEVCR5D0SRUAG71(676942),    -- V800R012C00 for CR5D0SRUAG71(SBOM) Switch and Route Processing Unit A15C
               virent8090DEVCR5DSFUIT075(676944),    -- V800R012C00 for CR5DSFUIT075(SBOM) 1Tbps Switch Fabric Unit F1(SFUI-1TC-F)
               virent8090DEVCR5D0EKGFC70(676945),    -- V800R012C00 for CR5D0EKGFC70(SBOM) 40-Port 100/1000Base-X-SFP Integrated Line Processing Unit (LPUI-52C)
               virent8090DEVCR5D0EKXFC70(676946),    -- V800R012C00 for CR5D0EKXFC70(SBOM) 40-Port 10GBase LAN/WAN-SFP+ Integrated Line Processing Unit (LPUI-402C)
               virent8090DEVCR5DLPUFT073(676947),    -- V800R012C00 for CR5DLPUFT073(SBOM) Flexible Card Line Processing Unit (LPUF-1T1C)
               --END
               --SIG9800 X8AX16A
               virent8090DEVIG2D0MPUB902(567843),    -- V800R012C10 for IG2D0MPUB902(SBOM) Main Processing Unit B9A(32G Memory)
               virent8090DEVIG2DSFUIT202(567844),    -- V800R012C10 for IG2DSFUIT202(SBOM) 2Tbps Switch Fabric Unit E1(SFUI-2TA-E)
               virent8090DEVIG2D0SRUAD02(567845),    -- V800R012C10 for IG2D0SRUAD02(SBOM) Switch and Route Processing Unit A13A(32G Memory)
               virent8090DEVIG2DSFUIT212(567846),    -- V800R012C10 for IG2DSFUIT212(SBOM) 2Tbps Switch Fabric Unit F1(SFUI-2TA-F)
               virent8090DEVIG2DLPUFM302(567847),    -- V800R012C10 for IG2DLPUFM302(SBOM) Flexible Card Line Processing Unit(LPUF-483A)
               virent8090DEVIG2DLPUFT002(567848),    -- V800R012C10 for IG2DLPUFT002(SBOM) Flexible Card Line Processing Unit(LPUF-1T2A)
               virent8090DEVIG2D00EENB02(567849),    -- V800R012C10 for IG2D00EENB02(SBOM) 20-Port 100GBase-QSFP28 Integrated Line Processing Unit (LPUI-2TA)
               virent8090DEVIG2D00SPUG02(567960),    -- V800R012C10 for IG2D00SPUG02(SBOM) High Performance X8A&X16A Service Processing Unit-SPUGA,with HW Service Inspection Gateway Software
               --END
               virent8090DEVCR5DLPUFM370(676948),    -- V800R012C10 for CR5DLPUFM370(SBOM) Flexible Card Line Processing Unit (LPUF-483)
               virent8090DEVCR5DLPUFF370(676949),    -- V800R012C10 for CR5DLPUFF370(SBOM) Flexible Card Line Processing Unit (LPUF-243)
               virent8090DEVCR5DLPUF5370(676950),    -- V800R012C10 for CR5DLPUF5370(SBOM) Flexible Card Line Processing Unit A(LPUF-53A)
               virent8090DEVCR5DLPUFM371(676961),    -- V800R012C10 for CR5DLPUFM371(SBOM) Flexible Card Line Processing Unit A(LPUF-483A)
               virent8090DEVCR5DLPUFF371(676962),    -- V800R012C10 for CR5DLPUFF371(SBOM) Flexible Card Line Processing Unit A(LPUF-243A)
               virent8090DEVCR5DLPUF5371(676963),    -- V800R012C10 for CR5DLPUF5371(SBOM) Flexible Card Line Processing Unit(LPUF-53)
               virent8090DEVCX6DISUFM310(676964),    -- V800R012C10 for CX6DISUFM310(SBOM) Flexible Card Line Processing Unit A(ISUF-483A)
               virent8090DEVCX6DISUFF310(676965),    -- V800R012C10 for CX6DISUFF310(SBOM) Flexible Card Line Processing Unit A(ISUF-243A)
               virent8090DEVCX6DISUF5310(676966),    -- V800R012C10 for CX6DISUF5310(SBOM) Flexible Card Line Processing Unit A(ISUF-53A)
               virent8090DEVCR5DLPUFF571(676967),    -- V800R012C10 for CR5DLPUFF571(SBOM) Flexible Card Line Processing Unit E(LPUF-245A-E)
               virent8090DEVCR5DLPUFM571(676968),    -- V800R012C10 for CR5DLPUFM571(SBOM) Flexible Card Line Processing Unit E(LPUF-485A-E)
			   virent8090DEVCX6DISUFM311(178864),    -- V8R21C10 for CX6DISUFM311(SBOM) Flexible Card Line Processing Unit(ISUF-483B)
               virent8090DEVCR5D0SRUAE71(567821),    --V800R012C00 for CR5D0SRUAE71(SBOM) Switch and Route Processing Unit A14A(32G Memory)
               virent8090DEVME0D0SRUAD71(567823),    --V800R012C00 for ME0D0SRUAD71(SBOM) Switch and Route Processing Unit A15(32G Memory)
               virent8090DEVCR5DSFUIT27M(567828),    --V800R012C00 for CR5DSFUIT27M(SBOM) 2Tbps Switch Fabric Unit H(SFUI-2T-H)
               virent8090DEVCR5DSFUIT27N(567829),    --V800R012C00 for CR5DSFUIT27N(SBOM) 2Tbps Switch Fabric Unit H(SFUI-2TA-H)
               virent8090DEVCR5DSFUIT27K(567830),    --V800R012C00 for CR5DSFUIT27K(SBOM) 2Tbps Switch Fabric Unit G(SFUI-2T-G)
               virent8090DEVCR5DSFUIT27L(567831),    --V800R012C00 for CR5DSFUIT27L(SBOM) 2Tbps Switch Fabric Unit G(SFUI-2TA-G)
               virent8090DEVCX6DSFUIT27F(567832),    --V800R012C00 for CX6DSFUIT27F(SBOM) 2Tbps Switch Fabric Unit G(SFUI-2T-G)
               virent8090DEVCX6DSFUIU07G(567833),    --V800R012C00 for CX6DSFUIU07G(SBOM) 2Tbps Switch Fabric Unit H(SFUI-2T-H)
               virent8090DEVTNRDSFUIT27G(567834),    --V800R012C00 for TNRDSFUIT27G(SBOM) 2Tbps Switch Fabric Unit G(SFUI-2T-G)
               virent8090DEVTNRDSFUIU07H(567835),    --V800R012C00 for TNRDSFUIU07H(SBOM) 2Tbps Switch Fabric Unit H(SFUI-2T-H)
               virent8090DEVME0DSFUIT07E(567824),    --V800R012C00 for ME0DSFUIT07E(SBOM) 1Tbps Switch Fabric Unit E(SFUI-1T-E)
               virent8090DEVME0DSFUIT17E(567825),    --V800R012C00 for ME0DSFUIT17E(SBOM) 1Tbps Switch Fabric Unit E(SFUI-1TA-E)
               virent8090DEVME0DSFUIT07F(567826),    --V800R012C00 for ME0DSFUIT07F(SBOM) 1Tbps Switch Fabric Unit F(SFUI-1T-F)
               virent8090DEVME0DSFUIT17F(567827),    --V800R012C00 for ME0DSFUIT17F(SBOM) 1Tbps Switch Fabric Unit F(SFUI-1TA-F)
               virent8090DEVCR5DSFUIT076(567850),    --V800R012C00 for CR5DSFUIT076(SBOM) 1Tbps Switch Fabric Unit G(SFUI-1T-G)
               virent8090DEVCR5DSFUIT077(567851),    --V800R012C00 for CR5DSFUIT077(SBOM) 1Tbps Switch Fabric Unit G(SFUI-1TA-G)
               virent8090DEVCR5DSFUIT078(567852),    --V800R012C00 for CR5DSFUIT078(SBOM) 1Tbps Switch Fabric Unit H(SFUI-1T-H)
               virent8090DEVCR5DSFUIT079(567853),    --V800R012C00 for CR5DSFUIT079(SBOM) 1Tbps Switch Fabric Unit H(SFUI-1TA-H)
               virent8090DEVCX6DSFUIT072(567854),    --V800R012C00 for CX6DSFUIT072(SBOM) 1Tbps Switch Fabric Unit G(SFUI-1T-G)
               virent8090DEVCX6DSFUIT073(567855),    --V800R012C00 for CX6DSFUIT073(SBOM) 1Tbps Switch Fabric Unit H(SFUI-1T-H)
               virent8090DEVTNRDSFUIT072(567856),    --V800R012C00 for TNRDSFUIT072(SBOM) 1Tbps Switch Fabric Unit G(SFUI-1T-G)
               virent8090DEVTNRDSFUIT073(567857),    --V800R012C00 for TNRDSFUIT073(SBOM) 1Tbps Switch Fabric Unit H(SFUI-1T-H)
               virent8090DEVCX6DSFUIT27J(567858),    --V800R012C00 for CX6DSFUIT27J(SBOM) Switch Fabric Unit G(SFUI-1T-G)
               virent8090DEVCX6DSFUIT21H(567859),    --V800R012C00 for CX6DSFUIT21H(SBOM) Switch Fabric Unit H(SFUI-1T-H)
               virent8090DEVCR5D0SRUAC76(567860),    --V800R012C00 for CR5D0SRUAC76(SBOM) Switch and Route Processing Unit A162
               virent8090DEVCR9P9KHALM8B(567836),    --V800R012C00 for CR9P9KHALM8B(SBOM) 20-Port 100GE-QSFP28 Integrated Line Process Unit(LPUI-2TA)
               virent8090DEVCR5DSFUIM17E(567870),    -- V8R12C10 for CR5DSFUIM17E(SBOM) 480Gbps Switch Fabric Unit E(SFUI-480A-E)
               virent8090DEVCR5DSFUIM07E(567871),    -- V8R12C10 for CR5DSFUIM07E(SBOM) 480bps Switch Fabric Unit E(SFUI-480-E)
               virent8090DEVCR5DSFUIM17F(567872),    -- V8R12C10 for CR5DSFUIM17F(SBOM) 480Gbps Switch Fabric Unit F(SFUI-480-F)
               virent8090DEVCR5D0SRUAB71(567873),    -- V8R12C10 for CR5D0SRUAB71(SBOM) Switch and Route Processing Unit A11
               virent8090DEVCR5DSFUIM07F(567874),    -- V8R12C10 for CR5DSFUIM07F(SBOM) 480Gbps Switch Fabric Unit F(SFUI-480A-F)
               virent8090DEVCR5D0SRUAB70(567875),    -- V8R12C10 for CR5D0SRUAB70(SBOM) Switch and Route Processing Unit A11A
               --BEGIN for V8R12C10 X8AK
               virent8090DEVCR5D0SRUADK1(567837),    -- V8R12C10 for CR5D0SRUADK1(SBOM) Switch and Route Processing Unit A13-K(32G Memory)
               virent8090DEVCR5DSFUIT2KN(567838),    -- V8R12C10 for CR5DSFUIT2KN(SBOM) 2Tbps Switch Fabric Unit H(SFUI-2T-HK)
               virent8090DEVCR5DLPUFF3K1(567839),    -- V8R12C10 for CR5DLPUFF3K1(SBOM) Flexible Card Line Processing Unit CM(LPUF-243-K)
               virent8090DEVCR5DLPUF53K0(567840),    -- V8R12C10 for CR5DLPUF53K0(SBOM) Flexible Card Line Processing Unit(LPUF-53-K)
               virent8090DEVCR5D00EENBK3(567841),    -- V8R12C10 for CR5D00EENBK3(SBOM) 20-Port 100GBase-QSFP28 Integrated Line Processing Unit (LPUI-2T-K)
               virent8090DEVCR5DVSUFK0K2(567842),    -- V8R12C10 for CR5DVSUFK0K2(SBOM) Integrated Service Unit 400A(VSUI-400-K)
               --END
               virent8090DEVCR5DEDVE8N71(567876),    -- V8R12C10 for CR5DEDVE8N71(SBOM) 16-Port 50G/8-Port 100GBase-QSFP28 FlexE/MACsec Integrated Line Processing Unit L(LPUI-1T2-L)
               virent8090DEVCR9D00EENB84(567877),    -- V8R12C10 for CR9D00EENB84(SBOM) 20-Port 100GE-QSFP28 FlexE/MACSec Integrated Line Process Unit L(LPUI-2T-L)
               virent8090DEVCR5D0MPUBA70(567878),    -- V8R12C10 for CR5D0MPUBA70(SBOM) Main Processing Unit B10(32G Memory)
               virent8090DEVCR5D0MPUBA71(567879),    -- V8R12C10 for CR5D0MPUBA71(SBOM) Main Processing Unit B10A(32G Memory)
               virent8090DEVCR5D0SRUAB72(567880),    -- V8R12C10 for CR5D0SRUAB72(SBOM) Switch and Route Processing Unit A17
               virent8090DEVCR5D0SRUAB74(567881),    -- V8R12C10 for CR5D0SRUAB74(SBOM) Switch and Route Processing Unit A17A
               --BEGIN for V8R12C10 LS
               virent8090DEVCR9D0MPUR180-VMPU(570077),   -- v8r12c10 VMPU In NE9000-8 Main Processing Unit R1(MPUR1)
               virent8090DEVCR9D0MPUQ180-VMPU(570078),   -- v8r12c10 VMPU In NE9000-20 Main Processing Unit Q1(MPUQ1)
               --END
               --BEGIN for V8R13C00 NE8000X4X8
               virent8090DEVCR8DSFU14TCA(567882),    -- V8R13C00 for CR8DSFU14TCA(SBOM) NetEngine 8000 X4 14.4Tbps Switch Fabric Unit(SFUI-14T4-B)
               virent8090DEVCR8DSFU14TCB(567883),    -- V8R13C00 for CR8DSFU14TCB(SBOM) NetEngine 8000 X4 14.4Tbps Switch Fabric Unit(SFUIA-14T4-B)
               virent8090DEVCR8DSFU14TC8(567884),    -- V8R13C00 for CR8DSFU14TC8(SBOM) NetEngine 8000 X8 14.4Tbps Switch Fabric Unit(SFUI-14T4-A)
               virent8090DEVCR8DSFU14TC9(567885),    -- V8R13C00 for CR8DSFU14TC9(SBOM) NetEngine 8000 X8 14.4Tbps Switch Fabric Unit(SFUIA-14T4-A)
               --END
               --BEGIN: R12C10 CR58LPU4TB
               virent8090DEVCR9D00EKNB8T(567887),    -- V800R012C10 for CR9D00EKNB8T(SBOM) 40-Port 100GE/50GE-QSFP28 Integrated Line Process Unit CM(LPUI-4T-CM)
               virent8090DEVCR9D00EKNB8R(567888),    -- V800R012C10 for CR9D00EKNB8R(SBOM) 40-Port 100GE/50GE-QSFP28 Integrated Line Process Unit L(LPUI-4T-L)
               virent8090DEVCR9D00EKNB81(567889),    -- V800R012C10 for CR9D00EKNB81(SBOM) 40-Port 100GE/50GE-QSFP28 Integrated Line Process Unit(LPUI-4TA)
               virent8090DEVCR9DE8KE8N8U(567894),    -- V800R012C10 for CR9DE8KE8N8U(SBOM) 8-Port 400GE-QSFP-DD + 8-Port 100GE-QSFP28 Integrated Line Process Unit CM(LPUI-4T-CM)
               virent8090DEVCR9DE8KE8N8T(567891),    -- V800R012C10 for CR9DE8KE8N8T(SBOM) 8-Port 400GE-QSFP-DD + 8-Port 100GE-QSFP28 Integrated Line Process Unit(LPUI-4TA)
               virent8090DEVCR9D00EKNB8Q(567892),    -- V800R012C10 for CR9D00EKNB8Q(SBOM) 40-Port 100GE/50GE-QSFP28 Integrated Line Process Unit CM(LPUI-4T-CM)
               virent8090DEVCR9DE8KE8N8S(567893),    -- V800R012C10 for CR9DE8KE8N8S(SBOM) 8-Port 400GE-QSFP-DD + 8-Port 100GE-QSFP28 Integrated Line Process Unit CM(LPUI-4T-CM)
               --END
               --BEGIN: R13C00
               virent8090DEVCR5DSFUIT07C(688532),    -- V8R13C00 for CR5DSFUIT07C(SBOM) 1Tbps Switch Fabric Unit M(SFUI-1TA-M)
               virent8090DEVCR5DSFUIT07D(688533),    -- V8R13C00 for CR5DSFUIT07D(SBOM) 1Tbps Switch Fabric Unit M(SFUI-1T-M)
               virent8090DEVCR5DSFUIT07F(688534),    -- V8R13C00 for CR5DSFUIT07F(SBOM) 1Tbps Switch Fabric Unit N(SFUI-1TA-N)
               virent8090DEVCR5DSFUIT07G(688535),    -- V8R13C00 for CR5DSFUIT07G(SBOM) 1Tbps Switch Fabric Unit N(SFUI-1T-N)
               virent8090DEVCR5DSFUIM07I(688536),    -- V8R13C00 for CR5DSFUIM07I(SBOM) 480Gbps Switch Fabric Unit N(SFUI-480A-N)
               virent8090DEVCR5DSFUIM07J(688537),    -- V8R13C00 for CR5DSFUIM07J(SBOM) 480Gbps Switch Fabric Unit N(SFUI-480-N)
               virent8090DEVCX6DSFUIT074(688538),    -- V8R13C00 for CX6DSFUIT074(SBOM) 1Tbps Switch Fabric Unit M(SFUI-1T-M)
               virent8090DEVCX6DSFUIT075(688539),    -- V8R13C00 for CX6DSFUIT075(SBOM) 1Tbps Switch Fabric Unit N(SFUI-1T-N)
               virent8090DEVCX6DSFUIM07E(688540),    -- V8R13C00 for CX6DSFUIM07E(SBOM) 480Gbps Switch Fabric Unit N(SFUI-480-N)
               virent8090DEVCX6DSFUIT076(688541),    -- V8R13C00 for CX6DSFUIT076(SBOM) 1Tbps Switch Fabric Unit M(SFUI-1T-M)
               virent8090DEVCX6DSFUIT017(688542),    -- V8R13C00 for CX6DSFUIT017(SBOM) 1Tbps Switch Fabric Unit N(SFUI-1T-N)
               virent8090DEVCX6DSFUIM01E(688543),    -- V8R13C00 for CX6DSFUIM01E(SBOM) 480Gbps Switch Fabric Unit N(SFUI-480-N)
               virent8090DEVTNRDSFUIT074(688544),    -- V8R13C00 for TNRDSFUIT074(SBOM) 1Tbps Switch Fabric Unit M(SFUI-1T-M)
               virent8090DEVTNRDSFUIT077(688545),    -- V8R13C00 for TNRDSFUIT077(SBOM) 1Tbps Switch Fabric Unit N(SFUI-1T-N)
               virent8090DEVTNRDSFUIM07E(688546),    -- V8R13C00 for TNRDSFUIM07E(SBOM) 480Gbps Switch Fabric Unit N(SFUI-480-N)
               virent8090DEVME0DSFUIT07K(688547),    -- V8R13C00 for ME0DSFUIT07K(SBOM) 1Tbps Switch Fabric Unit M(SFUI-1TA-M)
               virent8090DEVME0DSFUIT07L(688548),    -- V8R13C00 for ME0DSFUIT07L(SBOM) 1Tbps Switch Fabric Unit M(SFUI-1T-M)
               virent8090DEVME0DSFUIT07I(688549),    -- V8R13C00 for ME0DSFUIT07I(SBOM) 1Tbps Switch Fabric Unit N(SFUI-1TA-N)
               virent8090DEVME0DSFUIT07J(688550),    -- V8R13C00 for ME0DSFUIT07J(SBOM) 1Tbps Switch Fabric Unit N(SFUI-1T-N)
               virent8090DEVME0DSFUIM07I(688551),    -- V8R13C00 for ME0DSFUIM07I(SBOM) 480Gbps Switch Fabric Unit N(SFUI-480A-N)
               virent8090DEVME0DSFUIM07J(688552),    -- V8R13C00 for ME0DSFUIM07J(SBOM) 480Gbps Switch Fabric Unit N(SFUI-480-N)
               virent8090DEVCR8D00LRXFC3(688553),    -- V8R13C00 for CR8D00LRXFC3(SBOM) 72-Port 10GE-SFP+ Integrated Line Processing Unit(LPUI-1TA-E-CM)
               virent8090DEVCR8D00EENBC8(688554),    -- V8R13C00 for CR8D00EENBC8(SBOM) 20-Port 100GBase-QSFP28 Integrated Line Processing Unit CM(LPUI-2TA-CM)
               virent8090DEVCR8D00LRXFC4(688555),    -- V8R13C00 for CR8D00LRXFC4(SBOM) 72-Port 10GE-SFP+ Integrated Line Processing Unit(LPUI-1TA-CM)
               virent8090DEVCR8D0MPUA3C4(688556),    -- V8R13C00 for CR8D0MPUA3C4(SBOM) NetEngine 8000E Main Processing Unit A3A(MPUA3A)
               virent8090DEVCR8D0MPUA5C5(688557),    -- V8R13C00 for CR8D0MPUA5C5(SBOM) NetEngine 8100 Main Processing Unit A5A(MPUA5A)
               --END
               virent8090DEVCR5DLPUFM07C(564946),    -- CR5DLPUFM07C Flexible Card Line Processing Unit(LPUF-480)
               virent8090DEVCX6DISUFM11C(564947),    -- CX6DISUFM11C Flexible Card Line Processing Unit(ISUF-480)
               virent8090DEVME0DMSUFM073(564948),    -- ME0DMSUFM073 Flexible Card Multi Service Unit(MSUF-480,2 sub-slots)
               virent8090DEVME0DBSUFM074(564949),    -- ME0DBSUFM074 Flexible Card Broadband Service Unit(BSUF-480,2 sub-slots)
               virent8090DEVCR5D0EEXFF70(564950),    -- CR5D0EEXFF70 20-Port 10Gase LAN/WAN-SFP+ FlexE Integrated Line Processing Unit CM(LPUI-242-CM)
               virent8090DEVCR5D0E2NBF70(564951),    -- CR5D0E2NBF70 2-Port 100GBase-QSFP28 FlexE Integrated Line Processing Unit CM(LPUI-242-CM)
               virent8090DEVCR5D0EEXFF71(564952),    -- CR5D0EEXFF71 20-Port 10Gase LAN/WAN-SFP+ FlexE Integrated Line Processing Unit(LPUI-242A)
               virent8090DEVCR5D0E2NBF71(564953),    -- CR5D0E2NBF71 2-Port 100GBase-QSFP28 FlexE Integrated Line Processing Unit(LPUI-242A)
               virent8090DEVCX6D0EEXFF11(564954),    -- CX6D0EEXFF11 20-Port 10Gase LAN/WAN-SFP+ FlexE Integrated Line Processing Unit(ISUI-242A)
               virent8090DEVCX6D0E2NBF12(564955),    -- CX6D0E2NBF12 2-Port 100GBase-QSFP28 FlexE Integrated Line Processing Unit(ISUI-242A)
               virent8090DEVCR5DVSUIK074(676969),    -- V8R12C11 for CR5DVSUIK074(SBOM) Integrated Service Unit 400(VSUI-400-S)
               virent8090DEVCR5DVSUIK075(676970),    -- V8R12C11 for CR5DVSUIK075(SBOM) Integrated Service Unit 400(VSUI-400A-S)
               virent8090DEVCR5DJYSUK073(676971),    -- V8R12C11 for CR5DJYSUK073(SBOM) Public Security Service Unit(PSSU-S)
               virent8090DEVME0DVSUIK074(676972),    -- V8R12C11 for ME0DVSUIK074(SBOM) Integrated Service Unit 400(VSUI-400-S)
               virent8090DEVME0DVSUIK075(676973),    -- V8R12C11 for ME0DVSUIK075(SBOM) Integrated Service Unit 400(VSUI-400A-S)
               virent8090DEVME0DJYSUK071(676974),    -- V8R12C11 for ME0DJYSUK071(SBOM) Public Security Service Unit(PSSU-S)
               virent8090DEVCR9DLPUIT080(676975),     -- V8R13C00 for CR9DLPUIT080(SBOM) 60-Port 10GBase LAN/WAN-SFP+ MACSec Integrated Line Process Unit (LPUI-1TA)
               virent8090DEVCR5D0MPUB972(688520),    -- V8R12C11 for CR5D0MPUB972(SBOM) Main Processing Unit B91(32G Memory)
               virent8090DEVCR5DSFUIT27P(688521),    -- V8R12C11 for CR5DSFUIT27P(SBOM) 2Tbps Switch Fabric Unit I(SFUI-2T-I)
               virent8090DEVCR5DSRUA9171(688522),    -- V8R12C11 for CR5DSRUA9171(SBOM) Switch and Route Processing Unit A131(16G Memory)
               virent8090DEVCR5DSFUITD71(688523),    -- V8R12C11 for CR5DSFUITD71(SBOM) 2Tbps Switch Fabric Unit J(SFUI-2T-J)
               virent8090DEVCX6D0MPUB972(688524),    -- V8R12C11 for CX6D0MPUB972(SBOM) Main Processing Unit B91(32G Memory)
               virent8090DEVCX6DSFUIT27P(688525),    -- V8R12C11 for CX6DSFUIT27P(SBOM) 2Tbps Switch Fabric Unit I(SFUI-2T-I)
               virent8090DEVCX6DSRUA9171(688526),    -- V8R12C11 for CX6DSRUA9171(SBOM) Switch and Route Processing Unit A131(16G Memory)
               virent8090DEVCX6DSFUITD71(688527),    -- V8R12C11 for CX6DSFUITD71(SBOM) 2Tbps Switch Fabric Unit J(SFUI-2T-J)
               virent8090DEVTNRD0MPUB972(688528),    -- V8R12C11 for TNRD0MPUB972(SBOM) Main Processing Unit B91(32G Memory)
               virent8090DEVTNRDSFUIT27P(688529),    -- V8R12C11 for TNRDSFUIT27P(SBOM) 2Tbps Switch Fabric Unit I(SFUI-2T-I)
               virent8090DEVTNRDSRUA9171(688530),    -- V8R12C11 for TNRDSRUA9171(SBOM) Switch and Route Processing Unit A131(16G Memory)
               virent8090DEVTNRDSFUITD71(688531),    -- V8R12C11 for TNRDSFUITD71(SBOM) 2Tbps Switch Fabric Unit J(SFUI-2T-J)
               virent8090DEVCR8DSFUI4TC4(688424),    -- V8R12C11 for CR8DSFUI4TC4(SBOM) NetEngine 8000 X4 4Tbps Switch Fabric Unit(SFUI-4T-C)
               virent8090DEVCR8DSFUI4TC5(688425),    -- V8R12C11 for CR8DSFUI4TC5(SBOM) NetEngine 8000 X4 4Tbps Switch Fabric Unit(SFUIA-4T-C)
               virent8090DEVCR8DSFUI4TC6(688426),    -- V8R12C11 for CR8DSFUI4TC6(SBOM) NetEngine 8000 X8 4Tbps Switch Fabric Unit(SFUI-4T-D)
               virent8090DEVCR8DSFUI4TC7(688427),    -- V8R12C11 for CR8DSFUI4TC7(SBOM) NetEngine 8000 X8 4Tbps Switch Fabric Unit(SFUIA-4T-D)
               virent8090DEVCR8D00LRXFCS(688372),    -- V8R12C11 for CR8D00LRXFCS(SBOM) 72-Port 25GE(SFP28)/10GE(SFP+)/GE(SFP) Integrated Line Processing Unit L(LPUIA-2T-L)
               virent8090DEVCR8D00EENBC6(688428),    -- V8R12C11 for CR8D00EENBC6(SBOM) 20-Port 100GBase-QSFP28 Integrated Line Processing Unit CM(LPUI-2TA-CM)
               virent8090DEVCR5D0MPUB873(688566),    -- V8R13C00 for CR5D0MPUB873(SBOM) Main Processing Unit B81A
               virent8090DEVCR5D0MPUB874(688567),    -- V8R13C00 for CR5D0MPUB874(SBOM) Main Processing Unit B81
               virent8090DEVCX6D0MPUB872(688568),    -- V8R13C00 for CX6D0MPUB872(SBOM) Main Processing Unit B81
               virent8090DEVCX6D0MPUB811(688569),    -- V8R13C00 for CX6D0MPUB811(SBOM) Main Processing Unit B81A
               virent8090DEVTNRD0MPUB872(688570),    -- V8R13C00 for TNRD0MPUB872(SBOM) Main Processing Unit B81
               virent8090DEVCR9D00EENB85(688571),    -- V8R12C11 for CR9D00EENB85(SBOM) 20-Port 100GE/50GE-QSFP28 Integrated Line Process Unit CM(LPUI-2T-CM)
               virent8090DEVCR9D00EKNB85(688572),    -- V8R12C11 for CR9D00EKNB85(SBOM) 20-Port 100GE/50GE-QSFP28 Integrated Line Process Unit L(LPUI-2T-L)
               virent8090DEVCR9P9KHALM8D(688573),    -- V8R12C11 for CR9P9KHALM8D(SBOM) 20-Port 100GE/50GE-QSFP28 Integrated Line Process Unit (LPUI-2TA)
               virent8090DEVCR5DSFUIM07G(688574),    -- V8R13C00 for CR5DSFUIM07G(SBOM) 480Gbps Switch Fabric Unit M(SFUI-480A-M)
               virent8090DEVCR5DSFUIM07H(688575),    -- V8R13C00 for CR5DSFUIM07H(SBOM) 480Gbps Switch Fabric Unit M(SFUI-480-M)
               virent8090DEVME0DSFUIM07G(688576),    -- V8R13C00 for ME0DSFUIM07G(SBOM) 480Gbps Switch Fabric Unit M(SFUI-480A-M)
               virent8090DEVME0DSFUIM07H(688577),    -- V8R13C00 for ME0DSFUIM07H(SBOM) 480Gbps Switch Fabric Unit M(SFUI-480-M)
               virent8090DEVCR5DNPU48071(677910),     -- V8R13C00 for CR5DNPU48071(SBOM) Network Processing Unit(NPU-480-B)
               virent8090DEVCR5DNPU1TM72(677911),     -- V8R13C00 for CR5DNPU1TM72(SBOM) Network Processing Unit (NPU-1T-B)
               virent8090DEVCR8D00EENBCE(688669),    -- V8R21C00 for CR8D00EENBCE(SBOM) 20-Port 100GBase-QSFP28 MACsec Integrated Line Processing Unit CM(LPUI-2TA-CM)
               virent8090DEVCR8D00EENBCF(688670),    -- V8R21C00 for CR8D00EENBCF(SBOM) 20-Port 100GBase-QSFP28 MACsec Integrated Line Processing Unit CM(LPUI-2T-CM)
               virent8090DEVCR8D00EENBCB(688671),    -- V8R21C00 for CR8D00EENBCB(SBOM) 20-Port 100GBase-QSFP28 MACsec Integrated Line Processing Unit L CM(LPUI-2TA-L-CM)
               virent8090DEVCR8D00EENBCG(688672),    -- V8R21C00 for CR8D00EENBCG(SBOM) 20-Port 100GBase-QSFP28 MACsec Integrated Line Processing Unit L CM(LPUI-2T-L-CM)
               virent8090DEVCR8D00EENBC7(688578),    -- V8R13C00 for CR8D00EENBC7(SBOM) 20-Port 100GBase-QSFP28 Integrated Line Processing Unit CM(LPUI-2T-CM)
               virent8090DEVCR8D00EENBCD(688579),    -- V8R13C00 for CR8D00EENBCD(SBOM) 20-Port 100GBase-QSFP28 Integrated Line Processing Unit CM(LPUI-2TA-CM)
               virent8090DEVCR8D00EENBC9(688580),    -- V8R13C00 for CR8D00EENBC9(SBOM) 20-Port 100GBase-QSFP28 Integrated Line Processing Unit L CM(LPUI-2T-L-CM)
               virent8090DEVCR8D00EENBCA(688581),    -- V8R13C00 for CR8D00EENBCA(SBOM) 20-Port 100GBase-QSFP28 Integrated Line Processing Unit L CM(LPUI-2TA-L-CM)
               virent8090DEVCR8D00EKNBC6(688582),    -- V8R13C00 for CR8D00EKNBC6(SBOM) 40-Port 100GBase-QSFP28 Integrated Line Processing Unit CM(LPUI-4T-CM)
               virent8090DEVCR8D00EKNBC7(688583),    -- V8R13C00 for CR8D00EKNBC7(SBOM) 40-Port 100GBase-QSFP28 Integrated Line Processing Unit CM(LPUI-4TA-CM)
               virent8090DEVCR8D00EKNBC8(688584),    -- V8R13C00 for CR8D00EKNBC8(SBOM) 40-Port 100GBase-QSFP28 Integrated Line Processing Unit L CM(LPUI-4T-L-CM)
               virent8090DEVCR8D00EKNBC9(688585),    -- V8R13C00 for CR8D00EKNBC9(SBOM) 40-Port 100GBase-QSFP28 Integrated Line Processing Unit L CM(LPUI-4TA-L-CM)
               virent8090DEVCR5DLPUFM372(686950),    -- V8R13C00 for CR5DLPUFM372(SBOM) Flexible Card Line Processing Unit(LPUF-483)
               virent8090DEVCR5DLPUFM374(686951),    -- V8R13C00 for CR5DLPUFM374(SBOM) Flexible Card Line Processing Unit (LPUF-483A)
               virent8090DEVCR5DLPUFM373(686952),    -- V8R13C00 for CR5DLPUFM373(SBOM) Flexible Card Line Processing Unit(LPUF-483-CM)
               virent8090DEVCR5DLPUFF375(686953),    -- V8R13C00 for CR5DLPUFF375(SBOM) Flexible Card Line Processing Unit (LPUF-243)
               virent8090DEVCR5DLPUFF374(686954),    -- V8R13C00 for CR5DLPUFF374(SBOM) Flexible Card Line Processing Unit (LPUF-243A)
               virent8090DEVCR5DLPUF5373(686955),    -- V8R13C00 for CR5DLPUF5373(SBOM) Flexible Card Line Processing Unit (LPUF-53)
               virent8090DEVCR5DLPUF5372(686956),    -- V8R13C00 for CR5DLPUF5372(SBOM) Flexible Card Line Processing Unit (LPUF-53A)
               virent8090DEVCR5DLPUFT078(686957),    -- V8R13C00 for CR5DLPUFT078(SBOM) Flexible Card Line Processing Unit (LPUF-1T2)
               virent8090DEVCR5DLPUFT079(686958),    -- V8R13C00 for CR5DLPUFT079(SBOM) Flexible Card Line Processing Unit (LPUF-1T2A)
               virent8090DEVME0DMSUFT076(686959),    -- V8R13C00 for ME0DMSUFT076(SBOM) Flexible Card Broadband Service Unit(BSUF-1T2,2 sub-slots)
               virent8090DEVME0DMSUFT077(686960),    -- V8R13C00 for ME0DMSUFT077(SBOM) Flexible Card Broadband Service Unit(BSUF-1T2A,2 sub-slots)
               virent8090DEVIG2DLPUFM305(686961),    -- V8R13C00 for IG2DLPUFM305(SBOM) Flexible Card Line Processing Unit (LPUF-483A)
               virent8090DEVIG2DLPUFT005(686963),    -- V8R13C00 for IG2DLPUFT005(SBOM) Flexible Card Line Processing Unit (LPUF-1T2A)
               virent8090DEVCR5D00E8NB7R(686964),    -- V8R13C00 for CR5D00E8NB7R(SBOM) 16-Port 50G/8-Port 100GBase-QSFP28 FlexE/MACsec Integrated Line Processing Unit CM(LPUI-1T2-CM)
               virent8090DEVCR5D00E8NB7S(686965),    -- V8R13C00 for CR5D00E8NB7S(SBOM) 16-Port 50G/8-Port 100GBase-QSFP28 FlexE/MACsec Integrated Line Processing Unit CM(LPUI-1T2A-CM)	688437		 
               virent8090DEVCR2DNSPC1010(688612),    -- V8R13C00 for CR2DNSPC1010(SBOM) Network Processing Unit (NSP-C1)
               virent600DEVTNRDIPU1T2C5(688613),     -- V8R13C00 for TNRDIPU1T2C5(SBOM)Integrated Network Processing Unit (IPU-1T2-BN)
               virent8090DEVIG2D00SPUG06(688614),    -- V8R13C00 for IG2D00SPUG06(SBOM)High Performance X8A&X16A Enhanced Service Processing Unit-SPUGEA,with HW Service Inspection Gateway Software
               virent8090DEVCR8DIPU480C6(800009),    --V8R21C00 CR8DIPU480C6(SBOM) Integrated Network Processing Unit (IPUA-480-B)
               virent8090DEVCR8DIPU1T2CD(800010),    --V8R21C00 CR8DIPU1T2CD(SBOM) Integrated Network Processing Unit (IPUA-1T2-BN)
               virent8090DEVCR8DIPU1T212(800101),    --V8R21C00 CR8DIPU1T212(SBOM) Integrated Network Processing Unit (IPUA-1T2)
               virent8090DEVCR8DIPU1T211(800102),    --V8R21C00 CR8DIPU1T211(SBOM) Integrated Network Processing Unit (IPUA-1T2)
               virent8090DEVCR8DMPUF8AZ1(800103),    -- V8R22C00 CR8DMPUF8AZ1(SBOM) NetEngine 8000E F Main Processing Unit B1Z(MPUB1Z)
               virent8090DEVCR8DMPUF8AC1(800104),    -- V8R22C00 CR8DMPUF8AC1(SBOM) NetEngine 8000E F Main Processing Unit B1A(MPUB1A)
               virent8090DEVCR8DMPUF8AC0(800105),    -- V8R22C00 CR8DMPUF8AC0(SBOM) NetEngine 8000 F Main Processing Unit B1(MPUB1)
               virent8090DEVCR8DSFUIK0C1(800106),    -- V8R22C00 CR8DSFUIK0C1(SBOM) NetEngine 8000E F 2T Switch Routing Unit(SRUA-2T-A)
               virent8090DEVCR8DSFUIK0C0(800107),    -- V8R22C00 CR8DSFUIK0C0(SBOM) NetEngine 8000 F 2T Switch Routing Unit(SRU-2T-A)
               virent8090DEVCR8D0SFUT6D0(800108),    -- V8R23C00 CR8D0SFUT6D0(SBOM) NetEngine 8000 F 6T4 Switch Routing Unit(SRU-6T4-A)
               --BEGIN for V8R21C00 3.2T_sfu 
               virent8090DEVCR5DSFUIT350(562183),    -- V8R21C00 for CR5DSFUIT350(SBOM) NE5000E CCC-A 3.2T Cluster Central Switch Fabric Unit (SFUI-3T2-C)
               virent8090DEVCR5DSFUIT361(562184),    -- V8R21C00 for CR5DSFUIT361(SBOM) NE5000E-20 3.2T CLC Integrated Switch Fabric Unit for Multi-Chassis (SFUI-3T2-M)
               virent8090DEVCR5DSFUIT360(562185),    -- V8R21C00 for CR5DSFUIT360(SBOM) NE5000E-20 3.2T CLC Switch Fabric Unit for Single Chassis(SFU-3T2-S)
               virent8090DEVCR5DLPUFT360(562186),    -- V8R21C00 for CR5DLPUFT360(SBOM) 3.2T Flexible Card Line Processing Unit CM(NE5000E LPUF-3T2-CM,2 sub-slots)
			   virent8090DEVCR5DSFUIT26J(562187),    -- V8R21C00 for CR5DSFUIT26J(SBOM) NE5000E-20 1.6T CLC Integrated Switch Fabric Unit for Multi-Chassis (SFUI-1T6-M)
               -- END

               virent8090DEVCR5D00EDNB66(562120),    -- V8R22C00 for CR5D00EDNB66(SBOM) 16-Port 100GBase QSFP28 Integrated Line Process Unit C(NE5000E LPUI-1T6-C)
               virent8090DEVCR5D00EDNB67(562121),    -- V8R22C00 for CR5D00EDNB67(SBOM) 16-Port 100GBase QSFP28 Integrated Line Process Unit C CM(NE5000E LPUI-1T6-C-CM)(4 ports enable)
               virent8090DEVCR5D00LRXF63(562122),    -- V8R22C00 for CR5D00LRXF63(SBOM) 72-Port 10GBase LAN/WAN-SFP+ Integrated Line Process Unit C(NE5000E LPUI-1T6-C)
               virent8090DEVCR5D00LRXF64(562123),    -- V8R22C00 for CR5D00LRXF64(SBOM) 72-Port 10GBase LAN/WAN-SFP+ Integrated Line Process Unit C CM(NE5000E LPUI-1T6-C-CM)(24 ports enable) 

               virent8090DEVCR5DSFUIT351(562188),    -- V8R21C10 for CR5DSFUIT351(SBOM) NE5000E CCC-A 3.2T Cluster Central Switch Fabric Unit (SFUI-3T2-C2)
               virent8090DEVCR5DSFUIT365(562189),    -- V8R21C10 for CR5DSFUIT365(SBOM) NE5000E-20 3.2T CLC Integrated Switch Fabric Unit for Multi-Chassis (SFUI-3T2-M2)
               virent8090DEVCR5DSFUIT364(562190),    -- V8R21C10 for CR5DSFUIT364(SBOM) NE5000E-20 3.2T CLC Switch Fabric Unit for Single Chassis (SFU-3T2-S2)

                virent8090DEVCR5D5KBASN61(562124),    -- V8R22C00 for CR5D5KBASN61(SBOM) NetEngine5000E 8-Port 400GBase QSFP-DD Integrated Line Process Unit(NE5000E LPUI-3T2)
                virent8090DEVCR5D5KBASN62(562125),    -- V8R22C00 for CR5D5KBASN62(SBOM) NetEngine5000E 32-Port 100GBase QSFP28 Integrated Line Process Unit(NE5000E LPUI-3T2)
                virent8090DEVCR5D5KHALN63(562126),    -- V8R22C00 for CR5D5KHALN63(SBOM) NetEngine5000E 8-Port 400GBase QSFP-DD Integrated Line Process Unit CM(NE5000E LPUI-3T2-CM) (Including 2*400GE Setup Port)
                virent8090DEVCR5D5KHALN64(562127),    -- V8R22C00 for CR5D5KHALN64(SBOM) NetEngine5000E 32-Port 100GBase QSFP28 Integrated Line Process Unit CM(NE5000E LPUI-3T2-CM) (Including 8*100GE Setup Port)
                
                --BEGIN for V8R23C00
                virent8090DEVCR5D00E8KB61(562132),    -- V8R23C00 for CR5D00E8KB61(SBOM) 8-Port 400GBase QSFP-DD Integrated Line Process Unit(NE5000E LPUI-3T2-C) 
                virent8090DEVCR5D00E8KB62(562133),    -- V8R23C00 for CR5D00E8KB62(SBOM) 8-Port 400GBase QSFP-DD Integrated Line Process Unit CM(NE5000E LPUI-3T2-C-CM)(2 ports enable)
                virent8090DEVCR5D00EINB61(562134),    -- V8R23C00 for CR5D00EINB61(SBOM) 32-Port 100GBase QSFP28 Integrated Line Process Unit(NE5000E LPUI-3T2-C) 
                virent8090DEVCR5D00EINB62(562135),    -- V8R23C00 for CR5D00EINB62(SBOM) 32-Port 100GBase QSFP28 Integrated Line Process Unit CM(NE5000E LPUI-3T2-C-CM)(8 ports enable)
                virent8090DEVCR5D00EDNB68(562136),    -- V8R23C00 for CR5D00EDNB68(SBOM) 16-Port 100GBase QSFP28 Integrated Line Process Unit(NE5000E LPUI-1T6-G) 
                virent8090DEVCR5D00EDNB69(562137),    -- V8R23C00 for CR5D00EDNB69(SBOM) 16-Port 100GBase QSFP28 Integrated Line Process Unit CM(NE5000E LPUI-1T6-G-CM)(4 ports enable)
                virent8090DEVCR5D00LRXF65(562138),    -- V8R23C00 for CR5D00LRXF65(SBOM) 72-Port 10GBase LAN/WAN-SFP+ Integrated Line Process Unit(NE5000E LPUI-1T6-G)
                virent8090DEVCR5D00LRXF66(562139),    -- V8R23C00 for CR5D00LRXF66(SBOM) 72-Port 10GBase LAN/WAN-SFP+ Integrated Line Process Unit CM(NE5000E LPUI-1T6-G-CM)(24 ports enable)
                virent8090DEVCR5DSFUIT261(562191),    -- V8R23C00 for CR5DSFUIT261(SBOM) NE5000E-20 1.6T CLC Integrated Switch Fabric Unit for Multi-Chassis (SFUI-1T6-M2)
                virent8090DEVCR5D00E8KB63(562192),    -- V8R23C00 for CR5D00E8KB63(SBOM) 8-Port 400GBase QSFP-DD Integrated Line Process Unit(NE5000E LPUI-3T2-C)
                virent8090DEVCR5D00EINB63(562193),    -- V8R23C00 for CR5D00EINB63(SBOM) 32-Port 100GBase QSFP28 Integrated Line Process Unit(NE5000E LPUI-3T2-C)
                virent8090DEVCR5D00E8KB64(562194),    -- V8R23C00 for CR5D00E8KB64(SBOM) 8-Port 400GBase QSFP-DD Integrated Line Process Unit CM(NE5000E LPUI-3T2-C-CM)(2 ports enable)
                virent8090DEVCR5D00EINB64(562195),    -- V8R23C00 for CR5D00EINB64(SBOM) 32-Port 100GBase QSFP28 Integrated Line Process Unit CM(NE5000E LPUI-3T2-C-CM)(8 ports enable)
                --END

                --BEGIN for V8R23C10
                virent8090DEVCR5D00NINB61(562140),    -- V8R23C10 for CR5D00NINB61(SBOM) 32-Port 100G OTN/ETH QSFP28 Integrated Line Process Unit(NE5000E LPUI-3T2-C)
                virent8090DEVCR5D00NINB62(562141),    -- V8R23C10 for CR5D00NINB62(SBOM) 32-Port 32-Port 100G OTN/ETH QSFP28 Integrated Line Process Unit(NE5000E LPUI-3T2-C-CM)(8 ports enable)
                --END

                --BEGIN for V8R24C00
                virent8090DEVCR5D00EEKBC0(562143),    -- V8R24C00 for CR5D00EEKBC0(SBOM) NetEngine5000E 20-Port 400GBase QSFP-DD Integrated Line Process Unit(NE5000E LPUI-8T)
                virent8090DEVCR5D00EEKBC1(562144),    -- V8R24C00 for CR5D00EEKBC1(SBOM) NetEngine5000E 20-Port 400GBase QSFP-DD Integrated Line Process Unit CM(NE5000E LPUI-8T-CM) (4 ports enable)
                virent8090DEVCR5D00EEKBC2(562145),    -- V8R24C00 for CR5D00EEKBC2(SBOM) NetEngine5000E 20-Port 400GBase QSFP-DD Integrated Line Process Unit Liquid Cooling(NE5000E LPUI-8T-L)
                virent8090DEVCR5DSFUIT460(562146),    -- V8R24C00 for CR5DSFUIT460(SBOM) NE5000E-20 8T CLC Switch Fabric Unit for Single Chassis(SFU-8T-S)
                virent8090DEVCR5DSFUIT461(562147),    -- V8R24C00 for CR5DSFUIT461(SBOM) NE5000E-20 8T CLC Switch Fabric Unit for Single Chassis Liquid Cooling(SFU-8T-S-L)
                virent8090DEVCR5D00EMNBC0(562148),    -- V8R24C00 for CR5D00EMNBC0(SBOM) NetEngine5000E 48-Port 100GBase QSFP28 Integrated Line Process Unit(NE5000E LPUI-8T)
                virent8090DEVCR5D00EMNBC1(562149),    -- V8R24C00 for CR5D00EMNBC1(SBOM) NetEngine5000E 48-Port 100GBase QSFP28 Integrated Line Process Unit CM(NE5000E LPUI-8T-CM)(8 ports enable)
                virent8090DEVCR5D00EMNBC2(562150),    -- V8R24C00 for CR5D00EMNBC2(SBOM) NetEngine5000E 48-Port 100GBase QSFP28 Integrated Line Process Unit Liquid Cooling(NE5000E LPUI-8T-L)
                virent8090DEVCR5D0MPUV1D0(567017),    -- V8R24C00 for NE5000E-20 Main Processing Unit V(MPUV)
                virent8090DEVCR5D0MPUV1D1(567018),    -- V8R24C00 for NE5000E-20 Main Processing Unit V Liquid Cooling(MPUV-L)
                virent8090DEVCR5D00E8KB65(562300),    -- V8R24C00 for CR5D00E8KB65(SBOM) 8-Port 400GBase QSFP-DD Integrated Line Process Unit CM(NE5000E LPUI-3T2-D-CM)
                virent8090DEVCR5D00EINB65(562301),    -- V8R24C00 for CR5D00EINB65(SBOM) 32-Port 100GBase QSFP28 Integrated Line Process Unit CM(NE5000E LPUI-3T2-D-CM)
                virent8090DEVCR5D00E8KB66(562196),    -- V8R24C00 for CR5D00E8KB66(SBOM) 8-Port 400GBase QSFP-DD Integrated Line Process Unit(NE5000E LPUI-3T2-E)
                virent8090DEVCR5D00EINB66(562197),    -- V8R24C00 for CR5D00EINB66(SBOM) 32-Port 100GBase QSFP28 Integrated Line Process Unit(NE5000E LPUI-3T2-E)
                virent8090DEVCR5D00E8KB67(562198),    -- V8R24C00 for CR5D00E8KB67(SBOM) 8-Port 400GBase QSFP-DD Integrated Line Process Unit CM(NE5000E LPUI-3T2-E-CM)(2 ports enable)
                virent8090DEVCR5D00EINB67(562199),    -- V8R24C00 for CR5D00EINB67(SBOM) 32-Port 100GBase QSFP28 Integrated Line Process Unit CM(NE5000E LPUI-3T2-E-CM)(8 ports enable)
                virent8090DEVCR5D00LRXF70(562306),    -- V8R24C00 for CR5D00LRXF70(SBOM) 72-Port 10GBase LAN/WAN-SFP+ Integrated Line Process Unit CM(NE5000E LPUI-1T6-K-CM)(12 ports enable)
                virent8090DEVCR5D00LRXF71(562307),    -- V8R24C00 for CR5D00LRXF71(SBOM) 72-Port 10GBase LAN/WAN-SFP+ Integrated Line Process Unit CM(NE5000E LPUI-1T6-L-CM)(12 ports enable)
                --END

              --BEGIN for V8R21C00 
               virent8090DEVCR8D00EJKBCP(676978),          -- V8R21C00 for CR8D00EJKBCP(SBOM) 36-Port 400GBase-QSFP-DD Integrated Line Processing Unit CM(LPUI-14T4-CM,Enable 36*100GE by default)
               virent8090DEVCR8D0E18KBCP(676979),          -- V8R21C00 for CR8D0E18KBCP(SBOM) 18-Port 400GBase-QSFP-DD Integrated Line Processing Unit CM(LPUI-7T2-CM,Enable 18*100GE by default)
               virent8090DEVCR8DVSUIK0C1(675822),    -- V8R21C00 for CR8DVSUIK0C1(SBOM) Integrated Service Unit 400(VSUI-400-E)
               virent8090DEVCR8D0CGN1HC1(676990),    -- V8R21C00 for CR8D0CGN1HC1(SBOM) CGN Versatile Service Flexible Card (VSUP-100)
               virent8090DEVCR8DVSUPA0C0(676993),    -- V8R21C00 for CR8DVSUPA0C0(SBOM) Integrated Service Card VSUP-100
               virent8090DEVCR8DVSUPA0C1(676994),    -- V8R21C00 for CR8DVSUPA0C1(SBOM) Integrated Service Card VSUPA-100
               virent8090DEVCR8DVSUIK0C2(675828),     -- V8R21C00 for CR8DVSUIK0C2(SBOM) Integrated Service Unit 400(VSUI-400A-E)
               virent8090DEVCR5DVSUIK076(688604),    -- V8R21C00 for CR5DVSUIK076(SBOM) Integrated Service Unit 400(VSUI-400)
               virent8090DEVCR5DVSUIK077(688605),    -- V8R21C00 for CR5DVSUIK077(SBOM) Integrated Service Unit 400(VSUI-400A)
               virent8090DEVCR5DVSUIK096(688696),    -- V8R24C00 for CR5DVSUIK096(SBOM) Integrated Service Unit(SAC)
               virent8090DEVCR5DVSUIK097(688697),    -- V8R24C00 for CR5DVSUIK097(SBOM) Integrated Service Unit(SAC-E)
               virent8090DEVME0DVSUIK076(688606),    -- V8R21C00 for ME0DVSUIK076(SBOM) Integrated Service Unit 400(VSUI-400)
               virent8090DEVME0DVSUIK077(688607),    -- V8R21C00 for ME0DVSUIK077(SBOM) Integrated Service Unit 400(VSUI-400A)
               virent8090DEVME0DVSUIK096(688698),    -- V8R24C00 for ME0DVSUIK096(SBOM) Integrated Service Unit(SAC)
               virent8090DEVME0DVSUIK097(688699),    -- V8R24C00 for ME0DVSUIK097(SBOM) Integrated Service Unit(SAC-E)
               virent8090DEVCR5DVSUIK078(688608),    -- V8R21C00 for CR5DVSUIK078(SBOM) Integrated Service Unit 400(VSUI-400-E)
               virent8090DEVCR5DVSUIK079(688609),    -- V8R21C00 for CR5DVSUIK079(SBOM) Integrated Service Unit 400(VSUI-400A-E)
               virent8090DEVME0DVSUIK078(688610),    -- V8R21C00 for ME0DVSUIK078(SBOM) Integrated Service Unit 400(VSUI-400-E)
               virent8090DEVME0DVSUIK079(688611),    -- V8R21C00 for ME0DVSUIK079(SBOM) Integrated Service Unit 400(VSUI-400A-E)
			   virent8090DEVME0DVSUIK07B(688692),    -- V8R21C00 for ME0DVSUIK07B(SBOM) Integrated Service Unit 401(VSUI-401)
               virent8090DEVME0DVSUIK07C(688693),    -- V8R21C00 for ME0DVSUIK07C(SBOM) Integrated Service Unit 401(VSUI-401A)
               virent8090DEVME0DVSUIK07D(688694),    -- V8R21C00 for ME0DVSUIK07D(SBOM) Integrated Service Unit 401(VSUI-401-E)
               virent8090DEVME0DVSUIK07E(688695),    -- V8R21C00 for ME0DVSUIK07E(SBOM) Integrated Service Unit 401(VSUI-401A-E)
               virent8090DEVCR5DVSUIK082(210040),    -- V8R25C00 for CR5DVSUIK082(SBOM) Integrated Service Unit 400(VSUI-400-E)
               virent8090DEVCR5DVSUIK081(210041),    -- V8R25C00 for CR5DVSUIK081(SBOM) Integrated Service Unit 400(VSUI-400-E)
               virent8090DEVME0DVSUIK07M(210042),    -- V8R25C00 for ME0DVSUIK07M(SBOM) Integrated Service Unit 400(VSUI-400A-E)
               virent8090DEVME0DVSUIK07L(210045),    -- V8R25C00 for ME0DVSUIK07L(SBOM) Integrated Service Unit 400(VSUI-400-E)
               virent8090DEVCR8DVSUF80C1(210046),    -- V8R25C00 for CR8DVSUF80C1(SBOM) Flexible Card Versatile Service Unit 800(VSUF-800)       
               virent600DEVCR8B0BKP03C6(688590),     -- V8R13C00 NetEngine-8000-F1A CR8B0BKP03C6(SBOM), F1A-8H20Q-E
               virent600DEVCR8B0BKP03C7(688591),     -- V8R13C00 NetEngine-8000-F1A CR8B0BKP03C7(SBOM), F1A-8H20Q-E
               virent600DEVCR8B0BKP03C8(688592),     -- V8R13C00 NetEngine-8000-F1A CR8B0BKP03C8(SBOM), F1A-8H20Q-E
               virent600DEVCR8B0BKP03C9(688593),     -- V8R13C00 NetEngine-8000-F1A CR8B0BKP03C9(SBOM), F1A-8H20Q-E
               virent600DEVCR8B0BKP03E1(688685),     -- V8R23C10 NetEngine-8000-F1A CR8B0BKP03E1(SBOM), F1A-C
               virent600DEVCR8B0BKP03E0(688686),     -- V8R23C10 NetEngine-8000-F1A CR8B0BKP03E0(SBOM), F1A-C
			   virent600DEVCR8B0BKP03E3(688691),     -- V8R24C00 NetEngine-8000-F1A CR8B0BKP03E3(SBOM), F1A-C
               virent8090DEVCR9DLPUIT081(688594),    -- V8R13C00 for CR9DLPUIT081(SBOM)
               virent8090DEVCR9D00EPYF8Q(688595),    -- V8R13C00 for CR9D00EPYF8Q(SBOM)
               virent8090DEVCR9D00EKNB82(688596),    -- V8R13C00 for CR9D00EKNB82(SBOM)
               virent8090DEVCR9DE8KE8N8V(688597),    -- V8R13C00 for CR9DE8KE8N8V(SBOM)
               virent8090DEVCR9D00EKNB8S(688598),    -- V8R13C00 for CR9D00EKNB8S(SBOM)
               virent8090DEVCR9D00EKNB8U(688599),    -- V8R13C00 for CR9D00EKNB8U(SBOM)
               virent8090DEVCR9DE8KE8N8W(688600),    -- V8R13C00 for CR9DE8KE8N8W(SBOM)
               virent8090DEVCR9D00EENB86(688601),    -- V8R13C00 for CR9D00EENB86(SBOM)
               virent8090DEVCR9D00EKNB86(688602),    -- V8R13C00 for CR9D00EKNB86(SBOM)
               virent8090DEVCR9P9KHALM8E(688603),    -- V8R13C00 for CR9P9KHALM8E(SBOM)
               virent8090DEVCR5D00EENB74(688615),    -- V8R13C00 for CR5D00EENB74(SBOM) 8-Port 20-Port 100GBase-QSFP28 Integrated Line Processing Unit (LPUI-2TA)
               virent8090DEVCR5D00EENB75(688616),    -- V8R13C00 for CR5D00EENB75(SBOM) 8-Port 20-Port 100GBase-QSFP28 Integrated Line Processing Unit L(LPUI-2T-L)
               virent8090DEVCR5D00EENB7R(688617),    -- V8R13C00 for CR5D00EENB7R(SBOM) 8-Port 20-Port 100GBase-QSFP28 FlexE/MACsec Integrated Line Processing Unit CM(LPUI-2T-CM)
               virent8090DEVCR5D00EENBK4(688618),    -- V8R13C00 for CR5D00EENBK4(SBOM) 8-Port 20-Port 100GBase-QSFP28 Integrated Line Processing Unit(LPUI-2T-K)
               virent8090DEVIG2D00EENB05(688619),    -- V8R13C00 for IG2D00EENB05(SBOM) 20-Port 100GBase-QSFP28 Integrated Line Processing Unit (LPUI-2TA)
               virent8090DEVCR5DSRUAD270(564873),    -- V8R13C00 for CR5DSRUAD270(SBOM) Switch and Route Processing Unit A132(32G Memory)
               virent8090DEVCR5DSFUIT27Q(564874),    -- V8R13C00 for CR5DSFUIT27Q(SBOM) 2Tbps Switch Fabric Unit P(SFUI-2T-P)
               virent8090DEVCR5DSFUITD72(564875),    -- V8R13C00 for CR5DSFUITD72(SBOM) 2Tbps Switch Fabric Unit Q(SFUI-2T-Q)
               virent8090DEVCR8D00LRXFC6(564878),    -- V8R13C00 for CR8D00LRXFC6(SBOM) 72-Port 25GE(SFP28)/10GE(SFP+)/GE(SFP) Integrated Line Processing Unit CM(LPUI-2T-CM)
               virent8090DEVCR8D00LRXFC7(564879),    -- V8R13C00 for CR8D00LRXFC7(SBOM) 72-Port 25GE(SFP28)/10GE(SFP+)/GE(SFP) Integrated Line Processing Unit CM(LPUI-2TA-CM)
               virent8090DEVCR8D00LRXFC8(564880),    -- V8R13C00 for CR8D00LRXFC8(SBOM) 72-Port 25GE(SFP28)/10GE(SFP+)/GE(SFP) Integrated Line Processing Unit L CM(LPUI-2T-L-CM)
               virent8090DEVCR8D00LRXFC9(564881),    -- V8R13C00 for CR8D00LRXFC9(SBOM) 72-Port 25GE(SFP28)/10GE(SFP+)/GE(SFP) Integrated Line Processing Unit L(LPUI-2TA-L-CM)
               virent8090DEVCR8DE8KE8NCU(564882),    -- V8R13C00 for CR8DE8KE8NCU(SBOM) 8-Port 400GBase-QSFP-DD + 8-Port 100GBase-QSFP28 Integrated Line Processing Unit CM(LPUI-4T-CM,Enable 16*100GE by default)
               virent8090DEVCR8DE8KE8NCV(564883),    -- V8R13C00 for CR8DE8KE8NCV(SBOM) 8-Port 400GBase-QSFP-DD + 8-Port 100GBase-QSFP28 Integrated Line Processing Unit CM(LPUI-4TA-CM)
               virent8090DEVCR8DE8KE8NCX(564884),    -- V8R13C00 for CR8DE8KE8NCX(SBOM) 8-Port 400GBase-QSFP-DD + 8-Port 100GBase-QSFP28 Integrated Line Processing Unit L CM(LPUI-4TA-L-CM)
               virent8090DEVCR8DE8KE8NCW(564885),    -- V8R13C00 for CR8DE8KE8NCW(SBOM) 8-Port 400GBase-QSFP-DD + 8-Port 100GBase-QSFP28 Integrated Line Processing Unit L CM(LPUI-4T-L-CM,Enable 16*100GE by default)
               virent8090DEVCR5DMPUX8673(688620),    -- V8R13C00 for CR5DMPUX8673(SBOM) Main Processing Unit B11A(32G Memory)
               virent8090DEVME0DMPUX8673(688621),    -- V8R13C00 for ME0DMPUX8673(SBOM) Main Processing Unit B11A(32G Memory)
               virent8090DEVCR5DMPUX8672(688622),    -- V8R13C00 for CR5DMPUX8672(SBOM) Main Processing Unit B11(32G Memory)
               virent8090DEVCX6DMPUX8672(688623),    -- V8R13C00 for CX6DMPUX8672(SBOM) Main Processing Unit B11(32G Memory)
               virent8090DEVTNRDMPUX8672(688624),    -- V8R13C00 for TNRDMPUX8672(SBOM) Main Processing Unit B11(32G Memory)
               virent8090DEVME0DMPUX8672(688625),    -- V8R13C00 for ME0DMPUX8672(SBOM) Main Processing Unit B11(32G Memory)
               virent8090DEVCR5D0SRUAI70(688626),    -- V8R13C00 for CR5D0SRUAI70(SBOM) Switch and Route Processing Unit A18A(SRUA-1TA-F, 32G Memory)
               virent8090DEVME0D0SRUAI70(688627),    -- V8R13C00 for ME0D0SRUAI70(SBOM) Switch and Route Processing Unit A18A(SRUA-1TA-F, 32G Memory)
               virent8090DEVCR5D0SRUAI71(688628),    -- V8R13C00 for CR5D0SRUAI71(SBOM) Switch and Route Processing Unit A18(SRUA-1T-F, 32G Memory)
               virent8090DEVCX6D0SRUAI71(688629),    -- V8R13C00 for CX6D0SRUAI71(SBOM) Switch and Route Processing Unit A18(SRUA-1T-F, 32G Memory)
               virent8090DEVTNRD0SRUAI71(688630),    -- V8R13C00 for TNRD0SRUAI71(SBOM) Switch and Route Processing Unit A18(SRUA-1T-F, 32G Memory)
               virent8090DEVME0D0SRUAI71(688631),    -- V8R13C00 for ME0D0SRUAI71(SBOM) Switch and Route Processing Unit A18(SRUA-1T-F, 32G Memory)
               virent8090DEVCR5D0SRUAH70(688632),    -- V8R13C00 for CR5D0SRUAH70(SBOM) Switch and Route Processing Unit A17A(SRUA-480A-G, 32G Memory)
               virent8090DEVME0D0SRUAH70(688633),    -- V8R13C00 for ME0D0SRUAH70(SBOM) Switch and Route Processing Unit A17A(SRUA-480A-G, 32G Memory)
               virent8090DEVCR5D0SRUAH71(688634),    -- V8R13C00 for CR5D0SRUAH71(SBOM) Switch and Route Processing Unit A17(SRUA-480-G, 32G Memory)
               virent8090DEVCX6D0SRUAH71(688635),    -- V8R13C00 for CX6D0SRUAH71(SBOM) Switch and Route Processing Unit A17(SRUA-480-G, 32G Memory)
               virent8090DEVTNRD0SRUAH71(688636),    -- V8R13C00 for TNRD0SRUAH71(SBOM) Switch and Route Processing Unit A17(SRUA-480-G, 32G Memory)
               virent8090DEVME0D0SRUAH71(688637),    -- V8R13C00 for ME0D0SRUAH71(SBOM) Switch and Route Processing Unit A17(SRUA-480-G, 32G Memory)
               virent8090DEVCX6DMPUX8613(688638),    -- V8R13C00 for CX6DMPUX8613(SBOM) Main Processing Unit B11A(32G Memory)
               virent8090DEVCX6D0SRUAI11(688639),    -- V8R13C00 for CX6D0SRUAI11(SBOM) Switch and Route Processing Unit A18(SRUA-1T-F, 32G Memory)
               virent8090DEVCX6D0SRUAH11(688640),    -- V8R13C00 for CX6D0SRUAH11(SBOM) Switch and Route Processing Unit A17(SRUA-480-G, 32G Memory)
               virent8090DEVCR5D0MPUB973(688641),    -- V8R13C00 for CR5D0MPUB973(SBOM) Main Processing Unit B91A(32G Memory)
               virent8090DEVCR5D0SRUAE72(688642),    -- V8R13C00 for CR5D0SRUAE72(SBOM) Switch and Route Processing Unit A141A(SRUA-1TA-E, 32G Memory)
               virent600DEVCR8P0BKP03C0(688646),    -- V8R21C00 CR8P0BKP03C0(SBOM) NetEngine 8000 F2A-8K36H Integrated Chassis Components(Port-side Intake)
               virent600DEVCR8P0BKP03C1(688647),     -- V8R21C00 CR8P0BKP03C1(SBOM) NetEngine 8000 F2A-8K36H Integrated Chassis Components(Port-side Exhaust)
               virent8090DEVIG2D00SPUG07(688648),    -- V8R13C00 for IG2D00SPUG07(SBOM) High Performance X8A&X16A Service Processing Unit-SPUGA,with HW Service Inspection Gateway Software
               virent8090DEVCR5D0SRUAE73(688650),    -- V8R13C00 for CR5D0SRUAE73(SBOM) Switch and Route Processing Unit A141(SRUA-1T-E, 32G Memory)
               virent8090DEVCX6D0SRUAI72(688651),    -- V8R13C00 for CX6D0SRUAI72(SBOM) Switch and Route Processing Unit A141(SRUA-1T-E, 32G Memory)
               virent8090DEVTNRD0SRUAI72(688652),    -- V8R13C00 for TNRD0SRUAI72(SBOM) Switch and Route Processing Unit A141(SRUA-1T-E, 32G Memory)
               virent8090DEVCX6D0SRUAI12(688653),    -- V8R13C00 for CX6D0SRUAI12(SBOM) Switch and Route Processing Unit A141A(SRUA-1TA-E, 32G Memory)
               virent8090DEVME0D0SRUAH72(688654),    -- V8R13C00 for ME0D0SRUAH72(SBOM) Switch and Route Processing Unit A19A(SRUA-480A-H, 32G Memory)
               virent8090DEVME0D0SRUAH73(688655),    -- V8R13C00 for ME0D0SRUAH73(SBOM) Switch and Route Processing Unit A19(SRUA-480-H, 32G Memory)
               virent8090DEVME0D0SRUAI72(688656),    -- V8R13C00 for ME0D0SRUAI72(SBOM) Switch and Route Processing Unit A141(SRUA-1T-E, 32G Memory)
               virent8090DEVME0D0SRUAI73(688657),    -- V8R13C00 for ME0D0SRUAI73(SBOM) Switch and Route Processing Unit A141A(SRUA-1TA-E, 32G Memory)
               virent8090DEVCR5D0SRUAJ70(688658),    -- V8R13C00 for CR5D0SRUAJ70(SBOM) Switch and Route Processing Unit A19A(SRUA-480A-H, 32G Memory)
               virent8090DEVCR5D0SRUAJ71(688659),    -- V8R13C00 for CR5D0SRUAJ71(SBOM) Switch and Route Processing Unit A19(SRUA-480-H, 32G Memory)
               virent8090DEVCX6D0SRUAH72(688660),    -- V8R13C00 for CX6D0SRUAH72(SBOM) Switch and Route Processing Unit A19(SRUA-480-H, 32G Memory)
               virent8090DEVTNRD0SRUAH72(688661),    -- V8R13C00 for TNRD0SRUAH72(SBOM) Switch and Route Processing Unit A19(SRUA-480-H, 32G Memory)
               virent8090DEVCX6D0SRUAH12(688662),    -- V8R13C00 for CX6D0SRUAH12(SBOM) Switch and Route Processing Unit A19A(SRUA-480A-H, 32G Memory)
               virent8090DEVCR5DVSUFK0K3(688663),    -- V8R13C00 for CR5DVSUFK0K3(SBOM) Integrated Service Unit 400(VSUI-400-K)
               virent8090DEVCX6D0MPUB911(688664),    -- V8R13C00 for CX6D0MPUB911(SBOM) Main Processing Unit B91A(32G Memory)
               virent8090DEVME0D0MPUB971(688665),    -- V8R13C00 for ME0D0MPUB971(SBOM) Main Processing Unit B91(32G Memory)
               virent8090DEVME0DSFUIM07K(688666),    -- V8R13C00 for ME0DSFUIM07K(SBOM) 480Gbps Switch Fabric Unit N(SFUI-480A-N)
               virent8090DEVME0DSFUIM07L(688667),    -- V8R13C00 for ME0DSFUIM07L(SBOM) 480Gbps Switch Fabric Unit N(SFUI-480-N)
               virent8090DEVCX6DISUFT012(688668),    -- V8R13C00 for CX6DISUFT012(SBOM) Flexible Card Integrated Service Unit(ISUF-1TA)
               --END			   
               --BEGIN for V8R21C00
               virent8090DEVANGMHSTG1200(225642),    --V8R21C00 ANGMHSTG1200(SBOM) ATN 910C-G, AC Power, Port Capacity 16*10GE/GE/FE(o)+12*GE/FE(o)+4*GE/FE(e), Default 2*10GE+8*GE
               virent8090DEVANGMHSTG1100(225643),    --V8R21C00 ANGMHSTG1100(SBOM) ATN 910C-G, DC Power, Port Capacity 16*10GE/GE/FE(o)+12*GE/FE(o)+4*GE/FE(e), Default 2*10GE+8*GE
               virent8090DEVCR8PM1ABAS3(688485),     --V8R21C00 CR8PM1ABAS3(SBOM) NetEngine 8000 M1A, DC Power,Port Capacity 16*10GE+12*GE(o)+4*GE(e)
			   virent8090DEVCR8PM1ABAS4(688433),     --V8R21C00 CR8PM1ABAS4(SBOM) NetEngine 8000 M1A, AC Power,Port Capacity 16*10GE+12*GE(o)+4*GE(e)
               virent8090DEVCR8PM1ABAS6(688434),     --V8R21C00 CR8PM1ABAS6(SBOM) NetEngine 8000 M1A, AC Power,Port Capacity 16*10GE+12*GE(o)+4*GE(e)
               virent8090DEVCR8PM1ABAS5(688435),     --V8R21C00 CR8PM1ABAS5(SBOM) NetEngine 8000 M1A, DC Power,Port Capacity 16*10GE+12*GE(o)+4*GE(e)
               virent8090DEVCR8PM1ABAS7(688436),     --V8R21C00 CR8PM1ABAS7(SBOM) NetEngine 8000 M1A, DC Power,Port Capacity 16*10GE+12*GE(o)+4*GE(e)
               virent8090DEVCR8PM1ABASDD(333126),     --V8R24C10 CR8PM1ABASDD(SBOM) NetEngine 8000E M1A, DC Power,Port Capacity 16*10GE+12*GE(o)+4*GE(e)
               virent8090DEVCR8PM1ABASAD(333127),     --V8R24C10 CR8PM1ABASAD(SBOM) NetEngine 8000E M1A, AC Power,Port Capacity 16*10GE+12*GE(o)+4*GE(e)
               virent8090DEVCR8PM1ABASDE(333128),     --V8R24C10 CR8PM1ABASDE(SBOM) NetEngine 8000E M1A, DC Power,Port Capacity 16*10GE+12*GE(o)+4*GE(e)
               virent8090DEVCR8PM1ABASAE(333129),     --V8R24C10 CR8PM1ABASAE(SBOM) NetEngine 8000E M1A, AC Power,Port Capacity 16*10GE+12*GE(o)+4*GE(e)
               virent8090DEVCR8PM1CBASAT(333130),     --V8R24C10 CR8PM1CBASAT(SBOM) NetEngine 8000E M1C, AC Power,Port Capacity 16*10GE+8*GE(o)+4*GE(e), None of the ports are available by default
               virent8090DEVCR8PM1CBASD3(333131),     --V8R24C10 CR8PM1CBASD3(SBOM) NetEngine 8000E M1C, DC Power,Port Capacity 16*10GE+8*GE(o)+4*GE(e), None of the ports are available by default
               virent8090DEVCR8PM1CBASAR(333132),     --V8R24C10 CR8PM1CBASAR(SBOM) NetEngine 8000E M1C, AC Power,Port Capacity 16*10GE+8*GE(o)+4*GE(e), None of the ports are available by default
               virent8090DEVCR8PM1CBASD2(333133),     --V8R24C10 CR8PM1CBASD2(SBOM) NetEngine 8000E M1C, DC Power,Port Capacity 16*10GE+8*GE(o)+4*GE(e), None of the ports are available by default
               virent8090DEVCR8PM1DBASD1(333134),     --V8R24C10 CR8PM1DBASD1(SBOM) NetEngine 8000E M1D, DC Power,Port Capacity 4*100GE/50GE+16*25GE/10GE/GE/FE+8*10GE/GE/FE,exclude auxiliary materials
               virent8090DEVCR8PM1DBASA1(333135),     --V8R24C10 CR8PM1DBASA1(SBOM) NetEngine 8000E M1D, AC Power,Port Capacity 4*100GE/50GE+16*25GE/10GE/GE/FE+8*10GE/GE/FE,exclude auxiliary materials
               virent8090DEVCR8PM1DBASA0(333136),     --V8R24C10 CR8PM1DBASA0(SBOM) NetEngine 8000E M1D, AC Power,Port Capacity 4*100GE/50GE+16*25GE/10GE/GE/FE+8*10GE/GE/FE,exclude auxiliary materials
               virent8090DEVCR8PM1DBASD0(333137),     --V8R24C10 CR8PM1DBASD0(SBOM) NetEngine 8000E M1D, DC Power,Port Capacity 4*100GE/50GE+16*25GE/10GE/GE/FE+8*10GE/GE/FE,exclude auxiliary materials
               virent8090DEVCR8PM1EBBSD0(120024),     --V8R25C10 CR8PM1EBBSD0(SBOM) NetEngine 8000E M1E-B, DC Power(Port Capacity 2*400/100GE+4*100/50GE+8*50/25/10/GE+16*25/10/GE,xclude auxiliary materials)
               virent8090DEVCR8PM1EBBSA0(120023),     --V8R25C10 CR8PM1EBBSA0(SBOM) NetEngine 8000E M1E-B, AC Power(Port Capacity 2*400/100GE+4*100/50GE+8*50/25/10/GE+16*25/10/GE,xclude auxiliary materials)
               virent8090DEVCR5D0MPUB974(688673),    -- V8R21C00 for CR5D0MPUB974(SBOM) Main Processing Unit B92A(32G Memory)
               virent8090DEVCR5D0MPUB975(688674),    -- V8R21C00 for CR5D0MPUB975(SBOM) Main Processing Unit B92(32G Memory)
               virent8090DEVME0D0MPUB974(688675),    -- V8R21C00 for ME0D0MPUB974(SBOM) Main Processing Unit B92A(32G Memory)
               virent8090DEVME0D0MPUB975(688676),    -- V8R21C00 for ME0D0MPUB975(SBOM) Main Processing Unit B92(32G Memory)
               virent8090DEVTNRD0MPUB975(688677),    -- V8R21C00 for TNRD0MPUB975(SBOM) Main Processing Unit B92(32G Memory)
               virent8090DEVCX6D0MPUB974(688678),    -- V8R21C00 for CX6D0MPUB974(SBOM) Main Processing Unit B92A(32G Memory)
               virent8090DEVCX6D0MPUB975(688679),    -- V8R21C00 for CX6D0MPUB975(SBOM) Main Processing Unit B92(32G Memory)
               virent8090DEVME0DVSUF8072(161609),    -- V8R21C00 for ME0DVSUF8072(SBOM) Flexible Card Versatile Service Unit 80(VSUF-80-T)
               --END

               --BEGIN for V8R21C00
               virent8090DEVCR5DLPUFM375(365445),   -- V8R21C00 for CR5DLPUFM375(SBOM) Flexible Card Line Processing Unit(LPUF-483-E-CM, enable slot 0 by default)
               virent8090DEVME0DBSUFM073(425568),   -- V8R21C00 for ME0DBSUFM073(SBOM) Flexible Card Broadband Service Unit(BSUF-483-E,2 sub-slots)
               virent8090DEVCR5DSFUIT27R(350117),   -- V8R21C00 for CR5DSFUIT27R(SBOM) 2Tbps Switch Fabric Unit P(SFUI-2TA-P)
               virent8090DEVCX6DSFUIT27G(809173),   -- V8R21C00 for CX6DSFUIT27G(SBOM) 2Tbps Switch Fabric Unit P(SFUI-2T-P)
               virent8090DEVTNRDSFUIT27Q(388472),   -- V8R21C00 for TNRDSFUIT27Q(SBOM) 2Tbps Switch Fabric Unit P(SFUI-2T-P)
               virent8090DEVCR5DSFUITD73(194560),   -- V8R21C00 for CR5DSFUITD73(SBOM) 2Tbps Switch Fabric Unit Q(SFUI-2TA-Q)
               virent8090DEVCX6DSFUIT270(977102),   -- V8R21C00 for CX6DSFUIT270(SBOM) 2Tbps Switch Fabric Unit Q(SFUI-2T-Q)
               virent8090DEVTNRDSFUIT270(895279),   -- V8R21C00 for TNRDSFUIT270(SBOM) 2Tbps Switch Fabric Unit Q(SFUI-2T-Q)
               virent8090DEVCR5DSRUAD271(973375),   -- V8R21C00 for CR5DSRUAD271(SBOM) Switch and Route Processing Unit A132A(32G Memory)
               virent8090DEVCX6D0SRUAD72(841680),   -- V8R21C00 for CX6D0SRUAD72(SBOM) Switch and Route Processing Unit A132(32G Memory)
               virent8090DEVTNRD0SRUAD72(744977),   -- V8R21C00 for TNRD0SRUAD72(SBOM) Switch and Route Processing Unit A132(32G Memory)
			   
			    virent8090DEVCR5D0SRUAH72(884885),   --  for CR5D0SRUAH72(SBOM) Switch and Route Processing Unit A20A(SRUA-480A-I, 32G Memory)
                virent8090DEVCR5D0SRUAH73(923108),   --  for CR5D0SRUAH73(SBOM) Switch and Route Processing Unit A20(SRUA-480-I, 32G Memory)
                virent8090DEVCX6D0SRUAH73(773065),   --  for CX6D0SRUAH73(SBOM) Switch and Route Processing Unit A20(SRUA-480-I, 32G Memory)
                virent8090DEVCX6D0SRUAH13(773066),   --  for CX6D0SRUAH13(SBOM) Switch and Route Processing Unit A20(SRUA-480-I, 32G Memory)
				virent8090DEVTNRD0SRUAH73(727642),   --  for TNRD0SRUAH73(SBOM) Switch and Route Processing Unit A20(SRUA-480-I, 32G Memory)
                virent8090DEVME0D0SRUAH76(256575),   --  for ME0D0SRUAH76(SBOM) Switch and Route Processing Unit A20A(SRUA-480A-I, 32G Memory)
                virent8090DEVME0D0SRUAH77(553460),   --  for ME0D0SRUAH77(SBOM) Switch and Route Processing Unit A20(SRUA-480-I, 32G Memory)
               virent8090DEVME0D0SRUAH78(553461),   --  for ME0D0SRUAH78(SBOM) Switch and Route Processing Unit A22A(SRUA-480A-J, 32G Memory)
               virent8090DEVME0D0SRUAH79(553462),   --  for ME0D0SRUAH79(SBOM) Switch and Route Processing Unit A22(SRUA-480-J, 32G Memory)
                virent8090DEVCR5D0SRUAI72(872979),   --  for CR5D0SRUAI72(SBOM) Switch and Route Processing Unit A21A(SRUA-1TA-H, 32G Memory)
                virent8090DEVCR5D0SRUAI73(179748),   --  for CR5D0SRUAI73(SBOM) Switch and Route Processing Unit A21(SRUA-1T-H, 32G Memory)
                virent8090DEVCX6D0SRUAI73(394380),   --  for CX6D0SRUAI73(SBOM) Switch and Route Processing Unit A21(SRUA-1T-H, 32G Memory)
                virent8090DEVCX6D0SRUAI13(394381),   --  for CX6D0SRUAI13(SBOM) Switch and Route Processing Unit A21(SRUA-1T-H, 32G Memory)
				virent8090DEVTNRD0SRUAI73(959654),   --  for TNRD0SRUAI73(SBOM) Switch and Route Processing Unit A21(SRUA-1T-H, 32G Memory)
                virent8090DEVME0D0SRUAI74(870511),   --  for ME0D0SRUAI74(SBOM) Switch and Route Processing Unit A21A(SRUA-1TA-H, 32G Memory)
                virent8090DEVME0D0SRUAI75(576765),   --  for ME0D0SRUAI75(SBOM) Switch and Route Processing Unit A21(SRUA-1T-H, 32G Memory)
                virent8090DEVIG2D0SRUAI72(385921),   --  for IG2D0SRUAI72(SBOM) Switch and Route Processing Unit A21A(SRUA-1TA-H, 32G Memory)

               virent8090DEVTPSM0HOSTA1(249599),    -- V8R21C00 for TPSM0HOSTA1(SBOM)
               virent8090DEVTPSM0HOSTD0(249699),    -- V8R21C00 for TPSM0HOSTD0(SBOM)
               virent8090DEVTPSM0HOSTB1(249799),    -- V8R21C00 for TPSM0HOSTB1(SBOM)
               virent8090DEVTND1MD1A(249899),       -- V8R21C00 for TND1MD1A(SBOM)
               virent8090DEVCR5DLPUFF373(567862),   -- V8R21C00 for CR5DLPUFF373(SBOM)
               virent8090DEVCR5DLPUFF372(567861),   -- V8R21C00 for CR5DLPUFF372(SBOM)
               virent8090DEVCR57LPU2TE(675817),      -- V8R21C00 for CR57LPU2TE(SBOM)
               virent8090DEVCR5DEDVE8N72(688680),   -- V8R21C00 for CR5DEDVE8N72(SBOM) 16-Port 50G/8-Port 100GBase-QSFP28 FlexE Integrated Line Processing Unit L(LPUI-1T2-L)
               virent8090DEVME0DMSUFT078(688681),   -- V8R21C00 for ME0DMSUFT078(SBOM) Flexible Card Multi Service Unit(MSUF-1T2,2 sub-slots)
               virent8090DEVME0DMSUFT079(688682),   -- V8R21C00 for ME0DMSUFT079(SBOM) Flexible Card Multi Service Unit(MSUF-1T2A,2 sub-slots)
               --END
               
               --BEGIN for V8R21C00 NE40E-200G
               virent8090DEVCR5DLPUF5374(513967),   -- V8R21C00 for CR5DLPUF5374(SBOM) Flexible Card Line Processing Unit(LPUF-53A)
               virent8090DEVCR5DLPUF5375(433904),   -- V8R21C00 for CR5DLPUF5375(SBOM) Flexible Card Line Processing Unit(LPUF-53)
               virent8090DEVCR5DLPUFF377(655297),   -- V8R21C00 for CR5DLPUFF377(SBOM) 8-Port GE-SFP/10GE-SFP+ and 16-Port GE-SFP Flexible Card Line Processing Unit(LPUI-243A-CM, Enable 8*100M+16*GE by default, Supporting one sub-slot for flexible card)
               virent8090DEVCR5DLPUFF378(467374),   -- V8R21C00 for CR5DLPUFF378(SBOM) 8-Port GE-SFP/10GE-SFP+ and 16-Port GE-SFP Flexible Card Line Processing Unit(LPUI-243-CM, Enable 8*100M+16*GE by default, Supporting one sub-slot for flexible card)
               --END

                --BEGIN for V1R21C10 X86 MPU
               virent8090DEVCR8D0MPUA4C1(682999),    -- V1R21C10 for CR8D0MPUA4C1(SBOM) NetEngine 8000 Main Processing Unit A4A(MPUA4A)
               virent8090DEVCR8D0MPUA4C0(706130),    -- V1R21C10 for CR8D0MPUA4C0(SBOM) NetEngine 8000 Main Processing Unit A4(MPUA4)
               virent8090DEVCR8D0MPUA5C1(159477),    -- V1R21C10 for CR8D0MPUA5C1(SBOM) NetEngine 8000E Main Processing Unit A5A(MPUA5A)
               virent8090DEVCR8D0MPUA8C5(932387),    -- V1R21C10 for CR8D0MPUA8C5(SBOM) NetEngine 8100 Main Processing Unit A8A(MPUA8A)
               virent8090DEVCR8D0MPUA6C0(852150),    -- V1R21C10 for CR8D0MPUA6C0(SBOM) NetEngine 8000 Main Processing Unit A6(MPUA6)
               virent8090DEVCR8D0MPUA6C1(517911),    -- V1R21C10 for CR8D0MPUA6C1(SBOM) NetEngine 8000 Main Processing Unit A6A(MPUA6A)
               virent8090DEVCR8D0MPUA7C4(736463),    -- V1R21C10 for CR8D0MPUA7C4(SBOM) NetEngine 8000E Main Processing Unit A7A(MPUA7A)
               virent8090DEVCR8D0MPUA6C2(329596),    -- V8R21C10 for CR8D0MPUA6C2(SBOM) NetEngine 8000 Main Processing Unit A6B(MPUA6B)
               virent8090DEVCR8D0MPUA4C2(517066),    -- V8R21C10 for CR8D0MPUA4C2(SBOM) NetEngine 8000 Main Processing Unit A4B(MPUA4B)
               virent8090DEVCR8D0MPUAXC0(688760),    -- V8R23C00 for CR8D0MPUAXC0(SBOM) NetEngine 8000 Main Processing Unit A10(MPUA10)
               virent8090DEVCR8D0MPUAXC2(688761),    -- V8R23C00 for CR8D0MPUAXC2(SBOM) NetEngine 8000 Main Processing Unit A10B(MPUA10B)
               virent8090DEVCR8D0MPUAXCA(688762),    -- V8R23C00 for CR8D0MPUAXCA(SBOM) NetEngine 8000 Main Processing Unit A10A(MPUA10A)
               virent8090DEVCR8D0MPUA8C6(688763),    -- V8R23C00 for CR8D0MPUA8C6(SBOM) NetEngine 8000 Main Processing Unit A9A(MPUA9A)
               virent8090DEVCR8D0MPUAXC1(688764),    -- V8R23C00 for CR8D0MPUAXC1(SBOM) NetEngine 8000 Main Processing Unit A11(MPUA11)
               virent8090DEVCR8D0MPUAXC3(688765),    -- V8R23C00 for CR8D0MPUAXC3(SBOM) NetEngine 8000 Main Processing Unit A11B(MPUA11B)
			   virent8090DEVTPVM0HOSTA04(689209),  -- V8R23C00 for TPVM0HOSTA04(SBOM) PTN 917-F,TPVM0HOSTA04,PTN 917-F - AC Power,with 2*10GE Fine Granularity Unit(o),6*GE/FE(o),4*GE/FE(e)
			   virent8090DEVCR8DVSUPA0F0(679991),    -- V8R23C00 for CR8DVSUPA0F0(SBOM) Integrated Service Card 100(VSUP-100)
               virent8090DEVCR8DVSUPA0F1(679992),    -- V8R23C00 for CR8DVSUPA0F1(SBOM) Integrated Service Card 100(VSUPA-100)
			   virent8090DEVCR8DGSUPA0C0(679796),    -- V8R23C00 for CR8DGSUPA0C0(SBOM) Multi-function Integrated Service Card(VSUP-100)
               virent8090DEVCR8DGSUPA0C1(679797),    -- V8R23C00 for CR8DGSUPA0C1(SBOM) Multi-function Integrated Service Card(VSUPA-100)
               virent8090DEVCR8DVSUPA0F2(679798),    -- V8R25C00 for CR8DVSUPA0F2(SBOM) Multi-function Integrated Service Card(VSUP-100)
               virent8090DEVCR8DVSUPA0F3(679799),    -- V8R25C00 for CR8DVSUPA0F3(SBOM) Multi-function Integrated Service Card(VSUPA-100)
			   virent8090DEVCR8DVSUIK0C3(676828),    -- V8R23C00 for CR8DVSUIK0C3(SBOM) Integrated Service Unit 400(VSUI-400-E)
               virent8090DEVCR8DVSUIK0C4(676829),    -- V8R23C00 for CR8DVSUIK0C4(SBOM) Integrated Service Unit 400(VSUI-400A-E)
			   virent8090DEVCR8DLPUFT171(689369),   -- V8R23C00 for CR8DLPUFT171(SBOM) Flexible Card Line Processing Unit(LPUF-1T)
               virent8090DEVCR8DLPUFT072(689370),   -- V8R23C00 for CR8DLPUFT072(SBOM) Flexible Card Line Processing Unit (LPUF-1TA)
               virent8090DEVCR81LPUFT072(689371),   -- V8R23C00 for CR81LPUFT072(SBOM) Flexible Card Line Processing Unit (LPUF-1TA)
               virent8090DEVCR8DLPUFT172(689372),   -- V8R23C00 for CR8DLPUFT172(SBOM) Flexible Card Line Processing Unit (LPUF-1TA)
               virent8090DEVCR8DLPUFT0D1(689373),   -- V8R23C00 for CR8DLPUFT0D1(SBOM) Flexible Card Line Processing Unit(LPUF-2T)
               virent8090DEVCR8DLPUFT0D2(689374),   -- V8R23C00 for CR8DLPUFT0D2(SBOM) Flexible Card Line Processing Unit(LPUF-2TA)
               virent8090DEVCR8DLPUFT182(689376),   -- V8R23C00 for CR8DLPUFT182(SBOM) Flexible Card Line Processing Unit (LPUF-1TA-E)
               virent8090DEVCR8DLPUFT181(689375),   -- V8R23C00 for CR8DLPUFT181(SBOM) Flexible Card Line Processing Unit (LPUF-1T-E)
               virent8090DEVCR81LPUFT073(689379),   -- V8R24C10 for CR81LPUFT073(SBOM) Flexible Card Line Processing Unit(LPUF-1TA)
			   virent8090DEVANHMHSTA0700(229698),   -- V8R23C00 for ANHMHSTA0700(SBOM) ATN 910D-C, DC Power, Port Capacity 2*400G/100G+2*100GE+16*25G/10G/GE+8*25G/10G/GE, default all the GE/FE ports is enabled
               virent8090DEVANHMHSTA0800(229699),   -- V8R23C00 for ANHMHSTA0800(SBOM) ATN 910D-C, AC Power, Port Capacity 2*400G/100G+2*100GE+16*25G/10G/GE+8*25G/10G/GE, default all the GE/FE ports is enabled
                --END

               --BEGIN for V8R21C10 NE40E X86 SRU
               virent8090DEVCR5D0SRUAK70(689003),   -- V8R21C10 for CR5D0SRUAK70(SBOM) Switch and Route Processing Unit A112(SRUA-2T-F, 32G Memory)
               virent8090DEVCR5D0SRUAK71(689004),   -- V8R21C10 for CR5D0SRUAK71(SBOM) Switch and Route Processing Unit A112A(SRUA-2TA-F, 32G Memory)
               virent8090DEVCX6D0SRUAK70(689005),   -- V8R21C10 for CX6D0SRUAK70(SBOM) Switch and Route Processing Unit A112(SRUA-2T-F, 32G Memory)
               virent8090DEVTNRD0SRUAK70(689006),   -- V8R21C10 for TNRD0SRUAK70(SBOM) Switch and Route Processing Unit A112(SRUA-2T-F, 32G Memory)
               virent8090DEVIG2D0SRUAK71(689007),   -- V8R21C10 for IG2D0SRUAK71(SBOM) Switch and Route Processing Unit A112A(SRUA-2TA-F, 32G Memory)
               --END

               --BEGIN for V8R21C00 480M 480B
               virent8090DEVCR5DLPUFME72(539127),   -- V8R21C00 for CR5DLPUFME72(SBOM) Flexible Card Line Processing Unit E(LPUF-480-E)
               virent8090DEVCR5DLPUFM376(914342),   -- V8R21C00 for CR5DLPUFM376(SBOM) 24-Port GE-SFP/10GE-SFP+ Flexible Card Line Processing Unit(LPUI-483A-CM, Enable 12*10GE+12*GE by default, Supporting one sub-slot for flexible card)
               virent8090DEVCR5DLPUFM377(948922),    -- V8R21C00 for CR5DLPUFM377(SBOM) 24-Port GE-SFP/10GE-SFP+ Flexible Card Line Processing Unit(LPUI-483-CM, Enable 12*10GE+12*GE by default, Supporting one sub-slot for flexible card)
               --END
			   
               --BEGIN for V8R21C00 NE8000-M8
               virent8090DEVCR8DIPU480C5(112043),   -- V8R21C00 for CR8DIPU480C5(SBOM) Integrated Network Processing Unit (IPU-480-BN)
               --END
               subbname8090DEVCR5D0LBXFM71(225991), --12-Port 10GBase LAN/WAN-SFP+ FlexE/MACsec Flexible Card (P243)
               
			   --BEGIN for V1R21C10 NE8000-X16
               virent8090DEVCR8DSFU14TC0(689000),    -- V1R21C10 for CR8DSFU14TC0(SBOM) NetEngine 8000 X16 14.4Tbps Switch Fabric Unit(SFUI-14T4-C)
               virent8090DEVCR8DSFU14TC1(689001),    -- V1R21C10 for CR8DSFU14TC1(SBOM) NetEngine 8000 X16 14.4Tbps Switch Fabric Unit(SFUIA-14T4-C)
               --END
			   
			   --BEGIN for V1R21C10 NE8000E-X16
			   virent8090DEVCR8DSFU14TC2(689002),    -- V1R21C10 for CR8DSFU14TC2(SBOM) NetEngine 8000E X16 Switch Fabric Unit(SFUIA-C)
			   --END
               
               --BEGIN for V8R21C10 NE8000E M14-Z
               virent8090DEVCR8DIPU1T2Z0(917063),   -- V8R21C10 for CR8DIPU1T2Z0(SBOM) Integrated Network Processing Unit (IPU-1T2-Z)
               --END
               
               --BEGIN for V8R21C10 NE40E X86 5885 480N
               virent8090DEVCR5DLPUFM378(914343),   -- V8R21C10 for CR5DLPUFM378(SBOM) Flexible Card Line Processing Unit(LPUF-485-CM, enable slot 0 by default)
               --END
               
               --BEGIN for V8R21C10 NE8000 M14
               virent8090DEVCR8DIPU800CG(888880),   -- V8R21C10 for CR8DIPU800CG(SBOM) Integrated Network Processing Unit (IPU-800-BN)
               virent8090DEVCR8DIPU800CH(434493),   -- V8R21C10 for CR8DIPU800CH(SBOM) Integrated Network Processing Unit (IPUA-800-BN)
			   virent8090DEVCR8DIPU1T2CE(549612),   -- V8R21C10 for CR8DIPU1T2CE(SBOM) Integrated Network Processing Unit (IPU-1T2-CN)
			   virent8090DEVTNRDIPU1T2C6(256325),   -- V8R21C10 for TNRDIPU1T2C6(SBOM) Integrated Network Processing Unit (IPU-1T2-CN)
               virent8090DEVCR5DIPU1T2CB(412532),   -- V8R21C10 for CR5DIPU1T2CB(SBOM) Integrated Network Processing Unit (IPU-1T2-CN)
			   virent8090DEVME0D0LFXFB71(333415),   -- V8R21C10 for ME0D0LFXFB71(SBOM) 24-Port 10GBase LAN/WAN-SFP+ Broadband Service Unit Integrated(BSUI-245A)
			   virent8090DEVME0D0LFXFA71(368093),   -- V8R21C10 for ME0D0LFXFA71(SBOM) 24-Port 10GBase LAN/WAN-SFP+ Multi Service Unit Integrated(MSUI-245A)
               --END
               
               --BEGIN for V8R21C10 NetEngine 8100 X8
               virent8090DEVCR8DSFUI4TC8(240310),   -- V8R21C10 for CR8DSFUI4TC8(SBOM) NetEngine 8100 X8 4Tbps Switch Fabric Unit(SFUIA-4T-E)
               --END
               
               --BEGIN for V8R21C10 SIG 480N 1966MPU
               virent8090DEVIG2DMPUX8673(710465),   -- V8R21C10 for IG2DMPUX8673(SBOM) Main Processing Unit B11A(32G Memory)
               virent8090DEVIG2D0SRUAI70(131840),   -- V8R21C10 for IG2D0SRUAI70(SBOM) Main Processing Unit A18A(SRUA-1TA-F, 32G Memory)
               virent8090DEVIG2DSFUIT07C(700319),   -- V8R21C10 for IG2DSFUIT07C(SBOM) 1Tbps Switch Fabric Unit M(SFUI-1TA-M)
               virent8090DEVIG2DSFUIT07F(581443),   -- V8R21C10 for IG2DSFUIT07F(SBOM) 1Tbps Switch Fabric Unit M(SFUI-1TA-N)
               virent8090DEVIG2DLPUFM070(581444),   -- V8R21C10 for IG2DLPUFM070(SBOM) Flexible Card Line Processing Unit(LPUF-480)
               virent8090DEVME0DBSUFC871(659391),   -- V8R21C10 for ME0DBSUFC871(SBOM) Flexible Card Broadband Service Unit(BSUF-200A,2 sub-slots)
               virent8090DEVME0DBSUFM075(498559),   -- V8R21C10 for ME0DBSUFM075(SBOM) Flexible Card Broadband Service Unit(BSUF-245,2 sub-slots)
               virent8090DEVME0DMSUFF071(795655),   -- V8R21C10 for ME0DMSUFF071(SBOM) Flexible Card Multi Service Unit(MSUF-245,2 sub-slots)
               virent8090DEVME0DMSUFF072(587637),   -- V8R21C10 for ME0DMSUFF072(SBOM) Flexible Card Multi Service Unit(MSUF-245A,2 sub-slots)
               virent8090DEVCR5DLPUF5271(719830),   -- V8R21C10 for CR5DLPUF5271(SBOM) Flexible Card Line Processing Unit(LPUF-55A,2 sub-slots)
               virent8090DEVCR5DLPUFE07F(769998),   -- V8R21C10 for CR5DLPUFE07F(SBOM) Flexible Card Line Processing Unit(LPUF-200A-E)
               virent8090DEVCR5DLPUFF072(613299),   -- V8R21C10 for CR5DLPUFF072(SBOM) Flexible Card Line Processing Unit(LPUF-245)
               virent8090DEVCR5DLPUFF073(841172),   -- V8R21C10 for CR5DLPUFF073(SBOM) Flexible Card Line Processing Unit(LPUF-245A)
               virent8090DEVCR5DLPUFF07G(878564),   -- V8R21C10 for CR5DLPUFF07G(SBOM) Flexible Card Line Processing Unit(LPUF-245-E)
               virent8090DEVCR5DLPUFF07H(430465),   -- V8R21C10 for CR5DLPUFF07H(SBOM) Flexible Card Line Processing Unit(LPUF-245A-E)
               virent8090DEVCR5DLPUFF379(177565),   -- V8R21C10 for CR5DLPUFF379(SBOM) 10-Port GE-SFP/10GE-SFP+ and 14-Port GE-SFP Flexible Card Line Processing Unit(LPUI-245-CM, 4*10GE+20*GE by default, one sub-slot for flexible card)
               virent8090DEVCR5DLPUFF37K(530105),   -- V8R21C10 for CR5DLPUFF37K(SBOM) 10-Port GE-SFP/10GE-SFP+ and 14-Port GE-SFP Flexible Card Line Processing Unit(LPUI-245A-CM, 4*10GE+20*GE by default, one sub-slot for flexible card)
               virent8090DEVME0DBSUFM077(131436),   -- V8R21C10 for ME0DBSUFM077(SBOM) Flexible Card Broadband Service Unit(BSUF-485,2 sub-slots)
               virent8090DEVME0DBSUFM078(294389),   -- V8R21C10 for ME0DBSUFM078(SBOM) Flexible Card Broadband Service Unit(BSUF-485A,2 sub-slots)
               virent8090DEVME0DMSUFM072(352083),   -- V8R21C10 for ME0DMSUFM072(SBOM) Flexible Card Multi Service Unit(MSUF-485,2 sub-slots)
               virent8090DEVCR5DLPUFM073(499637),   -- V8R21C10 for CR5DLPUFM073(SBOM) Flexible Card Line Processing Unit(LPUF-485)
               virent8090DEVCR5DLPUFM074(815725),   -- V8R21C10 for CR5DLPUFM074(SBOM) Flexible Card Line Processing Unit(LPUF-485A)
               virent8090DEVCR5DLPUFME73(137819),   -- V8R21C10 for CR5DLPUFME73(SBOM) Flexible Card Line Processing Unit E(LPUF-485-E)
               virent8090DEVCR5DLPUFME74(759171),   -- V8R21C10 for CR5DLPUFME74(SBOM) Flexible Card Line Processing Unit E(LPUF-485-E)
               virent8090DEVCR8D0IPU2TC5(285692),   -- V8R21C10 for CR8D0IPU2TC5(SBOM) Integrated Network Processing Unit (IPU-2T-C)
			   virent8090DEVCR8DIPU1T2CJ(285693),   -- V8R21C10 for CR8DIPU1T2CJ(SBOM) Integrated Network Processing Unit (IPU-1T2-C)
               virent8090DEVCR8D0IPU2TC6(867257),   -- V8R21C10 for CR8D0IPU2TC6(SBOM) Integrated Network Processing Unit (IPUA-2T-C)
			   virent8090DEVCR8DIPU1T2CK(867258),   -- V8R21C10 for CR8DIPU1T2CK(SBOM) Integrated Network Processing Unit (IPUA-1T2-C)
               virent8090DEVTNRD0IPU2TC3(469452),   -- V8R21C10 for TNRD0IPU2TC3(SBOM) Integrated Network Processing Unit (IPU-2T-C)
               virent8090DEVCR5D0IPU2TC5(983150),   -- V8R21C10 for CR5D0IPU2TC5(SBOM) Integrated Network Processing Unit (IPU-2T-C)
			   virent8090DEVCR5DIPU1T2C5(983151),   -- V8R21C10 for CR5DIPU1T2C5(SBOM) Integrated Network Processing Unit (IPU-1T2-C)
               virent8090DEVCR8D0IPU2TE1(634699),   -- V8R21C10 for CR8D0IPU2TE1(SBOM) Integrated Network Processing Unit (IPUA-2T-C)
               --END
			   
			   --BEGIN for V8R22C00 PTN
			   virent8090DEVTPRD01CXPB00(340340),   --  for TPRD01CXPB00(SBOM) System Control,Cross-connect and Multi-protocol Process Unit
               virent8090DEVTPRD01CXPB02(454776),   --  for TPRD01CXPB02(SBOM) System Control,Cross-connect and Multi-protocol Process Unit
               virent8090DEVTPQD02CXPB00(607496),   --  for TPQD02CXPB00(SBOM) System Control,Cross-connect and Multi-protocol Process Unit
               virent8090DEVTPQD02CXPB02(843488),   --  for TPQD02CXPB02(SBOM) System Control,Cross-connect and Multi-protocol Process Unit
               virent8090DEVTPND01CXPD00(345510),   --  for TPND01CXPD00(SBOM) System Control,Cross-connect and Multi-protocol Process Unit
               virent8090DEVTPND01CXPD02(520639),   --  for TPND01CXPD02(SBOM) System Control,Cross-connect and Multi-protocol Process Unit
               virent8090DEVTPTD01CXPB01(981763),   --  for TPTD01CXPB01(SBOM) System Control,Cross-connect and Multi-protocol Process Unit
               virent8090DEVTPSM1HOSTA0(823614),   --  for TPSM1HOSTA0(SBOM) PTN 916-F - DC Power,with 4*10GE(o),16*GE/FE(o),4*GE/FE(e) 
               virent8090DEVTPSM1HOSTB0(912192),   --  for TPSM1HOSTB0(SBOM) PTN 916-F - AC Power,with 4*10GE(o),16*GE/FE(o),4*GE/FE(e) 
               virent8090DEVTPSM1HOSTA1(707597),   --  for TPSM1HOSTA1(SBOM) PTN 916-F - DC Power,with 4*10GE(o),16*GE/FE(o),4*GE/FE(e) 
               virent8090DEVTPSM1HOSTB1(436296),   --  for TPSM1HOSTB1(SBOM) PTN 916-F - AC Power,with 4*10GE(o),16*GE/FE(o),4*GE/FE(e) 
               virent8090DEVTPSM1HOSTC0(232607),   --  for TPSM1HOSTC0(SBOM) PTN 916-F - DC Power,with 4*10GE(o,RTU control,default rate is 100 Mbit/s),16*GE/FE(o),4*GE/FE(e) 
               virent8090DEVTPSM1HOSTD0(204144),   --  for TPSM1HOSTD0(SBOM) PTN 916-F - AC Power,with 4*10GE(o,RTU control,default rate is 100 Mbit/s),16*GE/FE(o),4*GE/FE(e)
			   --END
			   
               --BEGIN for V8R21C10 VSU NE40E ME60 SIG9800 NE9000
			   virent8090DEVCR5DVSUIK07D(962214),   -- V8R21C10 for CR5DVSUIK07D(SBOM) Integrated Service Unit 401(VSUI-401A-E)
               virent8090DEVCR5DVSUIK07C(580249),   -- V8R21C10 for CR5DVSUIK07C(SBOM) Integrated Service Unit 401(VSUI-401-E)
			   virent8090DEVCR5DVSUIK07B(509102),   -- V8R21C10 for CR5DVSUIK07B(SBOM) Integrated Service Unit 401(VSUI-401A)
               virent8090DEVCR5DVSUIK07A(927310),   -- V8R21C10 for CR5DVSUIK07A(SBOM) Integrated Service Unit 401(VSUI-401)
			   virent8090DEVME0DVSUIK07A(117254),   -- V8R21C10 for ME0DVSUIK07A(SBOM) Integrated Service Unit 401(VSUI-401A)
			   virent8090DEVIG2D00SPUG0C(125719),   -- V8R21C10 for IG2D00SPUG0C(SBOM) High Performance X8A&X16A Service Processing Unit-SPUGA-S,with HW Service Inspection Gateway Software
               virent8090DEVIG2D00SPUG0D(176245),   -- V8R21C10 for IG2D00SPUG0D(SBOM) High Performance X8A&X16A Enhanced Service Processing Unit-SPUGEA-S,with HW Service Inspection Gateway Software
			   virent8090DEVCR9D0SFUT480(570049),   -- V8R21C10 for CR9D0SFUT480(SBOM) NE9000-20 Switch Fabric Unit for Single Chassis(SFU4T-B)
			   virent8090DEVCR9D0SFUT280(564907),   -- V8R21C10 for CR9D0SFUT280(SBOM) NE9000-8 Switch Fabric Unit for Single Chassis(SFU2T-A)
			   --END

               --BEGIN for V8R21C10 B11 NE40E ME60 OC-CX600 CH-CX6000 OC-PTN6900
               virent8090DEVCR5DMPUX8674(782504),   -- V8R21C10 for CR5DMPUX8674(SBOM) Main Processing Unit B112(32G Memory)
               virent8090DEVCX6DMPUX8673(908549),   -- V8R21C10 for CX6DMPUX8673(SBOM) Main Processing Unit B112(32G Memory)
               virent8090DEVCX6DMPUX8614(602552),   -- V8R21C10 for CX6DMPUX8614(SBOM) Main Processing Unit B112A(32G Memory)
               virent8090DEVTNRDMPUX8673(429158),   -- V8R21C10 for TNRDMPUX8673(SBOM) Main Processing Unit B112(32G Memory)
               virent8090DEVME0DMPUX8674(640056),   -- V8R21C10 for ME0DMPUX8674(SBOM) Main Processing Unit B112(32G Memory)
               virent8090DEVME0DMPUX8675(898252),   -- V8R21C10 for ME0DMPUX8675(SBOM) Main Processing Unit B112A(32G Memory)
			   virent8090DEVCR5DMPUX8675(898253),   -- V8R21C10 for CR5DMPUX8675(SBOM) Main Processing Unit B112A(32G Memory)
              --END
			   
               --BEGIN for V8R21C10 A821 A821E
               virent8090DEVCP8PHST20A02(525128),   -- V8R21C10 for CP8PHST20A02(SBOM) NetEngine A821, CP8PHST20A02, NetEngine A821 AC System (6*10GE/GE/FE+4*GE/FE(o), 8*GE/FE(e), Default 2*10GE/GE/FE+8*GE/FE(o)+8*GE/FE(e))
               virent8090DEVCP8PHST20A04(525129),   -- V8R21C10 for CP8PHST20A04(SBOM) NetEngine A821, CP8PHST20A04, NetEngine A821 AC System (2*10GE/GE/FE+8*GE/FE(o)+8*GE/FE(e))
               virent8090DEVCP8PHST2EA00(439707),   -- V8R21C10 for CP8PHST2EA00(SBOM) NetEngine A821 E, CP8PHST2EA00, NetEngine A821 E AC Chassis(A) (6*10GE/GE/FE+4*GE/FE(o), 8*GE/FE(e), Default 2*10GE/GE/FE(o)+8*GE/FE(o)+8*GE/FE(e))
               virent8090DEVCP8PHST2EA01(856064),   -- V8R21C10 for CP8PHST2EA01(SBOM) NetEngine A821 E, CP8PHST2EA01, NetEngine A821 E AC Chassis (6*10GE/GE/FE+4*GE/FE(o), 8*GE/FE(e), Default 2*10GE/GE/FE(o)+8*GE/FE(o)+8*GE/FE(e))
               virent8090DEVCP8PHST10A08(525130),   -- V8R22C00 for CP8PHST10A08(SBOM) NetEngine A813, CP8PHST10A08, NetEngine A813 AC System (6*GE/FE(o)+8*GE/FE(e))
               virent8090DEVCP8PHST1EA07(525131),   -- V8R22C00 for CP8PHST1EA07(SBOM) NetEngine A813 E, CP8PHST1EA07, NetEngine A813 E AC Chassis (6*GE/FE(o)+8*GE/FE(e))
               virent8090DEVCP8PHST1EAA6(525132),   -- V8R22C00 for CP8PHST1EAA6(SBOM) NetEngine A813 E, CP8PHST1EAA6, NetEngine A813 E AC Chassis (6*GE/FE(o)+8*GE/FE(e))
               virent8090DEVANPM01HOST5(525133),    -- V8R22C00 for ANPM01HOST5(SBOM)  ATN 905, ANPM01HOST5, ATN 905-S System,AC,4*GE/FE(o),4*GE/FE(e)
               virent8090DEVANPM01HOST6(525134),    -- V8R22C00 for ANPM01HOST6(SBOM)  ATN 905, ANPM01HOST6, ATN 905-S System,AC,4*GE/FE(o),4*GE/FE(e)
               virent8090DEVCP8PHST2EA21(525135),   -- V8R22C00 for CP8PHST2EA21(SBOM) NetEngine A822 E, CP8PHST2EA21, NetEngine A822 E AC Chassis(A)(2*10GE/GE/FE(o)+4*GE/FE(o)+8*GE/FE(e))
               virent8090DEVCP8PHST2EA22(525136),   -- V8R22C00 for CP8PHST2EA22(SBOM) NetEngine A822 E, CP8PHST2EA22, NetEngine A822 E AC Chassis (2*10GE/GE/FE(o)+4*GE/FE(o)+8*GE/FE(e))
               virent8090DEVCR8P8KHALMC7(689243),   -- V8R22C00 for CR8P8KHALMC7(SBOM) 20-Port 100GBase-QSFP28 Integrated Line Processing Unit CM(LPUI-2T-CM)
               virent8090DEVCR8DEANCJXCB(539206),   -- V8R22C00 for CR8DEANCJXCB(SBOM) 10-Port 100GBase-QSFP28 + 36-Port 25GE(SFP28)/10GE(SFP+)/GE(SFP) Integrated Line Processing Unit CM(LPUI-2T-CM)
               virent8090DEVGPLI36YS10CQE3(539207), -- V8R25C00 for CR8DEANEWAD0 10-Port 100GBase-QSFP28 + 36-Port 10GE(SFP+)/GE(SFP).
               virent8090DEVCP8PHST2EA10(525137),   -- V8R22C00 for CP8PHST2EA10(SBOM) NetEngine A831 E, CP8PHST2EA10, NetEngine A831 E AC Chassis(A) (3*10G/GE/FE(o)+7*GE/FE(o)+4*GE/FE(e))
               virent8090DEVCP8PHST2EA15(525145),   -- V8R24C00 for CP8PHST2EA15(SBOM) NetEngine A831 E DC Chassis(3*10G/GE/FE(o)+7*GE/FE(o)+4*GE/FE(e))
               virent8090DEVISR801BASAX1(525144),   -- V8R22C00 for ISR801BASAX1(SBOM) Mining intrinsic safety 10GE router KJJ12, NetEngine A831 E(3*10G/GE/FE(o)+7*GE/FE(o)+4*GE/FE(e))
               virent8090DEVCP8P15HALA02(525146),   -- V8R22C00 for CP8P15HALA02(SBOM) NetEngine A815 T, CP8P15HALA02, NetEngine A815 T AC System (4*GE(o)+4*GE/FE(e))
               virent8090DEVCP8P25HALD02(525147),   -- V8R22C00 for CP8P25HALD02(SBOM) NetEngine A825 T, CP8P25HALD02, NetEngine A825 T DC System(16*10GE/GE/FE(o)+12*GE/FE(o)+4*GE/FE(e), Default 2*10GE+8*GE)
               virent8090DEVCP8P25HALA02(525148),   -- V8R22C00 for CP8P25HALA02(SBOM) NetEngine A825 T, CP8P25HALA02, NetEngine A825 T AC System(16*10GE/GE/FE(o)+12*GE/FE(o)+4*GE/FE(e), Default 2*10GE+8*GE)
               virent8090DEVCP8DCXP16001(525149),   -- V8R22C00 for CP8DCXP16001(SBOM) NetEngine A835 T, CP8DCXP16001, System Control,Cross-connect and Multi-protocol Process Unit (CXPA-160)
               virent8090DEVANHMHSTA0600(525138),   -- V8R22C00 for ANHMHSTA0600(SBOM) ATN 910D-B, AC Power, Port Capacity 2*50GE(convertible into 10*10GE)+2*25GE(convertible into 4*10GE/GE)+2*10GE/GE+10*GE(o)+4*GE(e), default 2*25GE ports and all the GE/FE ports are enabled
               virent8090DEVANHMHSTA0500(525139),   -- V8R22C00 for ANHMHSTA0500(SBOM) ATN 910D-B, DC Power, Port Capacity 2*50GE(convertible into 10*10GE)+2*25GE(convertible into 4*10GE/GE)+2*10GE/GE+10*GE(o)+4*GE(e), default 2*25GE ports and all the GE/FE ports are enabled
               virent8090DEVCR8PM1DBASCJ(525140),   -- V8R22C00 for CR8PM1DBASCJ(SBOM) NetEngine 8000 M1D-B, AC Power (Port Capacity 2*50GE(convertible into 10*10GE)+2*25GE(convertible into 4*10GE/GE)+2*10GE/GE+10*GE(0)+4*GE(e), default 2*25GE ports and all the GE/FE ports are enabled,exclude auxiliary materials)
               virent8090DEVCR8PM1DBASCK(525141),   -- V8R22C00 for CR8PM1DBASCK(SBOM) NetEngine 8000 M1D-B, AC Power (Port Capacity 2*50GE(convertible into 10*10GE)+2*25GE(convertible into 4*10GE/GE)+2*10GE/GE+10*GE(0)+4*GE(e), default 2*25GE ports and all the GE/FE ports are enabled,exclude auxiliary materials)
               virent8090DEVCR8PM1DBASCF(525142),   -- V8R22C00 for CR8PM1DBASCF(SBOM) NetEngine 8000 M1D-B, DC Power (Port Capacity 2*50GE(convertible into 10*10GE)+2*25GE(convertible into 4*10GE/GE)+2*10GE/GE+10*GE(0)+4*GE(e), default 2*25GE ports and all the GE/FE ports are enabled,exclude auxiliary materials)
               virent8090DEVCR8PM1DBASCH(525143),   -- V8R22C00 for CR8PM1DBASCH(SBOM) NetEngine 8000 M1D-B, DC Power (Port Capacity 2*50GE(convertible into 10*10GE)+2*25GE(convertible into 4*10GE/GE)+2*10GE/GE+10*GE(0)+4*GE(e), default 2*25GE ports and all the GE/FE ports are enabled,exclude auxiliary materials)
               virent8090DEVCR8DSFUI2TC1(676895),   -- V8R23C00 for CR8DSFUI2TC1(SBOM) NetEngine 8000 X16 14.4Tbps Switch Fabric Unit(SFUI-2T-C)
               virent8090DEVCR8DSFUI2TC2(676896),   -- V8R23C00 for CR8DSFUI2TC2(SBOM) NetEngine 8000 X16 2Tbps Switch Fabric Unit(SFUIA-2T-C)
               virent8090DEVCR8D00LRXFC5(120022),   -- V8R22C00 for CR8D00LRXFC5(SBOM) 72-Port 25GE(SFP28)/10GE(SFP+)/GE(SFP) Integrated Line Processing Unit CM(LPUI-2TA-CM)
               virent8090DEVCR8DE4KEFNC0(629166),   -- V8R22C00 for CR8DE4KEFNC0(SBOM) 4-Port 400GBase-QSFP-DD + 24-Port 100GBase-QSFP28 Integrated Line Processing Unit CM (LPUI-4T-CM)
               virent8090DEVCR8DE4KFBNC2(629167),   --  for CR8DE4KFBNC2(SBOM) 4-Port 400GBase-QSFP-DD + 24-Port 100GBase-QSFP28 Integrated Line Processing Unit CM (LPUI-4T-L-CM)
			   virent8090DEVCR5DLPUFM392(688683),   -- V8R22C00 for CR5DLPUFM392(SBOM) Flexible Card Line Processing Unit(LPUF-483A, Supportting DIP)
               virent8090DEVCR5DLPUFM393(688684),   -- V8R22C00 for CR5DLPUFM393(SBOM) Flexible Card Line Processing Unit(LPUF-483A, Supportting DIP)
			   virent8090DEVCR5D0MPUB977(398204),   -- V8R22C00 for CR5D0MPUB977(SBOM) Main Processing Unit B12A(32G Memory)
               virent8090DEVCR5D0MPUB976(168741),   -- V8R22C00 for CR5D0MPUB976(SBOM) Main Processing Unit B12(32G Memory)
			   virent8090DEVCX6DMPUB1215(429159),   -- V8R22C00 for CX6DMPUB1215(SBOM) Main Processing Unit B112(32G Memory)
               virent8090DEVME0DMPUX8677(817646),   -- V8R22C00 for ME0DMPUX8677(SBOM) Main Processing Unit B12A(32G Memory)
               virent8090DEVME0DMPUX8676(816731),   -- V8R22C00 for ME0DMPUX8676(SBOM) Main Processing Unit B12(32G Memory)
               virent8090DEVCX6DMPUX8674(768006),   -- V8R22C00 for CX6DMPUX8674(SBOM) Main Processing Unit B12(32G Memory)
               virent8090DEVTNRDMPUX8674(754372),   -- V8R22C00 for TNRDMPUX8674(SBOM) Main Processing Unit B12(32G Memory)
               virent8090DEVIG2D0MPUB977(997356),   -- V8R22C00 for IG2D0MPUB977(SBOM) Main Processing Unit B12A(32G Memory)
               virent8090DEVCP8PHST3A00(284791),   -- V8R24C00 for CP8PHST3A00(SBOM) NetEngine XH821 AC Chassis(A) ((2*10GE/GE/FE(o)+4*GE(o)(default 4*GE,RTU can be upgrade to 4*10GE)+4*GE/FE(o)+8*GE/FE(e)
               virent8090DEVCP8PHST3EA00(284792),   -- V8R24C00 for CP8PHST3EA00(SBOM) NetEngine XH821 E AC Chassis(A) (6*10GE/GE/FE(o)+4*GE/FE(o)+8*GE/FE(e), Default 2*10GE/GE/FE(o)+8*GE/FE(o)+8*GE/FE(e))
               virent8090DEVCR5DLPUFF376(688992),   -- V8R21C12 for CR5DLPUFF376(SBOM) Flexible Card Line Processing Unit(LPUF-243A)
               virent8090DEVCR5DLPUFM379(688993),   -- V8R21C12 for CR5DLPUFM379(SBOM) 48-Port 10GBase LAN/WAN-SFP+ Integrated Line Processing Unit L(LPUI-483-L)
               --END
               
               --BEGIN for V800R021C10 3.2T coll
               virent8090DEVCR8D00EINBC1(564886),   -- V8R21C10 for CR8D00EINBC1(SBOM) 32-Port 100GBase-QSFP28 Integrated Line Processing Unit CM(LPUI-3T2A-CM)
               --END

               --BEGIN for V8R24C10
               virent8090DEVCR5D00E4LB61(562302),   -- V8R24C10 for CR5D00E4LB61(SBOM) 4-Port 800GBase QSFP-DD Integrated Line Process Unit(NE5000E LPUI-3T2-E)
               --END
			   
               --BEGIN for V8R25C00
               virent8090DEVCR5DSFUIT462(562303),   -- V8R25C00 for CR5DSFUIT462(SBOM) NE5000E-20 8T CLC Integrated Switch Fabric Unit for Multi-Chassis(SFUI-8T-M)
               virent8090DEVCR5DSFUIT463(562305),   -- V8R25C00 for CR5DSFUIT463(SBOM) NE5000E CCC-A 8T Cluster Central Switch Fabric Unit (SFUI-8T-C)
               --END
        
               --BEGIN for V8R25C00
               virent8090DEVCR5D00TPU060(562304),   -- V8R25C00 for CR5D00TPU060(SBOM) NetEngine5000E Threat Protection Unit(NE5000E TPUI-A)
               --END

                --BEGIN for V8R25C10
                virent8090DEVCR5D00EMNBC4(562151),    -- V8R25C10 for CR5D00EMNBC4(SBOM) 48-Port 100GBase QSFP28 Integrated Line Process Unit CM(NE5000E LPUI-8T-CM)
                virent8090DEVCR5D00EEKBC4(562152),    -- V8R25C10 for CR5D00EEKBC4(SBOM) 20-Port 400GBase QSFP-DD Integrated Line Process Unit CM(NE5000E LPUI-8T-CM)
                virent8090DEVCR5D00EDNB70(562308),    -- V8R25C10 for CR5D00EDNB70(SBOM) 16-Port 100GBase QSFP28 Integrated Line Process Unit(NE5000E LPUI-1T6-M)
                virent8090DEVCR5D00EDNB71(562309),    -- V8R25C10 for CR5D00EDNB71(SBOM) 16-Port 100GBase QSFP28 Integrated Line Process Unit CM(NE5000E LPUI-1T6-M-CM)(4 ports enable)
                virent8090DEVCR5D000CMU64(676000),    -- V8R25C10 for CR5D000CMU64(SBOM) Centralized Monitoring Module D
                --END

               virent8090DEVCR5DLPUFF07F(675265),   -- V8R21C10 for CR5DLPUFF07F(SBOM) Flexible Card Line Processing Unit(LPUF-240A-E)
               virent8090DEVCX6DISUFF011(157329),   -- V8R21C10 for CX6DISUFF011(SBOM) Flexible Card Integrated Service Unit(ISUF-240A)
               virent8090DEVME0DBSUF5270(133753),   -- V8R21C10 for ME0DBSUF5270(SBOM) Flexible Card Broadband Service Unit(BSUF-55A,2 sub-slots)
               virent8090DEVCR8DIPU480C8(107344),   -- V8R21C10 for CR8DIPU480C8(SBOM) Integrated Network Processing Unit (IPUA-480-BN)
               virent8090DEVCR8DIPU800CJ(203627),   -- V8R21C10 for CR8DIPU800CJ(SBOM) Integrated Network Processing Unit (IPUA-800-BN)
               virent8090DEVME0DBSUFM076(385871),   -- V8R21C10 for ME0DBSUFM076(SBOM) Flexible Card Broadband Service Unit(BSUF-480A,2 sub-slots)
               virent8090DEVME0DBSUFK072(682199),   -- V8R21C10 for ME0DBSUFK072(SBOM) Flexible Card Broadband Service Unit(BSUF-400A,2 sub-slots)
			   virent8090DEVCR8DEANCJXCD(468753),   -- V8R22C00 for CR8DEANCJXCD(SBOM) 10-Port 100GBase-QSFP28 + 36-Port 25GE(SFP28)/10GE(SFP+)/GE(SFP) Integrated Line Processing Unit CM(LPUI-2TA-CM)
               virent8090DEVCR8DEANCJXCE(468754),   -- V8R22C00 for CR8DEANCJXCE(SBOM) 10-Port 100GBase-QSFP28 + 36-Port 25GE(SFP28)/10GE(SFP+)/GE(SFP) Integrated Line Processing Unit L CM(LPUI-2TA-L-CM)
               virent8090DEVCR8DEANCJXCC(468755),   -- V8R22C00 for CR8DEANCJXCC(SBOM) 10-Port 100GBase-QSFP28 + 36-Port 25GE(SFP28)/10GE(SFP+)/GE(SFP) Integrated Line Processing Unit L CM(LPUI-2T-L-CM)
               virent8090DEVCR8DSSUFT4CS(468756),   -- V8R22C00 for CR8DSSUFT4CS(SBOM) 32-Port 100GBase-QSFP28 FlexE Integrated Line Processing Unit CM (LPUI-3T2-CM)
               virent8090DEVCR8DSSUFT4CP(468757),   -- V8R22C00 for CR8DSSUFT4CP(SBOM) 32-Port 100GBase-QSFP28 FlexE Integrated Line Processing Unit CM (LPUI-3T2A-CM)
               virent8090DEVCR8DSSUFT4CU(468758),   -- V8R22C00 for CR8DSSUFT4CU(SBOM) 32-Port 100GBase-QSFP28 FlexE Integrated Line Processing Unit L CM (LPUI-3T2A-L-CM)
               virent8090DEVCR8DSSUFT4CW(468759),   -- V8R22C00 for CR8DSSUFT4CW(SBOM) 32-Port 100GBase-QSFP28 FlexE Integrated Line Processing Unit L CM (LPUI-3T2-L-CM)
               virent8090DEVCR8DE4KEFNC1(468760),   -- V8R22C00 for CR8DE4KEFNC1(SBOM) 4-Port 400GBase-QSFP-DD + 24-Port 100GBase-QSFP28 Integrated Line Processing Unit CM (LPUIA-4T-CM)
               virent8090DEVCR8DIPU480C9(468763),   -- V8R22C00 for CR8DIPU480C9(SBOM) Integrated Network Processing Unit (IPUA-480-C)
               virent8090DEVCR8DIPU1T2E2(468767),   -- V8R22C00 for CR8DIPU1T2E2(SBOM) Integrated Network Processing Unit (IPUA-480-C)
               virent8090DEVCR8DIPU480E1(468768),   -- V8R22C00 for CR8DIPU480E1(SBOM) Integrated Network Processing Unit (IPUA-1T2-C)
               virent8090DEVCR8DIPU1T2CF(468769),   -- V8R22C00 for CR8DIPU1T2CF(SBOM) Integrated Network Processing Unit (IPUA-1T2-CN)
               virent8090DEVCR8DIPU1T2E1(468773),   -- V8R22C00 for CR8DIPU1T2E1(SBOM) Integrated Network Processing Unit (IPUA-1T2-CN)
               virent8090DEVCR8DIPU1T2M1(468779),   -- V8R22C00 for CR8DIPU1T2M1(SBOM) Integrated Network Processing Unit (IPUA-1T2-D)
               virent8090DEVCR8DIPU480M0(468780),   -- V8R22C00 for CR8DIPU480M0(SBOM) Integrated Network Processing Unit (IPUA-480-D)
               virent8090DEVCR8DIPU1T2CL(468781),   -- V8R22C00 for CR8DIPU1T2CL(SBOM) Integrated Network Processing Unit (IPU-1T2-D)
               virent8090DEVCR8DIPU480CA(468782),   -- V8R22C00 for CR8DIPU480CA(SBOM) Integrated Network Processing Unit (IPU-480-D)
               virent8090DEVCR8DIPU1T2M0(468783),   -- V8R22C00 for CR8DIPU1T2M0(SBOM) Integrated Network Processing Unit (IPUA-1T2-D)
               virent8090DEVCR8DIPU1T2CN(468784),   -- V8R22C00 for CR8DIPU1T2CN(SBOM) Integrated Network Processing Unit (IPU-1T2-D)
               virent8090DEVCR8DIPU1T2CU(468785),   -- V8R22C00 for CR8DIPU1T2CU(SBOM) Integrated Network Processing Unit (IPU-1T2-D)
               virent8090DEVCR8DE4KFBNC1(468775),   -- V8R22C00 for CR8DE4KFBNC1(SBOM) Integrated Line Processing Unit CM (LPUI-4TA-L-CM)
               virent8090DEVCR8DEANEJXDM(634588),   -- V8R22C10 for CR8DEANEJXDM(SBOM) 10-Port 100GBase-QSFP28 MACsec + 36-Port 10GE(SFP+)/GE(SFP) MACsec Integrated Line Processing Unit CM(LPUI-1T-CM)
               virent8090DEVCR8DEANEJXD1(979962),   -- V8R22C10 for CR8DEANEJXD1(SBOM) 10-Port 100GBase-QSFP28 + 36-Port 10GE(SFP+)/GE(SFP) Integrated Line Processing Unit CM(LPUI-1T-CM)
               virent8090DEVCR8DEANEJXD2(709131),   -- V8R22C10 for CR8DEANEJXD2(SBOM) 10-Port 100GBase-QSFP28 + 36-Port 10GE(SFP+)/GE(SFP) Integrated Line Processing Unit CM(LPUI-1TA-CM)
               virent8090DEVCR8DEANEJXDN(315861),   -- V8R22C10 for CR8DEANEJXDN(SBOM) 10-Port 100GBase-QSFP28 MACsec + 36-Port 10GE(SFP+)/GE(SFP) MACsec Integrated Line Processing Unit CM(LPUI-1TA-CM)
               virent8090DEVCR5DVSUIK07E(954290),   -- V8R22C00 for CR5DVSUIK07E(SBOM) Enhanced Data Redundancy Elimination Integrated Service Unit 400(VSUI-400-E)
               virent8090DEVCR5DVSUIK07F(158967),   -- V8R22C00 for CR5DVSUIK07F(SBOM) Enhanced Data Redundancy Elimination Integrated Service Unit 400(VSUI-400A-E)
               virent8090DEVCR5DVSUIK07G(185740),   -- V8R22C00 for CR5DVSUIK07G(SBOM) Data Redundancy Elimination Integrated Service Unit 400(VSUI-400-S)
               virent8090DEVCR5DVSUIK07H(544950),   -- V8R22C00 for CR5DVSUIK07H(SBOM) Data Redundancy Elimination Integrated Service Unit 400(VSUI-400A-S)
               virent8090DEVCR8PM1ABAS0(689484),    -- V8R22C00 for CR8PM1ABAS0(SBOM) NetEngine 8000,CR8PM1ABAS0,NetEngine 8000 M1A, AC Power,Port Capacity 16*10GE+12*GE(o)+4*GE(e)
               virent8090DEVCR8PM1ABAS1(689485),    -- V8R22C00 for CR8PM1ABAS1(SBOM) NetEngine 8000,CR8PM1ABAS1,NetEngine 8000 M1A, AC Power,Port Capacity 16*10GE+12*GE(o)+4*GE(e)
               virent8090DEVCR8PM1ABAS2(689486),    -- V8R22C00 for CR8PM1ABAS2(SBOM) NetEngine 8000,CR8PM1ABAS2,NetEngine 8000 M1A, DC Power,Port Capacity 16*10GE+12*GE(o)+4*GE(e)
			   virent8090DEVCR5DSFUIT27S(112979),   -- V8R21C12 for CR5DSFUIT27S(SBOM) 2Tbps Switch Fabric Unit I(SFUI-2TA-I)
               virent8090DEVCR5DSFUITD74(700991),   -- V8R21C12 for CR5DSFUITD74(SBOM) 2Tbps Switch Fabric Unit J(SFUI-2TA-J)
               virent8090DEVME0DSFUIM07N(370522),   -- V8R21C12 for ME0DSFUIM07N(SBOM) 480Gbps Switch Fabric Unit N(SFUI-480A-M)
               virent8090DEVME0DSFUIM07M(487111),   -- V8R21C12 for ME0DSFUIM07M(SBOM) 480Gbps Switch Fabric Unit N(SFUI-480-M)
			   virent8090DEVME0D0SRUAH74(688990),   -- V8R21C12 for ME0D0SRUAH74(SBOM) Switch and Route Processing Unit A20A(SRUA-480A-G, 32G Memory)
               virent8090DEVME0D0SRUAH75(688991),   -- V8R21C12 for ME0D0SRUAH75(SBOM) Switch and Route Processing Unit A20(SRUA-480-G, 32G Memory)
			   virent8090DEVCR8PM1DBADC1(912355),   -- V8R21C12 for CR8PM1DBADC1(SBOM) NetEngine 8000 M1D, DC Power (Port Capacity 4*100GE/50GE+16*25GE/10GE/GE/FE+8*10GE/GE/FE,exclude auxiliary materials)
			   virent8090DEVCR8PM1DBADC3(341533),   -- V8R21C12 for CR8PM1DBADC3(SBOM) NetEngine 8000 M1D, DC Power (Port Capacity 4*100GE/50GE+16*25GE/10GE/GE/FE+8*10GE/GE/FE,exclude auxiliary materials)
			   virent8090DEVCR8PM1DBAACD(704146),   -- V8R21C12 for CR8PM1DBAACD(SBOM) NetEngine 8000 M1D, AC Power (Port Capacity 4*100GE/50GE+16*25GE/10GE/GE/FE+8*10GE/GE/FE,exclude auxiliary materials)
			   virent8090DEVCR8PM1DBAACE(225775),   -- V8R21C12 for CR8PM1DBAACE(SBOM) NetEngine 8000 M1D, AC Power (Port Capacity 4*100GE/50GE+16*25GE/10GE/GE/FE+8*10GE/GE/FE,exclude auxiliary materials)
			   virent8090DEVCR9D00EKNB83(624060),   -- V8R21C10 for CR9D00EKNB83(SBOM) 40-Port 100GE/50GE-QSFP28 Integrated Line Process Unit(LPUI-4TA)
			   virent8090DEVCR9DE8KE8N8X(613774),   -- V8R21C10 for CR9DE8KE8N8X(SBOM) 8-Port 400GE-QSFP-DD + 8-Port 100GE-QSFP28 Integrated Line Process Unit(LPUI-4TA)
			   virent8090DEVCR9D00EKNB8V(355341),   -- V8R21C10 for CR9D00EKNB8V(SBOM) 40-Port 100GE/50GE-QSFP28 Integrated Line Process Unit CM(LPUI-4T-CM)
			   virent8090DEVCR9D00EKNB8Y(359774),   -- V8R21C10 for CR9D00EKNB8Y(SBOM) 40-Port 100GE/50GE-QSFP28 Integrated Line Process Unit L(LPUI-4T-L)
			   virent8090DEVCR9DE8KE8N8Z(949736),   -- V8R21C10 for CR9DE8KE8N8Z(SBOM) 8-Port 400GE-QSFP-DD + 8-Port 100GE-QSFP28 Integrated Line Process Unit CM(LPUI-4T-CM, 8*100G RTU Enabled by default)
			   virent8090DEVCR9D00EENB88(309227),   -- V8R21C10 for CR9D00EENB88(SBOM) 20-Port 100GE/50GE-QSFP28 Integrated Line Process Unit CM(LPUI-2T-CM)
			   virent8090DEVCR9D00EKNB87(102386),   -- V8R21C10 for CR9D00EKNB87(SBOM) 20-Port 100GE/50GE-QSFP28 Integrated Line Process Unit L(LPUI-2T-L)
			   virent8090DEVCR9P9KHALM8F(536293),    -- V8R21C10 for CR9P9KHALM8F(SBOM) 20-Port 100GE/50GE-QSFP28 Integrated Line Process Unit (LPUI-2TA)
               virent8090DEVCR8DEKNBFED1(520102),   -- V8R22C10 for CR8DEKNBFED1(SBOM) 40-Port 100GBase-QSFP28 Integrated Line Processing Unit CM(LPUI-4T-E-CM)
               virent8090DEVCR8DE4KEFND1(350519),   -- V8R22C10 for CR8DE4KEFND1(SBOM) 4-Port 400GBase-QSFP-DD + 24-Port 100GBase-QSFP28 Integrated Line Processing Unit CM (LPUI-4T-E-CM)
               virent8090DEVCR8DEKNBFED2(472559),   -- V8R22C10 for CR8DEKNBFED2(SBOM) 40-Port 100GBase-QSFP28 Integrated Line Processing Unit CM(LPUI-4TA-E-CM)
               virent8090DEVCR8DE4KEFND2(468790),   -- V8R22C10 for CR8DE4KEFND2(SBOM) 4-Port 400GBase-QSFP-DD + 24-Port 100GBase-QSFP28 Integrated Line Processing Unit CM (LPUI-4TA-E-CM)
               virent8090DEVCR8DERYBFED1(796564),   -- V8R22C10 for CR8DERYBFED1(SBOM) 72-Port 25GE(SFP28)/10GE(SFP+)/GE(SFP) Integrated Line Processing Unit CM(LPUI-2T-E-CM)
               virent8090DEVCR8DEENBFED1(229061),   -- V8R22C10 for CR8DEENBFED1(SBOM) 20-Port 100GBase-QSFP28 Integrated Line Processing Unit CM(LPUI-2T-E-CM)
               virent8090DEVCR8DEANEJYD1(855770),   -- V8R22C10 for CR8DEANEJYD1(SBOM) 10-Port 100GBase-QSFP28 + 36-Port 25GE(SFP28)/10GE(SFP+)/GE(SFP) Integrated Line Processing Unit CM(LPUI-2T-E-CM)
               virent8090DEVCR8DERYBFED2(175385),   -- V8R22C10 for CR8DERYBFED2(SBOM) 72-Port 25GE(SFP28)/10GE(SFP+)/GE(SFP) Integrated Line Processing Unit CM(LPUI-2TA-E-CM)
               virent8090DEVCR8DEENBFED2(548567),   -- V8R22C10 for CR8DEENBFED2(SBOM) 20-Port 100GBase-QSFP28 Integrated Line Processing Unit CM(LPUI-2TA-E-CM)
               virent8090DEVCR8DEANEJYD2(468791),   -- V8R22C10 for CR8DEANEJYD2(SBOM) 10-Port 100GBase-QSFP28 + 36-Port 25GE(SFP28)/10GE(SFP+)/GE(SFP) Integrated Line Processing Unit CM(LPUI-2TA-E-CM)
               virent8090DEVCR8DE8KE8ND1(463229),   -- V8R22C10 for CR8DE8KE8ND1(SBOM) 8-Port 400GBase-QSFP-DD + 8-Port 100GBase-QSFP28 Integrated Line Processing Unit CM(LPUI-4T-E-CM,Enable 16*100GE by default)
               virent8090DEVCR8DE8KE8ND2(588800),   -- V8R22C10 for CR8DE8KE8ND2(SBOM) 8-Port 400GBase-QSFP-DD + 8-Port 100GBase-QSFP28 Integrated Line Processing Unit CM(LPUI-4TA-E-CM,Enable 16*100GE by default)
               virent8090DEVCR5DLPUFT07F(130553),   -- V8R22C10 for CR5DLPUFT07F(SBOM) Flexible Card Line Processing Unit(LPUF-1T2A-E)
               virent8090DEVCR5DLPUFT07E(830576),   -- V8R22C10 for CR5DLPUFT07E(SBOM) Flexible Card Line Processing Unit(LPUF-1T2-E)
               virent8090DEVCR5D00EENB7E(843286),   -- V8R22C10 for CR5D00EENB7E(SBOM) 20-Port 100GBase-QSFP28 Integrated Line Processing Unit (LPUI-2TA-E)
               virent8090DEVCR5D00EENB7S(608128),   -- V8R22C10 for CR5D00EENB7S(SBOM) 20-Port 100GBase-QSFP28 FlexE/MACsec Integrated Line Processing Unit CM(LPUI-2T-E-CM)
               virent8090DEVME0DBSUFT07A(493005),   -- V8R22C10 for ME0DBSUFT07A(SBOM) Integrated Broadband Service Unit(BSUI-2T-CM)
               virent8090DEVME0DBSUFT07C(493006),   -- V8R22C10 for ME0DBSUFT07C(SBOM) Flexible Card Broadband Service Unit(BSUF-1T2A-E,2 sub-slots)
               virent8090DEVME0DBSUFT07E(493007),   -- V8R22C10 for ME0DBSUFT07E(SBOM) Flexible Card Broadband Service Unit(BSUF-1T2-E,2 sub-slots)
               virent8090DEVME0DMSUFT07A(482951),   -- V8R22C10 for ME0DMSUFT07A(SBOM) Integrated Multi Service Unit(MSUI-2T-CM)
               virent8090DEVME0DMSUFT07E(482952),   -- V8R22C10 for ME0DMSUFT07E(SBOM) Flexible Card Broadband Service Unit(BSUF-1T2-E,2 sub-slots)
               virent8090DEVME0DMSUFT07B(482953),   -- V8R22C10 for ME0DMSUFT07B(SBOM) Flexible Card Multi Service Unit(MSUF-1T2-E,2 sub-slots)
               virent8090DEVME0DMSUFT07C(482954),   -- V8R22C10 for ME0DMSUFT07C(SBOM) Flexible Card Broadband Service Unit(BSUF-1T2A-E,2 sub-slots)
               virent8090DEVME0DMSUFT07D(482955),   -- V8R22C10 for ME0DMSUFT07D(SBOM) Flexible Card Multi Service Unit(MSUF-1T2A-E,2 sub-slots)
               virent8090DEVCR8DSFUI4TDE(175386),   -- V8R22C10 for CR8DSFUI4TDE(SBOM) NetEngine 8000 X4 4Tbps Switch Fabric Unit(SFUI-4T-F)
               virent8090DEVCR8DSFU14TD1(175387),   -- V8R22C10 for CR8DSFU14TD1(SBOM) NetEngine 8000 X4 14.4Tbps Switch Fabric Unit(SFUI-14T4-D)
               virent8090DEVCR8DSFUI4TDF(175388),   -- V8R22C10 for CR8DSFUI4TDF(SBOM) NetEngine 8000 X8 4Tbps Switch Fabric Unit(SFUI-4T-G)
               virent8090DEVCR8DSFU14TDE(175389),   -- V8R22C10 for CR8DSFU14TDE(SBOM) NetEngine 8000 X8 14.4Tbps Switch Fabric Unit(SFUI-14T4-E)
               virent8090DEVCR8DSFUI4TD1(175390),   -- V8R22C10 for CR8DSFUI4TD1(SBOM) NetEngine 8000 X4 4Tbps Switch Fabric Unit(SFUIA-4T-F)
               virent8090DEVCR8DSFU14TD2(175391),   -- V8R22C10 for CR8DSFU14TD2(SBOM) NetEngine 8000 X4 14.4Tbps Switch Fabric Unit(SFUIA-14T4-D)
               virent8090DEVCR8DSFUI4TD2(175392),   -- V8R22C10 for CR8DSFUI4TD2(SBOM) NetEngine 8000 X8 4Tbps Switch Fabric Unit(SFUIA-4T-G)
               virent8090DEVCR8DSFU14TD3(175393),   -- V8R22C10 for CR8DSFU14TD3(SBOM) NetEngine 8000 X8 14.4Tbps Switch Fabric Unit(SFUIA-14T4-E)
               virent8090DEVCR8DE2UB00D1(676980),   -- V8R22C10 for CR8DE2UB00D1(SBOM) 2-Port 1.2TBase Integrated Line Processing Unit(LPUI-2T4A)
               virent8090DEVTPND02CXPB01(901611),   --  for TPND02CXPB01(SBOM) OptiX PTN 980, TPN2CXPA3, System Control,Cross-connect and Multi-protocol Process Unit
               virent8090DEVTPND02CXPB02(932124),   --  for TPND02CXPB02(SBOM) OptiX PTN 980, TPN2CXPA4, System Control,Cross-connect and Multi-protocol Process Unit
               virent8090DEVTPQD01CXPB01(852453),   --  for TPQD01CXPB01(SBOM) OptiX PTN 990E, TPQ1CXPA4, System Control,Cross-connect and Multi-protocol Process Unit
               virent8090DEVTPQD01CXPB02(967204),   --  for TPQD01CXPB02(SBOM) OptiX PTN 990E, TPQ1CXPA4, System Control,Cross-connect and Multi-protocol Process Unit
               virent8090DEVTPND02CXPB03(932125),   -- V8R23C10 for TPND02CXPB03(SBOM) OptiX PTN 980, TPN2CXPB2, System Control,Cross-connect and Multi-protocol Process Unit
               virent8090DEVTPND02CXPB04(932126),   -- V8R23C10 for TPND02CXPB04(SBOM) OptiX PTN 980, TPN2CXPB3, System Control,Cross-connect and Multi-protocol Process Unit
			   virent8090DEVTPND02CXPC00(932127),   -- V8R24C00 for TPND02CXPC00(SBOM) OptiX PTN 980, TPN2CXPC, System Control,Cross-connect and Multi-protocol Process Unit
               virent8090DEVTPQD01CXPB03(967205),   -- V8R23C10 for TPQD01CXPB03(SBOM) OptiX PTN 990E, TPQ1CXPB3, System Control,Cross-connect and Multi-protocol Process Unit
               virent8090DEVTPQD01CXPB04(967206),   -- V8R23C10 for TPQD01CXPB04(SBOM) OptiX PTN 990E, TPQ1CXPB4, System Control,Cross-connect and Multi-protocol Process Unit
               virent8090DEVCR8DSFUI2TDA(175394),   -- V8R22C10 for CR8DSFUI2TDA(SBOM) NetEngine 8000 X4 2Tbps Switch Fabric Unit(SFUI-2T-A)
               virent8090DEVCR8DSFUI2TDB(175395),   -- V8R22C10 for CR8DSFUI2TDB(SBOM) NetEngine 8000 X8 2Tbps Switch Fabric Unit(SFUI-2T-B)
               virent8090DEVCR8DSFUI2TD1(175396),   -- V8R22C10 for CR8DSFUI2TD1(SBOM) NetEngine 8000 X4 2Tbps Switch Fabric Unit(SFUIA-2T-A)
               virent8090DEVCR8DSFUI2TD2(175397),   -- V8R22C10 for CR8DSFUI2TD2(SBOM) NetEngine 8000 X8 2Tbps Switch Fabric Unit(SFUIA-2T-B)
			   virent8090DEVCR8D6SFU2TA0(679804),   -- V8R25C00 for CR8D6SFU2TA0(SBOM) NetEngine 6000 X4 2Tbps Switch Fabric Unit(SFUI-2T-A)
               virent8090DEVCR8D6SFU2TB0(679805),   -- V8R25C00 for CR8D6SFU2TB0(SBOM) NetEngine 6000 X8 2Tbps Switch Fabric Unit(SFUI-2T-B)
               virent8090DEVCR8D6VUF8HC1(679806),   -- V8R25C00 for CR8D6VUF8HC1(SBOM) Flexible Card Versatile Service Unit 800(VSUF-800)
               virent8090DEVCR8DMPUF8AF2(468786),   -- V8R22C10 for CR8DMPUF8AF2(SBOM) NetEngine 8000E F Main Processing Unit B2A(MPUB2A)
               virent8090DEVCR8DMPUF8BF1(468787),   -- V8R22C10 for CR8DMPUF8BF1(SBOM) NetEngine 8000 F Main Processing Unit B2(MPUB2)
               virent8090DEVCR2D0MPUD4E1(468800),   -- V8R22C10 for CR2D0MPUD4E1(SBOM) Main Processing Unit D4(16G Memory)
               virent8090DEVCR2DLPUFF3E1(468801),   -- V8R22C10 for CR2DLPUFF3E1(SBOM) Flexible Card Line Processing Unit(LPUF-243G)
               virent8090DEVCR2D0LBXFME0(468802),   -- V8R22C10 for CR2D0LBXFME0(SBOM) 12-Port 10GBase LAN/WAN-SFP+ MACsec Flexible Card(P243G)
               virent8090DEVCR2DE1NBFME0(468803),   -- V8R22C10 for CR2DE1NBFME0(SBOM) 2-Port 50GBase/1-Port 100GBase-QSFP28 MACsec Flexible Card (P243G)
               virent8090DEVCR2B0BKP03EB(468804),   -- V8R22C10 for CR2B0BKP03EB(SBOM) NE20-X3 Enhanced Integrated DC Chassis Components (Including Dual DC Power)
               virent8090DEVCR2B0BKP03E9(468805),   -- V8R22C10 for CR2B0BKP03E9(SBOM) NE20-X3 Enhanced Integrated AC/HVDC Chassis Components (Including Dual AC&240VHVDC Power)
               subbname8090DEVNetEngine-A815-T(115921),   --CARD NetEngine A815 T
               subbname8090DEVNetEngine-A825-T(115922),   --CARD NetEngine A825 T
               virent8090DEVCR8PM4BASDC6(689008),  -- V8R22C10 for CR8PM4BASDC6(SBOM) NetEngine 8000 M4 Basic Configuration CM (Enable Fixed Interface(2*100GE or 8*25GE combo+16*10GE,#4~19 enable GE), DC Power, without Software Charge,Document and auxiliary materials)
               virent8090DEVCR8PM4BASDC7(689009),  -- V8R22C10 for CR8PM4BASDC7(SBOM) NetEngine 8000 M4 Basic Configuration CM (Includes NetEngine 8000 M4 Chassis, Enable Fixed Interface, DC Power,without Software Charge,Document and auxiliary materials)
               virent8090DEVCR8PM4BASAC6(689010),  -- V8R22C10 for CR8PM4BASAC6(SBOM) NetEngine 8000 M4 Basic Configuration CM (Enable Fixed Interface(2*100GE or 8*25GE combo+16*10GE,#4~19 enable GE),AC Power,without Software Charge,Document and auxiliary materials)
               virent8090DEVCR8PM4BASAC7(689011),  -- V8R22C10 for CR8PM4BASAC7(SBOM) NetEngine 8000 M4 Basic Configuration CM (Includes NetEngine 8000 M4 Chassis, Enable Fixed Interface, AC Power,without Software Charge,Document and auxiliary materials)
               virent8090DEVCR8PM9BASACQ(689012),  -- V8R22C10 for CR8PM9BASACQ(SBOM) Integrated Network Processing Unit (IPUA-1T2-F)
               virent8090DEVCR8DIPU640C9(689013),  -- V8R22C10 for CR8DIPU640C9(SBOM) Integrated Network Processing Unit (IPUA-640)
               virent8090DEVTNRDIPU1T292(689014),  -- V8R22C10 for TNRDIPU1T292(SBOM) Integrated Network Processing Unit (IPU-1T2-F)
               virent8090DEVTNRDIPU48091(689015),  -- V8R22C10 for TNRDIPU48091(SBOM) Integrated Network Processing Unit (IPU-480-F)
               virent8090DEVCR8DIPU1T213(689016),  -- V8R22C10 for CR8DIPU1T213(SBOM) Integrated Network Processing Unit (IPUA-1T2-F)
               virent8090DEVCR8DIPU480MA(689017),  -- V8R22C10 for CR8DIPU480MA(SBOM) Integrated Network Processing Unit (IPU-480-CN)
               virent8090DEVCR8DIPU480MB(689018),  -- V8R22C10 for CR8DIPU480MB(SBOM) Integrated Network Processing Unit (IPUA-480-CN)
               virent8090DEVCR8DIPU1T2M6(689019),  -- V8R22C10 for CR8DIPU1T2M6(SBOM) Integrated Network Processing Unit (IPU-1T2-E)
               virent8090DEVCR8DIPU480M2(689020),  -- V8R22C10 for CR8DIPU480M2(SBOM) Integrated Network Processing Unit (IPU-480-E)
               virent8090DEVCR8D0IPU1T2MG(689021),  -- V8R22C10 for CR8D0IPU1T2MG(SBOM) Integrated Network Processing Unit (IPUA-1T2-E)
               virent8090DEVCR8D0IPU480MB(689022),  -- V8R22C10 for CR8D0IPU480MB(SBOM) Integrated Network Processing Unit (IPUA-480-E)
               virent8090DEVCR8DIPU480MC(689023),  -- V8R22C10 for CR8DIPU480MC(SBOM) Integrated Network Processing Unit (IPUA-480-E)
               virent8090DEVCR8D0IPU1T2MP(689024),  -- V8R22C10 for CR8D0IPU1T2MP(SBOM) Integrated Network Processing Unit (IPUA-1T2-E)
               virent8090DEVCR8DIPU1T2MT(689025),  -- V8R22C10 for CR8DIPU1T2MT(SBOM) Integrated Network Processing Unit (IPU-1T2-DA)
               virent8090DEVCR8DIPU480MG(689026),  -- V8R22C10 for CR8DIPU480MG(SBOM) Integrated Network Processing Unit (IPU-480-DA)
               virent8090DEVCR8DIPU1T2M4(689027),  -- V8R22C10 for CR8DIPU1T2M4(SBOM) Integrated Network Processing Unit (IPUA-1T2-DA)
               virent8090DEVCR8DIPU480M1(689028),  -- V8R22C10 for CR8DIPU480M1(SBOM) Integrated Network Processing Unit (IPUA-480-DA)
               virent8090DEVCR8D0IPU2TD2(689029),  -- V8R22C10 for CR8D0IPU2TD2(SBOM) Integrated Network Processing Unit (IPUA-2T-F)
               virent8090DEVCR8D0IPU2TM1(689030),  -- V8R22C10 for CR8D0IPU2TM1(SBOM) Integrated Network Processing Unit (IPU-2T-E)
               virent8090DEVCR8DIPUT2TM1(689031),  -- V8R22C10 for CR8DIPUT2TM1(SBOM) Integrated Network Processing Unit (IPU-1T2-E)
               virent8090DEVTNRD0IPU2T90(689032),  -- V8R22C10 for TNRD0IPU2T90(SBOM) Integrated Network Processing Unit (IPU-2T-F)
               virent8090DEVTNRDIPUT2T90(689033),  -- V8R22C10 for TNRDIPUT2T90(SBOM) Integrated Network Processing Unit (IPU-1T2-F)
               virent8090DEVCR5D0IPU2T91(689034),  -- V8R22C10 for CR5D0IPU2T91(SBOM) Integrated Network Processing Unit (IPU-2T-E)
               virent8090DEVCR5DIPUT2T91(689035),  -- V8R22C10 for CR5DIPUT2T91(SBOM) Integrated Network Processing Unit (IPU-1T2-E)
               virent8090DEVCR8D0IPU2TM2(689036),  -- V8R22C10 for CR8D0IPU2TM2(SBOM) Integrated Network Processing Unit (IPUA-2T-E)
               virent8090DEVCR8DIPU1T2M3(689037),  -- V8R22C10 for CR8DIPU1T2M3(SBOM) Integrated Network Processing Unit (IPU-1T2-EN)
               virent8090DEVTNRDIPU1T290(689038),  -- V8R22C10 for TNRDIPU1T290(SBOM) Integrated Network Processing Unit (IPU-1T2-FN)
               virent8090DEVCR5DIPU1T291(689039),  -- V8R22C10 for CR5DIPU1T291(SBOM) Integrated Network Processing Unit (IPU-1T2-EN)
               virent8090DEVCR8D0IPU1T2ME(689040),  -- V8R22C10 for CR8D0IPU1T2ME(SBOM) Integrated Network Processing Unit (IPUA-1T2-EN)
               virent8090DEVCR8D0IPU1T2MK(689041),  -- V8R22C10 for CR8D0IPU1T2MK(SBOM) Integrated Network Processing Unit (IPUA-1T2-EN)
               virent8090DEVCR8DIPU1T2MS(689042),  -- V8R22C10 for CR8DIPU1T2MS(SBOM) Integrated Network Processing Unit (IPU-1T2-DA)
               virent8090DEVCR8DIPU1T2M2(689043),  -- V8R22C10 for CR8DIPU1T2M2(SBOM) Integrated Network Processing Unit (IPUA-1T2-DA)
               virent8090DEVANND00CXPC00(689044),  -- V8R22C10 for ANND00CXPC00(SBOM) System Control,Cross-connect and Multi-protocol Process Unit with 800G
               virent8090DEVANND00CXPC03(689045),  -- V8R22C10 for ANND00CXPC03(SBOM) System Control,Cross-connect and Multi-protocol Process Unit with 360G
               virent8090DEVANND00CXPB01(689046),  -- V8R22C10 for ANND00CXPB01(SBOM) System Control,Cross-connect and Multi-protocol Process Unit with 320G
               virent8090DEVANND00CXPB02(689047),  -- V8R22C10 for ANND00CXPB02(SBOM) System Control,Cross-connect and Multi-protocol Process Unit with 360G
               virent8090DEVANND01CXPB01(689048),  -- V8R22C10 for ANND01CXPB01(SBOM) System Control,Cross-connect and Multi-protocol Process Unit with 800G
               virent8090DEVANRD00CXPC00(689049),  -- V8R22C10 for ANRD00CXPC00(SBOM) System Control, Cross-connect and Multi-protocol Process Unit with 160G
               virent8090DEVANRD00CXPA21(689050),  -- V8R22C10 for ANRD00CXPA21(SBOM) System Control, Cross-connect and Multi-protocol Process Unit with 160G
               virent8090DEVANRD01CXPD00(689051),  -- V8R22C10 for ANRD01CXPD00(SBOM) System Control, Cross-connect and Multi-protocol Process Unit with 400G
               virent8090DEVANRD01CXPE00(689052),  -- V8R22C10 for ANRD01CXPE00(SBOM) System Control, Cross-connect and Multi-protocol Process Unit with 800G
               virent8090DEVCR8DCXP160C6(689053),  -- V8R22C10 for CR8DCXP160C6(SBOM) System Control,Cross-connect and Multi-protocol Process Unit (CXP-160-C)
               virent8090DEVCR8DCXP160C7(689054),  -- V8R22C10 for CR8DCXP160C7(SBOM) System Control,Cross-connect and Multi-protocol Process Unit (CXPA-160-C)
               virent8090DEVCR8DCXP160C4(689140),  -- V8R24C00 for CR8DCXP160C4(SBOM) System Control,Cross-connect and Multi-protocol Process Unit (CXP-160-C)
               virent8090DEVCR8DCXP160C5(689141),  -- V8R24C00 for CR8DCXP160C5(SBOM) System Control,Cross-connect and Multi-protocol Process Unit (CXPA-160-C)
               virent8090DEVCR8DCXP160C8(689142),   -- V8R24C00 for CR8DCXP160C8(SBOM) System Control,Cross-connect and Multi-protocol Process Unit (CXPA-160-C),High anti-corrosion
               virent8090DEVANHMHSTA0101(689055),  -- V8R22C10 for ANHMHSTA0101(SBOM) ATN 910D-A, DC Power, Port Capacity 4*100GE/50GE + 16*25GE/10GE/GE/FE + 8*10GE/GE/FE, default all the GE/FE ports is enabled
               virent8090DEVANHMHSTA0201(689056),  -- V8R22C10 for ANHMHSTA0201(SBOM) ATN 910D-A, AC Power, Port Capacity 4*100GE/50GE + 16*25GE/10GE/GE/FE + 8*10GE/GE/FE, default all the GE/FE ports is enabled
               virent8090DEVANHMHSTA0122(689057),  -- V8R22C10 for ANHMHSTA0122(SBOM) ATN 910D-A, DC Power, Port Capacity 4*100GE/50GE + 16*25GE/10GE/GE/FE + 8*10GE/GE/FE, default all the GE/FE ports is enabled
               virent8090DEVANHMHSTA0222(689058),  -- V8R22C10 for ANHMHSTA0222(SBOM) ATN 910D-A, AC Power, Port Capacity 4*100GE/50GE + 16*25GE/10GE/GE/FE + 8*10GE/GE/FE, default all the GE/FE ports is enabled
               virent8090DEVANHMHSTA0332(689059),  -- V8R22C10 for ANHMHSTA0332(SBOM) ATN 910D-A, AC+DC Power, Port Capacity 4*100GE/50GE + 16*25GE/10GE/GE/FE + 8*10GE/GE/FE, default all the GE/FE ports is enabled
               virent8090DEVCR8PM1DBASCFP(689060),  -- V8R22C10 for CR8PM1DBASCFP(SBOM) NetEngine 8000 M1D-B DC(Port Capacity 2*50GE+2*25GE/10GE+2*10GE+14*GE,default 2*25GE&all GE,no aux material)
               virent8090DEVCR8PM1DBASCQ(689061),  -- V8R22C10 for CR8PM1DBASCQ(SBOM) NetEngine 8000 M1D-B DC(A)(Port Capacity 2*50GE+2*25GE/10GE+2*10GE+14*GE,default 2*25GE&all GE,no aux material)
               virent8090DEVCR8PM1DBASCR(689062),  -- V8R22C10 for CR8PM1DBASCR(SBOM) NetEngine 8000 M1D-B AC(Port Capacity 2*50GE+2*25GE/10GE+2*10GE+14*GE,default 2*25GE&all GE,no aux material)
               virent8090DEVCR8PM1DBASCS(689063),  -- V8R22C10 for CR8PM1DBASCS(SBOM) NetEngine 8000 M1D-B AC(A)(Port Capacity 2*50GE+2*25GE/10GE+2*10GE+14*GE,default 2*25GE&all GE,no aux material)
               virent8090DEVANHMHSTA0502(689064),  -- V8R22C10 for ANHMHSTA0502(SBOM) ATN 910D-B, DC Power, Port Capacity 2*50GE+2*25GE/10GE/GE+2*10GE/GE+10*GE(o)+4*GE(e), default 2*25GE and all GE/FE ports
               virent8090DEVANHMHSTA0602(689065),  -- V8R22C10 for ANHMHSTA0602(SBOM) ATN 910D-B, AC Power, Port Capacity 2*50GE+2*25GE/10GE/GE+2*10GE/GE+10*GE(o)+4*GE(e), default 2*25GE and all GE/FE ports
               virent8090DEVANHMHSTA0504(689119),  -- V8R23C00 for ANHMHSTA0602(SBOM) ATN 910D-B, DC Power, Port Capacity 4*25GE/10GE/GE +6*10GE/GE+10*GE(o)+4*GE(e), default 4*25GE and all GE/FE ports
               virent8090DEVANHMHSTA0604(689120),  -- V8R23C00 for ANHMHSTA0602(SBOM) ATN 910D-B, AC Power, Port Capacity 4*25GE/10GE/GE +6*10GE/GE+10*GE(o)+4*GE(e), default 4*25GE and all GE/FE ports
               virent8090DEVANHMHSTA0110(689121),   -- V8R23C10 for ANHMHSTA0110(SBOM) ATN 910D-H DC Basic Configuration(Includes Fixed Enable Interface (8*10GE+10*GE/Dual Power/FAN/Chassis)
               virent8090DEVANHMHSTA0210(689122),   -- V8R23C10 for ANHMHSTA0210(SBOM) ATN 910D-H AC Basic Configuration(Includes Fixed Enable Interface (8*10GE+10*GE/Dual Power/FAN/Chassis)
               virent8090DEVCP8PHST2EA11(689123),   -- V8R23C10 for CP8PHST2EA11(SBOM) NetEngine A812 E-S DC Chassis(10*GE/FE(o)+4*GE/FE(e))
               virent8090DEVCP8PHST2EA14(689137),   -- V8R24C00 for CP8PHST2EA14(SBOM) NetEngine A812 E-S DC Chassis(10*GE/FE(o)+4*GE/FE(e))
               virent8090DEVISR801BASAX2(689124),   -- V8R23C10 for ISR801BASAX2(SBOM) Mining intrinsic safety GE router KJJ12(A), NetEngine A812 E-S(10*GE/FE(o)+4*GE/FE(e))
               virent8090DEVANHMHSTA0111(689125),   -- V8R23C10 for ANHMHSTA0111(SBOM) ATN 910D-H DC Basic Configuration(Includes Fixed Enable Interface (8*10GE+10*GE/Dual Power/FAN/Chassis)
               virent8090DEVANHMHSTA0211(689126),   -- V8R23C10 for ANHMHSTA0211(SBOM) ATN 910D-H AC Basic Configuration(Includes Fixed Enable Interface (8*10GE+10*GE/Dual Power/FAN/Chassis)
               virent8090DEVCP8PHST20A10(689127),   -- V8R23C10 for CP8PHST20A10(SBOM) NetEngine A822 AC System (2*10GE/GE/FE(o)+4*GE/FE(o)+8*GE/FE(e), Default 6*GE/FE(o)+8*GE/FE(e))
               virent8090DEVCP8PHST20A12(689128),   -- V8R23C10 for CP8PHST20A12(SBOM) NetEngine A822 AC System (2*10GE/GE/FE(o)+4*GE/FE(o)+8*GE/FE(e), Default 6*GE/FE(o)+8*GE/FE(e))
               virent8090DEVCP8PHST10A20(210009),   -- V8R25C00 for CP8PHST10A20(SBOM) NetEngine A817 AC System (4*GE/FE(o)+4*GE/FE(e)+4*E1)
               virent8090DEVANHMHSTA0506(689129),  -- V8R23C10 for ANHMHSTA0506(SBOM) ATN 910D-B,DC Power,Port Capacity 2*50GE+2*25GE/10GE/GE+2*10GE/GE+10*GE(o)+4*GE(e),support 4*25GE mode,default enable all GE/FE
               virent8090DEVANHMHSTA0606(689130),  -- V8R23C10 for ANHMHSTA0606(SBOM) ATN 910D-B,AC Power,Port Capacity 2*50GE+2*25GE/10GE/GE+2*10GE/GE+10*GE(o)+4*GE(e),support 4*25GE mode,default enable all GE/FE
               virent8090DEVCR8PM1DBASDE(689131),   -- V8R23C10 for CR8PM1DBASDE(SBOM) NetEngine 8000 M1D, DC Power(A)(Port Capacity 4*100GE/50GE+16*25GE/10GE/GE/FE+8*10GE/GE/FE,exclude auxiliary materials)
               virent8090DEVCR8PM1DBASAE(689132),   -- V8R23C10 for CR8PM1DBASAE(SBOM) NetEngine 8000 M1D, AC Power(A)(Port Capacity 4*100GE/50GE+16*25GE/10GE/GE/FE+8*10GE/GE/FE,exclude auxiliary materials)
               virent8090DEVCR8PM1DBADM6(689133),   -- V8R23C10 for CR8PM1DBADM6(SBOM) NetEngine 8000 M1D, DC Power (Port Capacity 4*100GE/50GE+16*25GE/10GE/GE/FE+8*10GE/GE/FE,exclude auxiliary materials)
               virent8090DEVCR8PM1DBAAM6(689134),   -- V8R23C10 for CR8PM1DBAAM6(SBOM) NetEngine 8000 M1D Basic Configuration, AC Power (Port Capacity 4*100GE/50GE+16*25GE/10GE/GE/FE+8*10GE/GE/FE,exclude auxiliary materials)
			   virent8090DEVANGMHSTS0120(689135),   -- V8R23C10 for ANGMHSTS0120(SBOM) ATN 910C-S, DC Power, Port Capacity 6*10GE/GE/FE(o)+2*GE/FE(o)+4*GE/FE(e), Default 2*10GE+10*GE
			   virent8090DEVANGMHSTS0220(689136),   -- V8R23C10 for ANGMHSTS0220(SBOM) ATN 910C-S, AC Power, Port Capacity 6*10GE/GE/FE(o)+2*GE/FE(o)+4*GE/FE(e), Default 2*10GE+10*GE
			   virent8090DEVANHMHSTA5600(689138),   -- V8R24C00 for ANHMHSTA5600(SBOM) ATN 910D-A, DC Power, Port Capacity 2*100GE/50GE+8*25GE/10GE/GE/FE+16*10GE/GE/FE, default all the GE/FE ports is enabled
               virent8090DEVANHMHSTA5601(689139),   -- V8R24C00 for ANHMHSTA5601(SBOM) ATN 910D-A, AC Power, Port Capacity 2*100GE/50GE+8*25GE/10GE/GE/FE+16*10GE/GE/FE, default all the GE/FE ports is enabled
               virent8090DEVANGMHSTG0105(689066),  -- V8R22C10 for ANGMHSTG0105(SBOM) ATN 910C-G, DC Power, Port Capacity 16*10GE/GE/FE(o)+12*GE/FE(o)+4*GE/FE(e), Default 2*10GE+8*GE
               virent8090DEVANGMHSTG0204(689067),  -- V8R22C10 for ANGMHSTG0204(SBOM) ATN 910C-G, AC Power, Port Capacity 16*10GE/GE/FE(o)+12*GE/FE(o)+4*GE/FE(e), Default 2*10GE+8*GE
               virent8090DEVCR8PM1ABASD0(689068),  -- V8R22C10 for CR8PM1ABASD0(SBOM) NetEngine 8000 M1A, DC Power,Port Capacity 16*10GE+12*GE(o)+4*GE(e)
               virent8090DEVCR8PM1ABASA0(689069),  -- V8R22C10 for CR8PM1ABASA0(SBOM) NetEngine 8000 M1A, AC Power,Port Capacity 16*10GE+12*GE(o)+4*GE(e)
               virent8090DEVCR8PM1ABASD1(689070),  -- V8R22C10 for CR8PM1ABASD1(SBOM) NetEngine 8000 M1A, DC Power,Port Capacity 16*10GE+12*GE(o)+4*GE(e)
               virent8090DEVCR8PM1ABASA1(689071),  -- V8R22C10 for CR8PM1ABASA1(SBOM) NetEngine 8000 M1A, AC Power,Port Capacity 16*10GE+12*GE(o)+4*GE(e)
               virent8090DEVANGMHSTK0103(689072),  -- V8R22C10 for ANGMHSTK0103(SBOM) ATN 910C-K, DC Power, Port Capacity 16*10GE/GE/FE+8*GE/FE(o)+4*GE/FE(e)+16*E1,None of the ports are available by default
               virent8090DEVANGMHSTK0203(689073),  -- V8R22C10 for ANGMHSTK0203(SBOM) ATN 910C-K, AC Power, Port Capacity 16*10GE/GE/FE+8*GE/FE(o)+4*GE/FE(e)+16*E1,None of the ports are available by default
               virent8090DEVANGMHSTM0103(689074),  -- V8R22C10 for ANGMHSTM0103(SBOM) ATN 910C-M, DC Power, Port Capacity 16*10GE/GE/FE+8*GE/FE(o)+4*GE/FE(e),None of the ports are available by default
               virent8090DEVANGMHSTM0203(689075),  -- V8R22C10 for ANGMHSTM0203(SBOM) ATN 910C-M, AC Power, Port Capacity 16*10GE/GE/FE+8*GE/FE(o)+4*GE/FE(e),None of the ports are available by default
               virent8090DEVANGMHSTM0301(689076),  -- V8R22C10 for ANGMHSTM0301(SBOM) ATN 910C-M, AC+DC Power, Port Capacity 16*10GE/GE/FE+8*GE/FE(o)+4*GE/FE(e),None of the ports are available by default
               virent8090DEVCR8PM1CBASD0(689077),  -- V8R22C10 for CR8PM1CBASD0(SBOM) NetEngine 8000 M1C, 2*DC Power, Port Capacity 16*10GE+8*GE(o)+4*GE(e), None of the ports are available by default
               virent8090DEVCR8PM1CBASAQ(689078),  -- V8R22C10 for CR8PM1CBASAQ(SBOM) NetEngine 8000 M1C, 2*AC Power, Port Capacity 16*10GE+8*GE(o)+4*GE(e), None of the ports are available by default
               virent8090DEVCR8PM1CBASD1(689079),  -- V8R22C10 for CR8PM1CBASD1(SBOM) NetEngine 8000 M1C(A), 2*DC Power, Port Capacity 16*10GE+8*GE(o)+4*GE(e), None of the ports are available by default
               virent8090DEVCR8PM1CBASAS(689080),  -- V8R22C10 for CR8PM1CBASAS(SBOM) NetEngine 8000 M1C(A), 2*AC Power, Port Capacity 16*10GE+8*GE(o)+4*GE(e), None of the ports are available by default
               virent8090DEVANGMHSTH0110(689081),  -- V8R22C10 for ANGMHSTH0110(SBOM) ATN 910C-H DC Basic Configuration(Includes Fixed Enable Interface (4*10GE/GE/FE(o)+4*GE/FE(o)+4*GE/FE(e))/Dual Power/FAN/Chassis)
               virent8090DEVANGMHSTS0110(689082),  -- V8R22C10 for ANGMHSTS0110(SBOM) ATN 910C-S DC Basic Configuration(Includes Fixed Enable Interface (5*10GE/GE/FE(o)+3*GE/FE(o)+4*GE/FE(e))/Dual Power/FAN/Chassis)
               virent8090DEVANGMHSTH0210(689083),  -- V8R22C10 for ANGMHSTH0210(SBOM) ATN 910C-H AC Basic Configuration(Includes Fixed Enable Interface (4*10GE/GE/FE(o)+4*GE/FE(o)+4*GE/FE(e))/Power/FAN/Chassis)
               virent8090DEVANGMHSTS0210(689084),  -- V8R22C10 for ANGMHSTS0210(SBOM) ATN 910C-S AC Basic Configuration(Includes Fixed Enable Interface (5*10GE/GE/FE(o)+3*GE/FE(o)+4*GE/FE(e))/Power/FAN/Chassis)
               virent8090DEVCR5DLPUFM397(689085),  -- V8R22C10 for CR5DLPUFM397(SBOM) Flexible Card Line Processing Unit(LPUF-483D)
               virent8090DEVCR5DLPUFF394(689086),  -- V8R22C10 for CR5DLPUFF394(SBOM) Flexible Card Line Processing Unit(LPUF-243D)
               virent8090DEVCR5DLPUF5376(689087),  -- V8R22C10 for CR5DLPUF5376(SBOM) Flexible Card Line Processing Unit(LPUF-53D)
               virent8090DEVME0DVSUIK07F(689088),  -- V8R22C10 for ME0DVSUIK07F(SBOM) Integrated Service Unit 400(VSUI-400D)
               virent8090DEVANGMHSTM03D0(689089),  -- V8R22C10 for ANGMHSTM03D0(SBOM) ATN 910C-M,2*DC Power, Port Capacity 6*10GE+4*GE/FE(o)+4*GE/FE(e)
               virent8090DEVANGMHSTM03A0(689090),  -- V8R22C10 for ANGMHSTM03A0(SBOM) ATN 910C-M, 2*AC Power, Port Capacity 6*10GE+4*GE/FE(o)+4*GE/FE(e)
               virent8090DEVCR5D0MPUB97A(689102),  -- V8R22C10 for CR5D0MPUB97A(SBOM) Main Processing Unit B12(32G Memory)
               virent8090DEVCR5D0MPUB97B(689103),  -- V8R22C10 for CR5D0MPUB97B(SBOM) Main Processing Unit B12A(32G Memory)
               virent8090DEVCX6DMPUX867A(689104),  -- V8R22C10 for CX6DMPUX867A(SBOM) Main Processing Unit B12(32G Memory)
               virent8090DEVCX6DMPUB121A(689105),  -- V8R22C10 for CX6DMPUB121A(SBOM) Main Processing Unit B12A(32G Memory)
               virent8090DEVTNRDMPUX867A(689106),  -- V8R22C10 for TNRDMPUX867A(SBOM) Main Processing Unit B12(32G Memory)
               virent8090DEVME0DMPUX867A(689107),  -- V8R22C10 for ME0DMPUX867A(SBOM) Main Processing Unit B12(32G Memory)
               virent8090DEVME0DMPUX867B(689108),  -- V8R22C10 for ME0DMPUX867B(SBOM) Main Processing Unit B12A(32G Memory)
               virent8090DEVIG2D0MPUB97B(689109),  -- V8R22C10 for IG2D0MPUB97B(SBOM) Main Processing Unit B12A(32G Memory)
               virent8090DEVCR5DVSUIK07M(894575),   -- V8R22C10 for CR5DVSUIK07M(SBOM) Integrated Service Unit 400(VSUI-400B)
               virent8090DEVIG2D00SPUG0F(829027),   -- V8R22C10 for IG2D00SPUG0F(SBOM) High Performance X8A&X16A Service Processing Unit-SPUGA,with HW Service Inspection Gateway Software
               virent8090DEVIG2D00SPUG0E(836270),   -- V8R22C10 for IG2D00SPUG0E(SBOM) High Performance X8A&X16A Enhanced Service Processing Unit-SPUGEA,with HW Service Inspection Gateway Software
               virent8090DEVCR5D0SRUAK72(183685),   --  for CR5D0SRUAK72(SBOM) Switch and Route Processing Unit A113(SRUA-2T-G, 32G Memory)
               virent8090DEVCR5D0SRUAK73(959601),   --  for CR5D0SRUAK73(SBOM) Switch and Route Processing Unit A113A(SRUA-2TA-G, 32G Memory)
               virent8090DEVCX6D0SRUAK72(125962),   --  for CX6D0SRUAK72(SBOM) Switch and Route Processing Unit A113(SRUA-2T-G, 32G Memory)
               virent8090DEVTNRD0SRUAK72(300854),   --  for TNRD0SRUAK72(SBOM) Switch and Route Processing Unit A113(SRUA-2T-G, 32G Memory)
               virent8090DEVIG2D0SRUAK72(135469),   --  for IG2D0SRUAK72(SBOM) Switch and Route Processing Unit A113A(SRUA-2TA-G, 32G Memory)
               virent8090DEVCR5DSFUIT27V(465407),   --  for CR5DSFUIT27V(SBOM) Finished Board Unit,NetEngine40E,CR57SFU2TES01,2Tbps Switch Fabric Unit I(SFUI-2T-I)
               virent8090DEVCR5DSFUIT27W(606864),   --  for CR5DSFUIT27W(SBOM) Finished Board Unit,NetEngine40E,CR57SFU2TEA01,2Tbps Switch Fabric Unit I(SFUI-2TA-I)
               virent8090DEVCX6DSFUIT27U(440925),   --  for CX6DSFUIT27U(SBOM) Finished Board Unit,CX600,CX61SFU2TES00,2Tbps Switch Fabric Unit I(SFUI-2T-I)
               virent8090DEVTNRDSFUIT27U(978034),   --  for TNRDSFUIT27U(SBOM) Finished Board Unit,PTN6900,TNR1SFU2TES00,2Tbps Switch Fabric Unit I(SFUI-2T-I)
               virent8090DEVIG2DSFUIT214(310202),   --  for IG2DSFUIT214(SBOM) Finished Board Unit,SIG9800,IG21SFU2TE03,2Tbps Switch Fabric Unit E1(SFUI-2TA-I)
               virent8090DEVCR5DSFUIT27T(721887),   --  for CR5DSFUIT27T(SBOM) Finished Board Unit,NetEngine40E,CR57SFU2TFS1,2Tbps Switch Fabric Unit J(SFUI-2T-J)
               virent8090DEVCR5DSFUIT27U(413155),   --  for CR5DSFUIT27U(SBOM) Finished Board Unit,NetEngine40E,CR57SFU2TFA1,2Tbps Switch Fabric Unit J(SFUI-2TA-J)
               virent8090DEVCX6DSFUIT27T(471946),   --  for CX6DSFUIT27T(SBOM) Finished Board Unit,CX600,CX61SFU2TFS1,2Tbps Switch Fabric Unit J(SFUI-2T-J)
               virent8090DEVTNRDSFUIT27T(448824),   --  for TNRDSFUIT27T(SBOM) Finished Board Unit,PTN6900,CR57SFU2TFS1,2Tbps Switch Fabric Unit J(SFUI-2T-J)
               virent8090DEVIG2DSFUIT213(137349),   --  for IG2DSFUIT213(SBOM) Finished Board Unit,SIG9800,IG21SFU2TFA1,2Tbps Switch Fabric Unit F1(SFUI-2TA-J)
               virent8090DEVCR8DIPU1T214(658303),  -- V8R22C10 for CR8DIPU1T214(SBOM) Integrated Network Processing Unit (IPUA-1T2-F)
               virent8090DEVCR8DE8KE8ND9(578779),  -- V8R22C10 for 8-Port 400GBase-QSFP-DD + 8-Port 100GBase-QSFP28 Integrated Line Processing Unit CM(LPUI-4T-E-CM,Enable 16*100GE by default)
               virent8090DEVCR8DE4KEFND9(734940),  -- V8R22C10 for 4-Port 400GBase-QSFP-DD + 24-Port 100GBase-QSFP28 Integrated Line Processing Unit CM (LPUI-4T-E-CM)
               virent8090DEVCR8DEKNBFED9(193229),  -- V8R22C10 for 40-Port 100GBase-QSFP28 Integrated Line Processing Unit CM(LPUI-4T-E-CM)
               virent8090DEVCR8DEENBFED9(263591),  -- V8R22C10 for 20-Port 100GBase-QSFP28 Integrated Line Processing Unit CM(LPUI-2T-E-CM)
               virent8090DEVCR8DERYBFED9(623955),  -- V8R22C10 for 72-Port 25GE(SFP28)/10GE(SFP+)/GE(SFP) Integrated Line Processing Unit CM(LPUI-2T-E-CM)
               virent8090DEVCR8DEANEJYD9(245429),  -- V8R22C10 for 10-Port 100GBase-QSFP28 + 36-Port 25GE(SFP28)/10GE(SFP+)/GE(SFP) Integrated Line Processing Unit CM(LPUI-2T-E-CM)
               virent8090DEVCR8DEANEJXDQ(818320),  -- V8R22C10 for 10-Port 100GBase-QSFP28 MACsec + 36-Port 10GE(SFP+)/GE(SFP) MACsec Integrated Line Processing Unit CM(LPUI-1T-CM)
               virent8090DEVCR8DEANEJXD9(236875),  -- V8R22C10 for 10-Port 100GBase-QSFP28 + 36-Port 10GE(SFP+)/GE(SFP) Integrated Line Processing Unit CM(LPUI-1T-CM)
               virent8090DEVCR8DIPU480M3(115244),  -- V8R22C10 for CR8DIPU480M3(SBOM) Integrated Network Processing Unit (IPU-480-E)
               virent8090DEVCR8DMPUF8BF3(820122),   -- V8R22C10 for CR8DMPUF8BF3(SBOM) NetEngine 8000 F Main Processing Unit B1(MPUB1)
               virent8090DEVCR8DMPUF8BF2(560449),   -- V8R22C10 for CR8DMPUF8BF2(SBOM) NetEngine 8000 F Main Processing Unit B2(MPUB2)
               virent8090DEVCR8DMPUF8AZ2(333932),   -- V8R22C10 for CR8DMPUF8AZ2(SBOM) NetEngine 8000E F Main Processing Unit B1Z(MPUB1Z)
               virent8090DEVCR8DSFUIK0D0(278498),   -- V8R22C10 for CR8DSFUIK0D0(SBOM) NetEngine 8000 F 2T Switch Routing Unit(SRU-2T-A)
               virent8090DEVCR8DSFUIK0D1(333202),   -- V8R22C10 for CR8DSFUIK0D1(SBOM) NetEngine 8000E F 2T Switch Routing Unit(SRUA-2T-A)
               virent8090DEVCR8DSFUIK0E1(333203),   -- V8R25C00 for CR8DSFUIK0E1(SBOM) NetEngine 8000E F 1T6 Switch Routing Unit(SRUA-1T6-A)
               virent8090DEVCR8DSFUIK0E2(333204),   -- V8R25C00 for CR8DSFUIK0E2(SBOM) NetEngine 8000E F 1T6 Switch Routing Unit(SRU-1T6-A)
               virent8090DEVCR8DSFUIK0F0(333205),   -- V8R25C00 for CR8DSFUIK0F0(SBOM) NetEngine 8000 F 1T6 Switch Routing Unit(SRU-1T6-A)
               virent8090DEVCR8B0BKP2DF2(333206),   -- V8R25C00 for CR8B0BKP2DF2(SBOM) NetEngine 8000 F2D Integrated Chassis Components(Port-side Intake, including 3 fan box, excluding power module)
               virent8090DEVCR8B0BKP2DF3(333207),   -- V8R25C00 for CR8B0BKP2DF3(SBOM) NetEngine 8000 F2D Integrated Chassis Components(Port-side Exhaust, including 3 fan box, excluding power module)
               virent8090DEVCR8B0BKP2DF0(333208),   -- V8R25C00 for CR8B0BKP2DF0(SBOM) NetEngine 8000E F2D Integrated Chassis Components(Port-side Intake, including 3 fan box, excluding power module)
               virent8090DEVCR8B0BKP2DF1(333209),   -- V8R25C00 for CR8B0BKP2DF1(SBOM) NetEngine 8000E F2D Integrated Chassis Components(Port-side Exhaust, including 3 fan box, excluding power module)
               virent8090DEVCR8B0BKP2CFD(333220),   -- V8R25C00 for CR8B0BKP2CFD(SBOM) NetEngine 8000E F2D Programmable Computing Router Integrated Chassis Components(Port-side Intake, including 3 fan box, excluding power module)
               virent8090DEVCR8B0BKP2CFE(333221),   -- V8R25C00 for CR8B0BKP2CFE(SBOM) NetEngine 8000E F2D Programmable Computing Router Integrated Chassis Components(Port-side Intake, including 3 fan box, excluding power module)
               virent8090DEVCR8B0BKP2CFF(333222),   -- V8R25C00 for CR8B0BKP2CFF(SBOM) NetEngine 8000E F2D Programmable Computing Router Integrated Chassis Components(Port-side Exhaust, including 3 fan box, excluding power module)
               virent8090DEVCR8B0BKP2CFG(333223),   -- V8R25C00 for CR8B0BKP2CFG(SBOM) NetEngine 8000E F2D Programmable Computing Router Integrated Chassis Components(Port-side Exhaust, including 3 fan box, excluding power module)                
               virent8090DEVXHXDLPUF4TC3(333210),   -- V8R25C00 for XHXDLPUF4TC3(SBOM) Flexible Card Line Processing Unit(LPUF-4T8A)
               virent8090DEVXHXD0MPUAXC1(333211),   -- V8R25C00 for XHXD0MPUAXC1(SBOM) NetEngine XH16100 Main Processing Unit A10B(MPUA10B)
               virent8090DEVXHXD0MPUAXC2(333212),   -- V8R25C00 for XHXD0MPUAXC2(SBOM) NetEngine XH16200 Main Processing Unit A10B(MPUA10B)
               virent8090DEVXHXDSFUI9TC1(333213),   -- V8R25C00 for XHXDSFUI9TC1(SBOM) NetEngine XH16100 X8 9.6Tbps Switch Fabric Unit(SFUIA-9T6-B)
               virent8090DEVXHXDSFUI9TC2(333214),   -- V8R25C00 for XHXDSFUI9TC2(SBOM) NetEngine XH16200 X8 9.6Tbps Switch Fabric Unit(SFUIA-9T6-B)
               virent8090DEVXHXDLPUF4TC1(333215),   -- V8R25C00 for XHXDLPUF4TC1(SBOM) Flexible Card Line Processing Unit(LPUF-4T8A)
               virent8090DEVXHXDLPUF2TC2(333216),   -- V8R25C00 for XHXDLPUF2TC2(SBOM) Flexible Card Line Processing Unit(LPUF-2T4A)
               virent8090DEVXHXDLPUF2TC1(333217),   -- V8R25C00 for XHXDLPUF2TC1(SBOM) Flexible Card Line Processing Unit(LPUF-2T4A)
               virent8090DEVCR8D00EKNIC0(437814),   -- V8R22C10 for CR8D00EKNIC0(SBOM) 40-Port 100GBase-QSFP28 Integrated Line Processing Unit(LPUIA-4T)
               virent8090DEVCR8D00EINBC2(142863),   -- V8R22C10 for CR8D00EINBC2(SBOM) 32-Port 100GBase-QSFP28 Integrated Line Processing Unit CM(LPUI-3T2A-CM)
               virent8090DEVCR8D00LRXIC0(544919),   -- V8R22C10 for CR8D00LRXIC0(SBOM) 72-Port 10GE(SFP+)/GE(SFP) Integrated Line Processing Unit(LPUIA-2T)
               virent8090DEVCR8D00EENBCY(218591),   -- V8R22C10 for CR8D00EENBCY(SBOM) 20-Port 100GBase-QSFP28 Integrated Line Processing Unit CM(LPUI-2TA-CM)
               virent8090DEVCR8D00LRXFCY(142985),   -- V8R22C10 for CR8D00LRXFCY(SBOM) 72-Port 10GE-SFP+ Integrated Line Processing Unit(LPUI-1TA-CM)
               virent8090DEVIG2DLPUFT003(200560),   -- V8R22C10 for IG2DLPUFT003(SBOM) Flexible Card Line Processing Unit(LPUF-1T2A)
               virent8090DEVIG2DLPUFM306(641528),   -- V8R22C10 for IG2DLPUFM306(SBOM) Flexible Card Line Processing Unit(LPUF-483A)
               virent8090DEVCR5DEDVE8N7C(492102),   -- V8R22C10 for CR5DEDVE8N7C(SBOM) 16-Port 50G/8-Port 100GBase-QSFP28 FlexE Integrated Line Processing Unit L(LPUI-1T2-L)
               virent8090DEVCR5DEDVE8N7D(956150),   -- V8R22C10 for CR5DEDVE8N7D(SBOM) 16-Port 50G/8-Port 100GBase-QSFP28 FlexE/MACsec Integrated Line Processing Unit CM(LPUI-1T2-CM)
               virent8090DEVCR5DLPUFT07H(135161),   -- V8R22C10 for CR5DLPUFT07H(SBOM) Flexible Card Line Processing Unit(LPUF-1T2)
               virent8090DEVCR5DLPUF537G(163641),   -- V8R22C10 for CR5DLPUF537G(SBOM) Flexible Card Line Processing Unit(LPUF-53)
               virent8090DEVCR5DLPUFF397(540645),   -- V8R22C10 for CR5DLPUFF397(SBOM) Flexible Card Line Processing Unit(LPUF-243)
               virent8090DEVCR5DLPUFF37I(981704),   -- V8R22C10 for CR5DLPUFF37I(SBOM) 8-Port GE-SFP/10GE-SFP+ and 16-Port GE-SFP Flexible Card Line Processing Unit(LPUI-243-CM, 4*10GE+20*GE by default, one sub-slot for flexible card)
               virent8090DEVCR5DLPUFM37G(441838),   -- V8R22C10 for CR5DLPUFM37G(SBOM) Flexible Card Line Processing Unit(LPUF-483)
               virent8090DEVCR5DLPUFM37J(576508),   -- V8R22C10 for CR5DLPUFM37J(SBOM) Flexible Card Line Processing Unit(LPUF-483-CM, enable slot 0 by default)
               virent8090DEVCR5DLPUFM37I(505713),   -- V8R22C10 for CR5DLPUFM37I(SBOM) Flexible Card Line Processing Unit(LPUF-483-E-CM, enable slot 0 by default)
               virent8090DEVCR5DLPUFM37M(848667),   -- V8R22C10 for CR5DLPUFM37M(SBOM) 24-Port GE-SFP/10GE-SFP+ Flexible Card Line Processing Unit(LPUI-483-CM, Enable 12*10GE+12*GE by default, Supporting one sub-slot for flexible card)
               virent8090DEVCR5DLPUF537D(776113),   -- V8R22C10 for CR5DLPUF537D(SBOM) Flexible Card Line Processing Unit(LPUF-53)
               virent8090DEVCR5DLPUFF37X(900536),   -- V8R22C10 for CR5DLPUFF37X(SBOM) Flexible Card Line Processing Unit(LPUF-243)
               virent8090DEVCR5DLPUFF37W(620808),   -- V8R22C10 for CR5DLPUFF37W(SBOM) 8-Port GE-SFP/10GE-SFP+ and 16-Port GE-SFP Flexible Card Line Processing Unit(LPUI-243-CM, 4*10GE+20*GE by default, one sub-slot for flexible card)
               virent8090DEVCR5DLPUFM37Y(575487),   -- V8R22C10 for CR5DLPUFM37Y(SBOM) Flexible Card Line Processing Unit(LPUF-483)
               virent8090DEVCR5DLPUFM37Q(560576),   -- V8R22C10 for CR5DLPUFM37Q(SBOM) Flexible Card Line Processing Unit(LPUF-483-CM, enable slot 0 by default)
               virent8090DEVCR5DLPUFM37S(924968),   -- V8R22C10 for CR5DLPUFM37S(SBOM) Flexible Card Line Processing Unit(LPUF-483-E-CM, enable slot 0 by default)
               virent8090DEVCR5DLPUFM37U(822545),   -- V8R22C10 for CR5DLPUFM37U(SBOM) 24-Port GE-SFP/10GE-SFP+ Flexible Card Line Processing Unit(LPUI-483-CM, Enable 12*10GE+12*GE by default, Supporting one sub-slot for flexible card)
               virent8090DEVCR5DLPUFT07G(157738),   -- V8R22C10 for CR5DLPUFT07G(SBOM) Flexible Card Line Processing Unit(LPUF-1T2A)
               virent8090DEVCR5D00E8NB7T(477667),   -- V8R22C10 for CR5D00E8NB7T(SBOM) 16-Port 50G/8-Port 100GBase-QSFP28 FlexE/MACsec Integrated Line Processing Unit CM(LPUI-1T2A-CM)
               virent8090DEVCR5DLPUFT07K(558494),   -- V8R22C10 for CR5DLPUFT07K(SBOM) Flexible Card Line Processing Unit(LPUF-1T2A-E)
               virent8090DEVCR5DLPUF537H(248937),   -- V8R22C10 for CR5DLPUF537H(SBOM) Flexible Card Line Processing Unit(LPUF-53A)
               virent8090DEVCR5DLPUFF396(632083),   -- V8R22C10 for CR5DLPUFF396(SBOM) Flexible Card Line Processing Unit(LPUF-243A)
               virent8090DEVCR5DLPUFF39A(827356),   -- V8R22C10 for CR5DLPUFF39A(SBOM) 8-Port GE-SFP/10GE-SFP+ and 16-Port GE-SFP Flexible Card Line Processing Unit(LPUI-243A-CM, 4*10GE+20*GE by default, one sub-slot for flexible card)
               virent8090DEVCR5DLPUFM37H(530429),   -- V8R22C10 for CR5DLPUFM37H(SBOM) Flexible Card Line Processing Unit(LPUF-483A)
               virent8090DEVCR5DLPUFM37W(495978),   -- V8R22C10 for CR5DLPUFM37W(SBOM) Flexible Card Line Processing Unit(LPUF-483A)
               virent8090DEVCR5DLPUFM37K(715222),   -- V8R22C10 for CR5DLPUFM37K(SBOM) 24-Port GE-SFP/10GE-SFP+ Flexible Card Line Processing Unit(LPUI-483A-CM, Enable 12*10GE+12*GE by default, Supporting one sub-slot for flexible card)
               virent8090DEVME0DMSUFT07G(706119),   -- V8R22C10 for ME0DMSUFT07G(SBOM) Flexible Card Multi Service Unit(MSUF-1T2,2 sub-slots)
               virent8090DEVME0DBSUFT07F(165590),   -- V8R22C10 for ME0DBSUFT07F(SBOM) Flexible Card Broadband Service Unit(BSUF-1T2A,2 sub-slots)
               virent8090DEVME0DBSUFT07M(768000),   -- V8R22C10 for ME0DBSUFT07M(SBOM) Flexible Card Broadband Service Unit(BSUF-1T2-E,2 sub-slots)
               virent8090DEVME0DMSUFT07M(315631),   -- V8R22C10 for ME0DMSUFT07M(SBOM) Flexible Card Multi Service Unit(MSUF-1T2-E,2 sub-slots)
               virent8090DEVME0DBSUFT07N(995118),   -- V8R22C10 for ME0DBSUFT07N(SBOM) Flexible Card Broadband Service Unit(BSUF-1T2A-E,2 sub-slots)
               virent8090DEVME0DMSUFT07N(834245),   -- V8R22C10 for ME0DMSUFT07N(SBOM) Flexible Card Multi Service Unit(MSUF-1T2A-E,2 sub-slots)
               virent8090DEVME0DBSUFM07B(466368),   -- V8R22C10 for ME0DBSUFM07B(SBOM) Flexible Card Broadband Service Unit(BSUF-243-E,2 sub-slots)
               virent8090DEVME0DBSUFM07K(458457),   -- V8R22C10 for ME0DBSUFM07K(SBOM) Flexible Card Broadband Service Unit(BSUF-483-E,2 sub-slots)
               virent8090DEVME0DBSUFM07E(919145),   -- V8R22C10 for ME0DBSUFM07E(SBOM) Flexible Card Broadband Service Unit(BSUF-243-E,2 sub-slots)
               virent8090DEVME0DBSUFM07G(333879),   -- V8R22C10 for ME0DBSUFM07G(SBOM) Flexible Card Broadband Service Unit(BSUF-483-E,2 sub-slots)
               virent8090DEVCX6DISUFT014(390887),   -- V8R22C10 for CX6DISUFT014(SBOM) Flexible Card Integrated Service Unit(ISUF-1TA)
               virent8090DEVCX6DISUFT016(392871),   -- V8R22C10 for CX6DISUFT016(SBOM) Flexible Card Integrated Service Unit(ISUF-1T)
               virent8090DEVCX6DISUFM312(440866),   -- V8R22C10 for CX6DISUFM312(SBOM) Flexible Card Line Processing Unit(ISUF-483A)
			   virent8090DEVCR8PM1DBADM1(226170),  --NetEngine 8000 M1D, DC Power (Port Capacity 4*100GE/50GE+16*25GE/10GE/GE/FE+8*10GE/GE/FE,exclude auxiliary materials)
               virent8090DEVCR8PM1DBADM0(226171),  --NetEngine 8000 M1D, DC Power (Port Capacity 4*100GE/50GE+16*25GE/10GE/GE/FE+8*10GE/GE/FE,exclude auxiliary materials)
               virent8090DEVCR8PM1DBAAM1(226172),  --NetEngine 8000 M1D, AC Power (Port Capacity 4*100GE/50GE+16*25GE/10GE/GE/FE+8*10GE/GE/FE,exclude auxiliary materials)
               virent8090DEVCR8PM1DBAAM0(226173),  --NetEngine 8000 M1D, AC Power (Port Capacity 4*100GE/50GE+16*25GE/10GE/GE/FE+8*10GE/GE/FE,exclude auxiliary materials)
               virent8090DEVCR8PM1DBADM5(226174),  --NetEngine 8000 M1D, DC Power (Port Capacity 4*100GE/50GE+16*25GE/10GE/GE/FE+8*10GE/GE/FE,exclude auxiliary materials)
               virent8090DEVCR8PM1DBAAM5(226175),  --NetEngine 8000 M1D, AC Power (Port Capacity 4*100GE/50GE+16*25GE/10GE/GE/FE+8*10GE/GE/FE,exclude auxiliary materials)
               virent8090DEVANRD00CXPB02(226159),  --System Control, Cross-connect and Multi-protocol Process Unit with 160G
               virent8090DEVCR8PM1CBASC7(226199),  --NetEngine 8000 M1C, 2*AC Power, Port Capacity 16*10GE+8*GE(o)+4*GE(e), None of the ports are available by default
               virent8090DEVCR8PM1CBASA6(226200),  --NetEngine 8000 M1C(A), 2*DC Power, Port Capacity 16*10GE+8*GE(o)+4*GE(e), None of the ports are available by default
               virent8090DEVCR8PM1CBASA7(226201),  --NetEngine 8000 M1C(A), 2*AC Power, Port Capacity 16*10GE+8*GE(o)+4*GE(e), None of the ports are available by default
               virent8090DEVANGMHSTH0100(226206),  --ATN 910C-H DC Basic Configuration(Includes Fixed Enable Interface (4*10GE/GE/FE(o)+4*GE/FE(o)+4*GE/FE(e))/Dual Power/FAN/Chassis)
               virent8090DEVANGMHSTH0200(226208),  --ATN 910C-H AC Basic Configuration(Includes Fixed Enable Interface (4*10GE/GE/FE(o)+4*GE/FE(o)+4*GE/FE(e))/Power/FAN/Chassis)
               virent8090DEVANGMHSTS0200(226209),  --ATN 910C-S AC Basic Configuration(Includes Fixed Enable Interface (4*10GE/GE/FE(o)+4*GE/FE(o)+4*GE/FE(e))/Power/FAN/Chassis)
               virent8090DEVCP8PHST20A06(226214),  --NetEngine A821 AC System (2*10GE/GE/FE+8*GE/FE(o)+8*GE/FE(e))
               virent8090DEVCP8PHST20A08(226215),  --NetEngine A821 AC System (2*10GE/GE/FE+8*GE/FE(o)+8*GE/FE(e))
               virent8090DEVCP8PHST10A10(226216),  --NetEngine A813 AC System (6*GE/FE(o)+8*GE/FE(e))
               virent8090DEVCP8PHSB2EA04(226217),  --NetEngine A821 E AC Chassis(A) (6*10GE/GE/FE(o)+4*GE/FE(o)+8*GE/FE(e), Default 2*10GE/GE/FE(o)+8*GE/FE(o)+8*GE/FE(e))
               virent8090DEVCP8PHSB2EA05(226218),  --NetEngine A821 E AC Chassis (6*10GE/GE/FE(o)+4*GE/FE(o)+8*GE/FE(e), Default 2*10GE/GE/FE(o)+8*GE/FE(o)+8*GE/FE(e))
               virent8090DEVCP8PHST2EA29(226219),  --NetEngine A822 E AC Chassis(A)(2*10GE/GE/FE(o)+4*GE/FE(o)+8*GE/FE(e))
               virent8090DEVCP8PHST2EA28(226220),  --NetEngine A822 E AC Chassis (2*10GE/GE/FE(o)+4*GE/FE(o)+8*GE/FE(e))
               virent8090DEVCP8PHST2EA2C(525150),  --NetEngine A822 E AC Chassis (2*10GE/GE/FE(o)+4*GE/FE(o)+8*GE/FE(e))
               virent8090DEVCP8PHST1EA0A(226223),  --NetEngine A813 E AC Chassis (A)(6*GE/FE(o)+8*GE/FE(e))
               virent8090DEVCP8PHST1EAAB(226224),  --NetEngine A813 E AC Chassis (6*GE/FE(o)+8*GE/FE(e))
               virent8090DEVANPM01HOST7(226225),  --ATN 905-S System,AC,4*GE/FE(o),4*GE/FE(e)
               virent8090DEVANPM01HOST8(525151),  --ATN 905-S System,AC,4*GE/FE(o),4*GE/FE(e)
               virent8090DEVCR5D0SRUAI7A(226160),  --Switch and Route Processing Unit A21A(SRUA-1TA-H, 32G Memory)
               virent8090DEVCR5D0SRUAI7B(226161),  --Switch and Route Processing Unit A21(SRUA-1T-H, 32G Memory)
               virent8090DEVCX6D0SRUAI7A(226162),  --Switch and Route Processing Unit A21(SRUA-1T-H, 32G Memory)
               virent8090DEVCX6D0SRUAI1B(226163),  --Switch and Route Processing Unit A21(SRUA-1T-H, 32G Memory)
               virent8090DEVTNRD0SRUAI7A(226164),  --Switch and Route Processing Unit A21(SRUA-1T-H, 32G Memory)
               virent8090DEVME0D0SRUAI7B(226165),  --Switch and Route Processing Unit A21A(SRUA-1TA-H, 32G Memory)
               virent8090DEVME0D0SRUAI7C(226166),  --Switch and Route Processing Unit A21(SRUA-1T-H, 32G Memory)
               virent8090DEVIG2D0SRUAI7A(226167),  --Switch and Route Processing Unit A21A(SRUA-1TA-H, 32G Memory)
               virent8090DEVCR5D0SRUAH7C(226168),  --Switch and Route Processing Unit A20A(SRUA-480A-I, 32G Memory)
               virent8090DEVCR5D0SRUAH7D(226169),  --Switch and Route Processing Unit A20(SRUA-480-I, 32G Memory)
               virent8090DEVCX6D0SRUAH7B(226176),  --Switch and Route Processing Unit A20(SRUA-480-I, 32G Memory)
               virent8090DEVCX6D0SRUAH1A(226177),  --Switch and Route Processing Unit A20(SRUA-480-I, 32G Memory)
               virent8090DEVTNRD0SRUAH7B(226178),  --Switch and Route Processing Unit A20(SRUA-480-I, 32G Memory)
               virent8090DEVME0D0SRUAH7D(226179),  --Switch and Route Processing Unit A20A(SRUA-480A-I, 32G Memory)
               virent8090DEVME0D0SRUAH7E(226180),  --Switch and Route Processing Unit A20(SRUA-480-I, 32G Memory)
               virent8090DEVME0D0SRUAH7A(226181),  --Switch and Route Processing Unit A22A(SRUA-480A-J, 32G Memory)
               virent8090DEVME0D0SRUAH7P(226182),  --Switch and Route Processing Unit A22(SRUA-480-J, 32G Memory)
               virent8090DEVCR81IPU1T2CG(228002),  --Integrated Network Processing Unit (IPUA-1T2)
               virent8090DEVCR81IPU480AF(228003),  --Integrated Network Processing Unit (IPUA-480)
               virent8090DEVCR81IPU2TA9(228004),  --Integrated Network Processing Unit (IPUA-2T)
               virent8090DEVCR5DVSUIK07K(226183),  --Integrated Service Unit 400(VSUI-400)
               virent8090DEVCR5DVSUIK07Z(226184),  --Integrated Service Unit 400(VSUI-400B)
               virent8090DEVCR5DVSUIK08Z(434371),  -- V8R25C10 for CR5DVSUIK08Z(SBOM) Multi-Function Integrated Service Unit 400(VSUI-400A-S)
               virent8090DEVCR5DVSUIK07P(226185),  --Integrated Service Unit 400(VSUI-400A)
               virent8090DEVCR5DVSUIK07L(226186),  --Integrated Service Unit 400(VSUI-400)
               virent8090DEVCR5DVSUIK07O(226187),  --Integrated Service Unit 400(VSUI-400-S)
               virent8090DEVME0DVSUIK07G(226188),  --Integrated Service Unit 400(VSUI-400)
               virent8090DEVME0DVSUIK07P(226189),  --Integrated Service Unit 400(VSUI-400A)
               virent8090DEVCR5DVSUIK07J(226190),  --Integrated Service Unit 400(VSUI-400A-E)
               virent8090DEVCR5DVSUIK07V(226191),  --Enhanced Multi-Function Integrated Service Unit 400(VSUI-400-E)
               virent8090DEVCR5DVSUIK07R(226192),  --Enhanced Multi-Function Integrated Service Unit 400(VSUI-400-E)
               virent8090DEVCR5DVSUIK07W(226193),  --Enhanced Multi-Function Integrated Service Unit 400(VSUI-400A-E)
               virent8090DEVCR5DVSUIK07S(226194),  --Enhanced Multi-Function Integrated Service Unit 400(VSUI-400A-E)
               virent8090DEVME0DVSUIK07R(226195),  --Integrated Service Unit 400(VSUI-400-E)
               virent8090DEVME0DVSUIK07S(226196),  --Integrated Service Unit 400(VSUI-400A-E)
               virent8090DEVCR5DVSUIK07I(226198),  --Integrated Service Unit 400(VSUI-400A-S)
               virent8090DEVCR5DVSUIK07X(226226),  --Multi-Function Integrated Service Unit 400(VSUI-400-S)
               virent8090DEVCR5DVSUIK07T(226227),  --Multi-Function Integrated Service Unit 400(VSUI-400-S)
               virent8090DEVCR5DVSUIK07Y(226228),  --Multi-Function Integrated Service Unit 400(VSUI-400A-S)
               virent8090DEVCR5DVSUIK07U(226229),  --Multi-Function Integrated Service Unit 400(VSUI-400A-S)
               virent8090DEVCR5DJYSUK074(226230),  --Public Security Service Unit(PSSU-A)
               virent8090DEVCR5DJYSUK076(226231),  --Public Security Service Unit(PSSU-S)
               virent8090DEVME0DVSUIK07T(226232),  --Integrated Service Unit 400(VSUI-400-S)
               virent8090DEVME0DVSUIK07U(226233),  --Integrated Service Unit 400(VSUI-400-S)
               virent8090DEVME0DVSUIK07V(226234),  --Integrated Service Unit 400(VSUI-400A-S)
               virent8090DEVME0DJYSUK072(226235),  --Public Security Service Unit(PSSU-A)
               virent8090DEVME0DJYSUK074(226236),  --Public Security Service Unit(PSSU-S)
               virent8090DEVCR5D00EENB7T(892500),   -- V8R22C10 for CR5D00EENB7T(SBOM) 20-Port 100GBase-QSFP28 FlexE/MACsec Integrated Line Processing Unit CM(LPUI-2T-E-CM)
               virent8090DEVCR5DLPUF537P(948166),   -- V8R22C10 for CR5DLPUF537P(SBOM) Flexible Card Line Processing Unit(LPUF-53D)
               virent8090DEVCR5DLPUFF395(250006),   -- V8R22C10 for CR5DLPUFF395(SBOM) Flexible Card Line Processing Unit(LPUF-243D)
               virent8090DEVCR5DLPUFM398(778602),   -- V8R22C10 for CR5DLPUFM398(SBOM) Flexible Card Line Processing Unit(LPUF-483D)
               virent8090DEVCR5DLPUF5378(471965),   -- V8R22C10 for CR5DLPUF5378(SBOM) Flexible Card Line Processing Unit(LPUF-53)
               virent8090DEVCR5DLPUF5379(422392),   -- V8R22C10 for CR5DLPUF5379(SBOM) Flexible Card Line Processing Unit(LPUF-53A)
               virent8090DEVCR5DLPUF537Q(773447),   -- V8R22C10 for CR5DLPUF537Q(SBOM) Flexible Card Line Processing Unit(LPUF-53A)
               virent8090DEVCR5DLPUFF37J(417466),   -- V8R22C10 for CR5DLPUFF37J(SBOM) Flexible Card Line Processing Unit(LPUF-243)
               virent8090DEVCR5DLPUFF37U(824233),   -- V8R22C10 for CR5DLPUFF37U(SBOM) Flexible Card Line Processing Unit(LPUF-243A)
               virent8090DEVCR5DLPUFF37Q(625934),   -- V8R22C10 for CR5DLPUFF37Q(SBOM) 8-Port GE-SFP/10GE-SFP+ and 16-Port GE-SFP Flexible Card Line Processing Unit(LPUI-243A-CM, 4*10GE+20*GE by default, one sub-slot for flexible card)
               virent8090DEVCR5DLPUFF37V(820969),   -- V8R22C10 for CR5DLPUFF37V(SBOM) 8-Port GE-SFP/10GE-SFP+ and 16-Port GE-SFP Flexible Card Line Processing Unit(LPUI-243A-CM, 4*10GE+20*GE by default, one sub-slot for flexible card)
               virent8090DEVCR5DLPUFF37R(547778),   -- V8R22C10 for CR5DLPUFF37R(SBOM) 8-Port GE-SFP/10GE-SFP+ and 16-Port GE-SFP Flexible Card Line Processing Unit(LPUI-243-CM, 4*10GE+20*GE by default, one sub-slot for flexible card)
               virent8090DEVCR5DLPUFF37S(269662),   -- V8R22C10 for CR5DLPUFF37S(SBOM) 8-Port GE-SFP/10GE-SFP+ and 16-Port GE-SFP Flexible Card Line Processing Unit(LPUI-243-CM, 4*10GE+20*GE by default, one sub-slot for flexible card)
               virent8090DEVCR5DVSUIK07Q(793681),   -- V8R22C10 for CR5DVSUIK07Q(SBOM) Integrated Service Unit 400(VSUI-400A)
               virent8090DEVME0DVSUIK07Q(204391),   -- V8R22C10 for ME0DVSUIK07Q(SBOM) Integrated Service Unit 400(VSUI-400A)
               virent8090DEVCR5DLPUF537A(998152),   -- V8R22C10 for CR5DLPUF537A(SBOM) Flexible Card Line Processing Unit(LPUF-53)
               virent8090DEVCR5DLPUF537C(840258),   -- V8R22C10 for CR5DLPUF537C(SBOM) Flexible Card Line Processing Unit(LPUF-53A)
               virent8090DEVCR5DLPUFF39C(705910),   -- V8R22C10 for CR5DLPUFF39C(SBOM) Flexible Card Line Processing Unit(LPUF-243)
               virent8090DEVCR5DLPUFF398(609281),   -- V8R22C10 for CR5DLPUFF398(SBOM) Flexible Card Line Processing Unit(LPUF-243A)
               virent8090DEVCR5DLPUFF399(242316),   -- V8R22C10 for CR5DLPUFF399(SBOM) 8-Port GE-SFP/10GE-SFP+ and 16-Port GE-SFP Flexible Card Line Processing Unit(LPUI-243A-CM, 4*10GE+20*GE by default, one sub-slot for flexible card)
               virent8090DEVCR5DLPUFF39B(823300),   -- V8R22C10 for CR5DLPUFF39B(SBOM) 8-Port GE-SFP/10GE-SFP+ and 16-Port GE-SFP Flexible Card Line Processing Unit(LPUI-243-CM, 4*10GE+20*GE by default, one sub-slot for flexible card)
               virent8090DEVCR5DLPUFM37A(322248),   -- V8R22C10 for CR5DLPUFM37A(SBOM) Flexible Card Line Processing Unit(LPUF-483)
               virent8090DEVCR5DLPUFM37B(468309),   -- V8R22C10 for CR5DLPUFM37B(SBOM) Flexible Card Line Processing Unit(LPUF-483A)
               virent8090DEVCR5DLPUFM37D(520268),   -- V8R22C10 for CR5DLPUFM37D(SBOM) Flexible Card Line Processing Unit(LPUF-483A)
               virent8090DEVCR5DLPUFM37E(472413),   -- V8R22C10 for CR5DLPUFM37E(SBOM) Flexible Card Line Processing Unit(LPUF-483-CM, enable slot 0 by default)
               virent8090DEVCR5DLPUFM37F(950192),   -- V8R22C10 for CR5DLPUFM37F(SBOM) Flexible Card Line Processing Unit(LPUF-483-E-CM, enable slot 0 by default)
               virent8090DEVCR5DLPUFM37N(665079),   -- V8R22C10 for CR5DLPUFM37N(SBOM) 24-Port GE-SFP/10GE-SFP+ Flexible Card Line Processing Unit(LPUI-483A-CM, Enable 12*10GE+12*GE by default, Supporting one sub-slot for flexible card)
               virent8090DEVCR5DLPUFM37L(670588),   -- V8R22C10 for CR5DLPUFM37L(SBOM) 24-Port GE-SFP/10GE-SFP+ Flexible Card Line Processing Unit(LPUI-483-CM, Enable 12*10GE+12*GE by default, Supporting one sub-slot for flexible card)
               virent8090DEVCR5DLPUFM39A(307470),   -- V8R22C10 for CR5DLPUFM39A(SBOM) Flexible Card Line Processing Unit(LPUF-483A, Supportting DIP)
               virent8090DEVCR5DLPUFM39B(418653),   -- V8R22C10 for CR5DLPUFM39B(SBOM) Flexible Card Line Processing Unit(LPUF-483, Supportting DIP)
               virent8090DEVCR5D00EENB7A(384144),   -- V8R22C10 for CR5D00EENB7A(SBOM) 20-Port 100GBase-QSFP28 Integrated Line Processing Unit (LPUI-2TA)
               virent8090DEVCR5D00EENB7D(660183),   -- V8R22C10 for CR5D00EENB7D(SBOM) 20-Port 100GBase-QSFP28 FlexE/MACsec Integrated Line Processing Unit CM(LPUI-2T-CM)
               virent8090DEVME0DBSUFM07C(585779),   -- V8R22C10 for ME0DBSUFM07C(SBOM) Flexible Card Broadband Service Unit(BSUF-243-E,2 sub-slots)
               virent8090DEVME0DBSUFM07J(639282),   -- V8R22C10 for ME0DBSUFM07J(SBOM) Flexible Card Broadband Service Unit(BSUF-483-E,2 sub-slots)
               virent8090DEVIG2D00EENB03(482016),   -- V8R22C10 for IG2D00EENB03(SBOM) 20-Port 100GBase-QSFP28 Integrated Line Processing Unit (LPUI-2TA)
               virent8090DEVCR5DLPUF5377(995282),   -- V8R22C10 for CR5DLPUF5377(SBOM) Flexible Card Line Processing Unit(LPUF-53)
               virent8090DEVCR5DLPUF537B(486588),   -- V8R22C10 for CR5DLPUF537B(SBOM) Flexible Card Line Processing Unit(LPUF-53)
               virent8090DEVCR5DLPUFF37M(940300),   -- V8R22C10 for CR5DLPUFF37M(SBOM) Flexible Card Line Processing Unit(LPUF-243)
               virent8090DEVCR5DLPUFF37N(714849),   -- V8R22C10 for CR5DLPUFF37N(SBOM) Flexible Card Line Processing Unit(LPUF-243)
               virent8090DEVCR5DLPUFF37P(335140),   -- V8R22C10 for CR5DLPUFF37P(SBOM) Flexible Card Line Processing Unit(LPUF-243A)
               virent8090DEVCR5DLPUFF37T(933293),   -- V8R22C10 for CR5DLPUFF37T(SBOM) 8-Port GE-SFP/10GE-SFP+ and 16-Port GE-SFP Flexible Card Line Processing Unit(LPUI-243-CM, 4*10GE+20*GE by default, one sub-slot for flexible card)
               virent8090DEVCR5DLPUFM37P(733811),   -- V8R22C10 for CR5DLPUFM37P(SBOM) Flexible Card Line Processing Unit(LPUF-483)
               virent8090DEVCR5DLPUFM37R(778558),   -- V8R22C10 for CR5DLPUFM37R(SBOM) Flexible Card Line Processing Unit(LPUF-483-CM, enable slot 0 by default)
               virent8090DEVCR5DLPUFM37T(541057),   -- V8R22C10 for CR5DLPUFM37T(SBOM) Flexible Card Line Processing Unit(LPUF-483-E-CM, enable slot 0 by default)
               virent8090DEVCR5DLPUFM37V(488097),   -- V8R22C10 for CR5DLPUFM37V(SBOM) 24-Port GE-SFP/10GE-SFP+ Flexible Card Line Processing Unit(LPUI-483-CM, Enable 12*10GE+12*GE by default, Supporting one sub-slot for flexible card)
               virent8090DEVCR5DLPUFM399(175781),   -- V8R22C10 for CR5DLPUFM399(SBOM) Flexible Card Line Processing Unit(LPUF-483, Supportting DIP)
               virent8090DEVCR5D00EENB7F(811462),   -- V8R22C10 for CR5D00EENB7F(SBOM) 20-Port 100GBase-QSFP28 Integrated Line Processing Unit (LPUI-2TA-E)
               virent8090DEVME0DBSUFM07H(546995),   -- V8R22C10 for ME0DBSUFM07H(SBOM) Flexible Card Broadband Service Unit(BSUF-483-E,2 sub-slots)
               virent8090DEVME0DBSUFM07F(303620),   -- V8R22C10 for ME0DBSUFM07F(SBOM) Flexible Card Broadband Service Unit(BSUF-243-E,2 sub-slots)
               virent8090DEVCR5D00EENB7U(303621),   -- V8R22C10 for CR5D00EENB7U(SBOM) 20-Port 100GBase-QSFP28 Integrated Line Processing Unit L(LPUI-2T-L)
               virent8090DEVCR5DVSUIK091(303622),   -- V8R22C10 for CR5DVSUIK091(SBOM) Integrated Service Unit 400(VSUI-400-E)
               virent8090DEVCR5DVSUIK093(303623),   -- V8R22C10 for CR5DVSUIK093(SBOM) Integrated Service Unit 400(VSUI-400-S)
               virent8090DEVME0DVSUIK07W(303624),    -- V8R22C10 for ME0DVSUIK07W(SBOM) Integrated Service Unit 400(VSUI-400-S)
               virent8090DEVCR8DMPUF8AF4(115245),   -- V8R22C10 for CR8DMPUF8AF4(SBOM) NetEngine 8000E F Main Processing Unit B1A(MPUB1A)
               virent8090DEVCR8D00LRXFD6(693699),   -- V8R22C10 for CR8D00LRXFD6(SBOM) 72-Port 25GE(SFP28)/10GE(SFP+)/GE(SFP) Integrated Line Processing Unit CM(LPUI-2T-CM)
               virent8090DEVCR8D00EKNBD6(285562),   -- V8R22C10 for CR8D00EKNBD6(SBOM) 40-Port 100GBase-QSFP28 Integrated Line Processing Unit CM(LPUI-4T-CM)
               virent8090DEVCR8D00EENBD7(177236),   -- V8R22C10 for CR8D00EENBD7(SBOM) 20-Port 100GBase-QSFP28 Integrated Line Processing Unit CM(LPUI-2T-CM)
               virent8090DEVCR8DE4KEFND0(717476),   -- V8R22C10 for CR8DE4KEFND0(SBOM) 4-Port 400GBase-QSFP-DD + 24-Port 100GBase-QSFP28 Integrated Line Processing Unit CM (LPUI-4T-CM)
               virent8090DEVCR8DEANCJXDB(452016),   -- V8R22C10 for CR8DEANCJXDB(SBOM) 10-Port 100GBase-QSFP28 + 36-Port 25GE(SFP28)/10GE(SFP+)/GE(SFP) Integrated Line Processing Unit CM(LPUI-2T-CM)
               virent8090DEVCR8D00LRXFD8(722152),   -- V8R22C10 for CR8D00LRXFD8(SBOM) 72-Port 25GE(SFP28)/10GE(SFP+)/GE(SFP) Integrated Line Processing Unit L CM(LPUI-2T-L-CM)
               virent8090DEVCR8D00EKNBD8(679585),   -- V8R22C10 for CR8D00EKNBD8(SBOM) 40-Port 100GBase-QSFP28 Integrated Line Processing Unit L CM(LPUI-4T-L-CM)
               virent8090DEVCR8D00EENBD9(964479),   -- V8R22C10 for CR8D00EENBD9(SBOM) 20-Port 100GBase-QSFP28 Integrated Line Processing Unit L CM(LPUI-2T-L-CM)
               virent8090DEVCR8D00LRXFD7(422375),   -- V8R22C10 for CR8D00LRXFD7(SBOM) 72-Port 25GE(SFP28)/10GE(SFP+)/GE(SFP) Integrated Line Processing Unit CM(LPUI-2TA-CM)
               virent8090DEVCR8D00EKNBD7(855837),   -- V8R22C10 for CR8D00EKNBD7(SBOM) 40-Port 100GBase-QSFP28 Integrated Line Processing Unit CM(LPUI-4TA-CM)
               virent8090DEVCR8D00EENBDD(640421),   -- V8R22C10 for CR8D00EENBDD(SBOM) 20-Port 100GBase-QSFP28 Integrated Line Processing Unit CM(LPUI-2TA-CM)
               virent8090DEVCR8DE4KEFNF1(818326),   -- V8R22C10 for CR8DE4KEFNF1(SBOM) 4-Port 400GBase-QSFP-DD + 24-Port 100GBase-QSFP28 Integrated Line Processing Unit CM (LPUI-4TA-CM)
               virent8090DEVCR8DEANCJXDD(620583),   -- V8R22C10 for CR8DEANCJXDD(SBOM) 10-Port 100GBase-QSFP28 + 36-Port 25GE(SFP28)/10GE(SFP+)/GE(SFP) Integrated Line Processing Unit CM(LPUI-2TA-CM)
               virent8090DEVCR8D00LRXFD9(837511),   -- V8R22C10 for CR8D00LRXFD9(SBOM) 72-Port 25GE(SFP28)/10GE(SFP+)/GE(SFP) Integrated Line Processing Unit L(LPUI-2TA-L-CM)
               virent8090DEVCR8D00EKNBD9(336731),   -- V8R22C10 for CR8D00EKNBD9(SBOM) 40-Port 100GBase-QSFP28 Integrated Line Processing Unit L CM(LPUI-4TA-L-CM)
               virent8090DEVCR8D00EENBDA(288688),   -- V8R22C10 for CR8D00EENBDA(SBOM) 20-Port 100GBase-QSFP28 Integrated Line Processing Unit L CM(LPUI-2TA-L-CM)
               virent8090DEVCR8DEANEWAD0(359892),   -- V8R25C00 for CR8DEANEWAD0(SBOM) 10-Port 100GBase-QSFP28 + 36-Port 25GE(SFP28)/10GE(SFP+)/GE(SFP) Integrated Line Processing Unit(LPUI-2TA-E-G)
               virent8090DEVCR8D00EKWAD0(359891),   -- V8R25C00 for CR8D00EKWAD0(SBOM) Integrated Line Processing Unit(LPUI-4TA-G)
               virent8090DEVCR8DVSUIWAC0(359893),   -- V8R25C00 for CR8DVSUIWAC0(SBOM) Dedicated Service Unit 400(VSUI-400A-E-G)
               virent8090DEVCR8DVSUF80C2(161622),   -- V8R25C00 for CR8DVSUF80C2(SBOM) Flexible Card Versatile Service Unit 800(VSUF-800A)
               virent8090DEVCR8D8VUF8HC1(161620),   -- V8R25C00 for CR8D8VUF8HC1(SBOM) Flexible Card Versatile Service Unit 800(VSUF-800)
               virent8090DEVCR8DMSUF80C0(161623),   -- V8R25C00 for CR8DMSUF80C0(SBOM) Flexible Card Multi-Function Service Unit 800(MSUF-800)
               virent8090DEVCR8DMSUF80C1(161624),   -- V8R25C00 for CR8DMSUF80C1(SBOM) Flexible Card Multi-Function Service Unit 800(MSUF-800A)
               virent8090DEVCR8DVSUFWAC2(679807),   -- V8R25C00 for CR8DVSUFWAC2(SBOM) Flexible Card Dedicated Service Unit(VSUF-A-G)
               virent8090DEVCR8D0MPUAWAG(359890),   -- V8R25C00 for CR8D0MPUAWAG(SBOM) NetEngine 8000E Main Processing Unit A1B-G(MPUA1B-G)
               virent8090DEVCR8DVSUF8EC1(161625),   -- V8R25C00 for Flexible Card Versatile Service Unit 800(VSUF-800)
               virent8090DEVCR8DVSUF8EC0(161626),   -- V8R25C00 for Flexible Card Versatile Service Unit 800(VSUF-800A)
               virent8090DEVCR8DMSUFEC01(161627),   -- V8R25C00 for Flexible Card Multi-Function Service Unit 800(MSUF-800)
               virent8090DEVCR8DMSUF8EC0(161628),   -- V8R25C00 for Flexible Card Multi-Function Service Unit 800(MSUF-800A)
               virent8090DEVCR8S16APTHC1(161630),   -- V8R25C10 for CR8S16APTHC1(SBOM) Flexible Card Threat Prortection Unit(TPUF-800A)
               virent8090DEVCR5DVSUIK08A(434370),   -- V8R25C10 for CR5DVSUIK08A(SBOM) Enhanced Multi-Function Integrated Service Unit 400(VSUI-400A-E)
               virent8090DEVGPVF1SPCATPU(161629),  -- V8R25C10 for GPVF1SPCATPU(PcbName)
               virent8090DEVCR8DE4KFBND1(716032),   -- V8R22C10 for CR8DE4KFBND1(SBOM) 4-Port 400GBase-QSFP-DD + 24-Port 100GBase-QSFP28 Integrated Line Processing Unit CM (LPUI-4TA-L-CM)
               virent8090DEVCR8DEANCJXDE(209467),   -- V8R22C10 for CR8DEANCJXDE(SBOM) 10-Port 100GBase-QSFP28 + 36-Port 25GE(SFP28)/10GE(SFP+)/GE(SFP) Integrated Line Processing Unit L CM(LPUI-2TA-L-CM)
               virent8090DEVCR8DEANCJXDC(520236),   -- V8R22C10 for CR8DEANCJXDC(SBOM) 10-Port 100GBase-QSFP28 + 36-Port 25GE(SFP28)/10GE(SFP+)/GE(SFP) Integrated Line Processing Unit L CM(LPUI-2T-L-CM)
               virent8090DEVCR8DE4KFBND2(109608),   -- V8R22C10 for CR8DE4KFBND2(SBOM) 4-Port 400GBase-QSFP-DD + 24-Port 100GBase-QSFP28 Integrated Line Processing Unit CM (LPUI-4T-L-CM)
               virent8090DEVCR8DE8KE8NC7(109610),   -- V8R25C10 for CR8DE8KE8NC7(SBOM) 8-Port 400GBase-QSFP-DD + 8-Port 100GBase-QSFP28 Integrated Line Processing Unit CM(LPUI-4TA-CM,Enable 16*100GE by default)
               virent8090DEVCR8DE8KE8EC6(514839),   -- V8R25C10 for CR8DE8KE8EC6(SBOM) 8-Port 400GBase-QSFP-DD + 8-Port 100GBase-QSFP28 Integrated Line Processing Unit E CM(LPUI-4TA-E-CM,Enable 16*100GE by default)
               virent8090DEVCR8DE8KE8LC6(463240),   -- V8R25C10 for CR8DE8KE8LC6(SBOM) 8-Port 400GBase-QSFP-DD + 8-Port 100GBase-QSFP28 Integrated Line Processing Unit L CM(LPUI-4TA-L-CM,Enable 16*100GE by default)
               virent8090DEVCR5DLPUFT07J(558495),   -- V8R22C10 for CR5DLPUFT07J(SBOM) Flexible Card Line Processing Unit(LPUF-1T2-E)
               virent8090DEVCR8PM1DBASCP(303625),  -- V8R22C10 for CR8PM1DBASCP(SBOM) NetEngine 8000 M1D-B DC(Port Capacity 2*50GE+2*25GE/10GE+2*10GE+14*GE,default 2*25GE&all GE,no aux material)
               virent8090DEVCR5DLPUFME75(303626),   -- V8R23C00 for CR5DLPUFME75(SBOM) Flexible Card Line Processing Unit E(LPUF-486-E)
               virent8090DEVCR5DLPUFME76(303627),   -- V8R23C00 for CR5DLPUFME76(SBOM) Flexible Card Line Processing Unit E(LPUF-486-E)
               virent8090DEVCR5DLPUFME78(303628),   -- V8R23C00 for CR5DLPUFME78(SBOM) Flexible Card Line Processing Unit E(LPUF-486A-E)
               virent8090DEVME0DBSUFM07A(303629),   -- V8R23C00 for ME0DBSUFM07A(SBOM) Flexible Card Broadband Service Unit(BSUF-486,2 sub-slots)
               virent8090DEVME0DBSUFM079(303630),   -- V8R23C00 for ME0DBSUFM079(SBOM) Flexible Card Broadband Service Unit(BSUF-486-E,2 sub-slots)
               virent8090DEVME0DBSUFM07D(303631),   -- V8R23C00 for ME0DBSUFM07D(SBOM) Flexible Card Broadband Service Unit(BSUF-486A,2 sub-slots)
               virent8090DEVTNRPM4BASDC1(688029),  -- V8R22C10 for TNRPM4BASDC1(SBOM) PTN 6900-2-M4 Integrated DC Chassis Components(Including DC Power,Fan Box)
               virent8090DEVTNRPM4BASAC1(688030),  -- V8R22C10 for TNRPM4BASAC1(SBOM) PTN 6900-2-M4 Integrated AC Chassis Components(Including AC Power,Fan Box)
               virent8090DEVANND02CXPAC2(228001),  -- V8R22C10 ATN 980C,ANN3CXPA10,System Control,Cross-connect and Multi-protocol Process Unit with 360G
               virent8090DEVCR5DIPU1T292(689118),  -- V8R22C10 for CR5DIPU1T292(SBOM) Integrated Network Processing Unit (IPU-1T2-E)
               virent8090DEVCR8PM1DBASCX(689200),  -- V8R22C10 for CR8PM1DBASCX(SBOM) NetEngine 8000 M1D-B AC(A)(Port Capacity 2*50GE+2*25GE/10GE+2*10GE+14*GE,default 2*25GE&amp;all GE,no aux material)
               virent8090DEVCR8DIPU1T2M5(689201),  -- V8R22C10 for CR8DIPU1T2M5(SBOM) Integrated Network Processing Unit (IPU-1T2-E)
               virent8090DEVTNRDIPU1T293(689202),  -- V8R22C10 for TNRDIPU1T293(SBOM) Integrated Network Processing Unit (IPU-1T2-F)
               virent8090DEVCR8DIPU1T2ME(689203),  -- V8R22C10 for CR8DIPU1T2ME(SBOM) Integrated Network Processing Unit (IPUA-1T2-EN)
               virent8090DEVCR8DIPU1T2MG(689204),  -- V8R22C10 for CR8DIPU1T2MG(SBOM) Integrated Network Processing Unit (IPUA-1T2-E)
               virent8090DEVCR8DIPU480MH(689205),  -- V8R22C10 for CR8DIPU480MH(SBOM) Integrated Network Processing Unit (IPUA-480-E)
               virent8090DEVCR8DIPU1T2MK(689206),  -- V8R22C10 for CR8DIPU1T2MK(SBOM) Integrated Network Processing Unit (IPUA-1T2-EN)
			   virent8090DEVCR8DSFUI9TA0(265072),   -- V8R23C10 for CR8DSFUI9TA0(SBOM) NetEngine 8000 X16 9.6Tbps Switch Fabric Unit(SFUI-9T6-A)
               virent8090DEVCR8DSFUI9TA1(142655),   -- V8R23C10 for CR8DSFUI9TA1(SBOM) NetEngine 8000 X16 9.6Tbps Switch Fabric Unit(SFUIA-9T6-A)
               virent8090DEVCR8DSFUI9TB0(678751),   -- V8R23C10 for CR8DSFUI9TB0(SBOM) NetEngine 8000 X8 9.6Tbps Switch Fabric Unit(SFUI-9T6-B)
               virent8090DEVCR8DSFUI9TB1(569258),   -- V8R23C10 for CR8DSFUI9TB1(SBOM) NetEngine 8000 X8 9.6Tbps Switch Fabric Unit(SFUIA-9T6-B)
               virent8090DEVCR8D0SFUT6D1(116502),   -- V8R23C10 for CR8D0SFUT6D1(SBOM) NetEngine 8000 F 6T4 Switch Routing Unit(SRU-6T4-B)
               virent8090DEVCR8D0SFUT6D2(441885),   -- V8R23C10 for CR8D0SFUT6D2(SBOM) NetEngine 8000E F 6T4 Switch Routing Unit(SRUA-6T4-B)
			   virent8090DEVCR8DE6LEJKXP(441886),   -- V8R23C10 for CR8DE6LEJKXP(SBOM) 6-Port 800GBase-QSFP-DD + 36-Port 400GBase-QSFP-DD Integrated Line Processing Unit CM(LPUI-19T2-CM,Enable 6*400GE + 36*100GE by default)
			   virent8090DEVCR8D8MPUA1C0(205715),   -- V8R23C10 for CR8D8MPUA1C0(SBOM) NetEngine 8800 Main Processing Unit A1(MPUA1)
               virent8090DEVCR8D8MPUA2C0(364027),   -- V8R23C10 for CR8D8MPUA2C0(SBOM) NetEngine 8800 Main Processing Unit A2(MPUA2)
               virent8090DEVCR8D8SFU19A0(437796),   -- V8R23C10 for CR8D8SFU19A0(SBOM) NetEngine 8800 X4 19.2Tbps Switch Fabric Unit(SFUI-19T2-A)
               virent8090DEVCR8D8SFU19B0(376684),   -- V8R23C10 for CR8D8SFU19B0(SBOM) NetEngine 8800 X8 19.2Tbps Switch Fabric Unit(SFUI-19T2-B)
               virent8090DEVCR8DSFU19TA3(686021),   -- V8R25C10 for CR8DSFU19TA3(SBOM) NetEngine 8000 X16 19.2Tbps Switch Fabric Unit(SFUI-19T2-A)
               virent8090DEVCR8DSFU19TA4(686012),   -- V8R25C10 for CR8DSFU19TA4(SBOM) NetEngine 8000 X16 19.2Tbps Switch Fabric Unit(SFUIA-19T2-A)
               virent8090DEVCR8DSFU19TC0(686013),   -- V8R25C10 for CR8DSFU19TC0(SBOM) NetEngine 8000 X16 19.2Tbps Switch Fabric Unit(SFUI-19T2-A)
               virent8090DEVCR8DSFU19TC1(686014),   -- V8R25C10 for CR8DSFU19TC1(SBOM) NetEngine 8000 X16 19.2Tbps Switch Fabric Unit(SFUIA-19T2-A)
               virent8090DEVCR8D8SFU38A0(686015),   -- V8R25C10 for CR8D8SFU38A0(SBOM) NetEngine 8800 X16 38.4Tbps Switch Fabric Unit(SFUI-38T4-A, Enable 19.2T by default)
               virent8090DEVCR8D8SFU9TB0(223885),   -- V8R23C10 for CR8D8SFU9TB0(SBOM) NetEngine 8800 X8 9.6Tbps Switch Fabric Unit(SFUI-9T6-B)
               virent8090DEVCR8D8SFU9TC0(288568),   -- V8R23C10 for CR8D8SFU9TC0(SBOM) NetEngine 8800 X16 9.6Tbps Switch Fabric Unit(SFUI-9T6-C)
               virent8090DEVCR8D8SFU2TA0(667626),   -- V8R23C10 for CR8D8SFU2TA0(SBOM) NetEngine 8800 X4 2Tbps Switch Fabric Unit(SFUI-2T-A)
               virent8090DEVCR8D8SFU2TB0(490941),   -- V8R23C10 for CR8D8SFU2TB0(SBOM) NetEngine 8800 X8 2Tbps Switch Fabric Unit(SFUI-2T-B)
               virent8090DEVCR8D8SFU2TC0(287246),   -- V8R23C10 for CR8D8SFU2TC0(SBOM) NetEngine 8800 X16 2Tbps Switch Fabric Unit(SFUI-2T-C)
               virent8090DEVCR8D8E6LJKXP(329295),   -- V8R23C10 for CR8D8E6LJKXP(SBOM) 6-Port 800GBase-QSFP-DD + 36-Port 400GBase-QSFP-DD Integrated Line Processing Unit CM(LPUI-19T2-CM,Enable 6*400GE + 36*100GE by default)
               virent8090DEVCR8D8LPF2TC0(689587),   -- V8R23C10 for CR8D8LPF2TC0(SBOM) Flexible Card Line Processing Unit (LPUF-2T)
               virent8090DEVCR8D6LPF2TC0(679801),   -- V8R25C00 for CR8D6LPF2TC0(SBOM) Flexible Card Line Processing Unit (LPUF-2T)
               virent8090DEVCR8D8LPF2TL0(824667),   -- V8R23C10 for CR8D8LPF2TL0(SBOM) Flexible Card Line Processing Unit L(LPUF-2T-L)
               virent8090DEVCR8D8LPF1TE0(289558),   -- V8R23C10 for CR8D8LPF1TE0(SBOM) Flexible Card Line Processing Unit E(LPUF-1T-E)
               virent8090DEVCR8D6LPF1TE0(679802),   -- V8R25C00 for CR8D6LPF1TE0(SBOM) Flexible Card Line Processing Unit E(LPUF-1T-E)
               virent8090DEVCR8D8VSUK0C3(534152),   -- V8R23C10 for CR8D8VSUK0C3(SBOM) Integrated Service Unit 400(VSUI-400-E)
               virent8090DEVCR8D8LPF1TC0(299808),   -- V8R23C10 for CR8D8LPF1TC0(SBOM) Flexible Card Line Processing Unit (LPUF-1T)
               virent8090DEVCR8D6LPF1TC0(679800),   -- V8R25C00 for CR8D6LPF1TC0(SBOM) Flexible Card Line Processing Unit (LPUF-1T)
               virent8090DEVCR8DLPUFT6L4(165894),   -- V8R24C00 for CR8DLPUFT6L4(SBOM) Flexible Card Line Processing Unit L(LPUF-6T4-L)
               virent8090DEVCR8DLPUFT6T4(165895),   -- V8R24C00 for CR8DLPUFT6T4(SBOM) Flexible Card Line Processing Unit (LPUF-6T4)
               virent8090DEVCR8DLPUFT6E4(165896),   -- V8R24C00 for CR8DLPUFT6E4(SBOM) Flexible Card Line Processing Unit E(LPUF-6T4-E)
               virent8090DEVCR8DLPUFT6LA(165897),   -- V8R24C00 for CR8DLPUFT6LA(SBOM) Flexible Card Line Processing Unit L(LPUF-6T4A-L)
               virent8090DEVCR8DLPUFT6TA(165898),   -- V8R24C00 for CR8DLPUFT6TA(SBOM) Flexible Card Line Processing Unit(LPUF-6T4A)
               virent8090DEVCR8DLPUFT6EA(165899),   -- V8R24C00 for CR8DLPUFT6EA(SBOM) Flexible Card Line Processing Unit E(LPUF-6T4A-E)
               virent8090DEVCR8D8LPF6TC0(165900),   -- V8R24C00 for CR8D8LPF6TC0(SBOM) Flexible Card Line Processing Unit (LPUF-6T4)
               virent8090DEVCR5DLPUFM39D(172860),   -- V8R24C00 for CR5DLPUFM39D(SBOM) Flexible Card Line Processing Unit(LPUF-483D)
               virent8090DEVCR8D8LPF6TE0(165901),   -- V8R24C00 for CR8D8LPF6TE0(SBOM) Flexible Card Line Processing Unit E(LPUF-6T4-E)
               virent8090DEVCR8D8LPF6TL0(165902),   -- V8R24C00 for CR8D8LPF6TL0(SBOM) Flexible Card Line Processing Unit L(LPUF-6T4-L)
               virent8090DEVCR8B0BKP2CF1(165903),   -- V8R24C00 for CR8B0BKP2CF1(SBOM) Integrated Chassis Components(Port-side Intake)
			   virent8090DEVANPM001AICT9(215895),   -- V8R24C00 for ANPM001AICT9(SBOM) ATN 905-L System,AC,4*GE/FE(o),4*GE/FE(e)(without SRv6 and IFIT)
               virent8090DEVCR8B0BKP2CF2(165904),   -- V8R24C00 for CR8B0BKP2CF2(SBOM) Integrated Chassis Components(Port-side Exhaust)
               virent8090DEVCR8B0BKP2CF7(165905),   -- V8R24C00 for CR8B0BKP2CF7(SBOM) Integrated Chassis Components(Port-side Intake)
               virent8090DEVCR8B0BKP2CF8(165906),   -- V8R24C00 for CR8B0BKP2CF8(SBOM) Integrated Chassis Components(Port-side Exhaust)
               virent8090DEVCR8B0BKP2CF3(165907),   -- V8R24C00 for CR8B0BKP2CF3(SBOM) Integrated Chassis Components(Port-side Intake)
               virent8090DEVCR8B0BKP2CF4(165908),   -- V8R24C00 for CR8B0BKP2CF4(SBOM) Integrated Chassis Components(Port-side Exhaust)
               virent8090DEVCR8B0BKP2DF4(333218),   -- V8R25C00 for CR8B0BKP2DF4(SBOM) NetEngine 8000E F2D Integrated Chassis Components(Port-side Intake, including 3 fan box, excluding power module)
               virent8090DEVCR8B0BKP2DF5(333219),   -- V8R25C00 for CR8B0BKP2DF5(SBOM) NetEngine 8000E F2D Integrated Chassis Components(Port-side Exhaust, including 3 fan box, excluding power module)
               virent8090DEVANHB0BKP2DF0(333021),   -- V8R25C10 for ANHB0BKP2DF0(SBOM) NetEngine XH871 Integrated Chassis Components(Port-side Intake, including 3 fan box, excluding power module)
               virent8090DEVANHB0BKP2DF1(333012),   -- V8R25C10 for ANHB0BKP2DF1(SBOM) NetEngine XH871 Integrated Chassis Components(Port-side Exhaust, including 3 fan box, excluding power module)
               virent8090DEVCR8B0BKP2CF5(136614),   -- V8R25C10 for CR8B0BKP2CF5(SBOM) NetEngine 8000 F2C-P Integrated Chassis Components(Port-side Intake, excluding power module)
               virent8090DEVCR8B0BKP2CF6(136615),   -- V8R25C10 for CR8B0BKP2CF6(SBOM) NetEngine 8000 F2C-P Integrated Chassis Components(Port-side Exhaust, excluding power module)
               virent8090DEVCR8B0BKP2CFH(136612),   -- V8R25C10 for CR8B0BKP2CFH(SBOM) NetEngine 8000E F2C-P Integrated Chassis Components(Port-side Intake, excluding power module)
               virent8090DEVCR8B0BKP2CFI(136613),   -- V8R25C10 for CR8B0BKP2CFI(SBOM) NetEngine 8000E F2C-P Integrated Chassis Components(Port-side Exhaust, excluding power module)
               virent8090DEVGPVF1SPCA(161617),   -- V8R25C00 for GPVF1SPCA(PcbName)
               virent8090DEVGPVF4SPCA(161618),   -- V8R25C00 for GPVF4SPCA(PcbName)
               virent8090DEVGPVF4SPCB(161619),   -- V8R25C00 for GPVF4SPCB(PcbName)
               virent8090DEVCR8B0BKP2CF9(165976),   -- V8R25C00 for CR8B0BKP2CF9(SBOM) NetEngine 8000E F2C Programmable Computing Router Integrated Chassis Components(Port-side Intake, excluding power module)
               virent8090DEVCR8B0BKP2CFA(165977),   -- V8R25C00 for CR8B0BKP2CFA(SBOM) NetEngine 8000E F2C Programmable Computing Router Integrated Chassis Components(Port-side Intake, excluding power module)
               virent8090DEVCR8B0BKP2CFB(165978),   -- V8R25C00 for CR8B0BKP2CFB(SBOM) NetEngine 8000E F2C Programmable Computing Router Integrated Chassis Components(Port-side Exhaust, excluding power module)
               virent8090DEVCR8B0BKP2CFC(165979),   -- V8R25C00 for CR8B0BKP2CFC(SBOM) NetEngine 8000E F2C Programmable Computing Router Integrated Chassis Components(Port-side Exhaust, excluding power module)
               virent8090DEVCR8B0BKP2CFJ(165980),   -- V8R25C00 for CR8B0BKP2CFJ(SBOM) NetEngine 8000 F2C Programmable Computing Router Integrated Chassis Components(Port-side Intake, excluding power module)
               virent8090DEVCR8B0BKP2CFK(165981),   -- V8R25C00 for CR8B0BKP2CFK(SBOM) NetEngine 8000 F2C Programmable Computing Router Integrated Chassis Components(Port-side Exhaust, excluding power module)
               virent8090DEVCR8DIPU2T4M1(165911),   -- V8R24C00 for CR8DIPU2T4M1(SBOM) Integrated Network Processing Unit (IPU-2T4-A)
               virent8090DEVCR8DIPU1T2MA(165912),   -- V8R24C00 for CR8DIPU1T2MA(SBOM) Integrated Network Processing Unit (IPU-1T2-AU)
               virent8090DEVCR8DIPU2T4M2(165913),   -- V8R24C00 for CR8DIPU2T4M2(SBOM) Integrated Network Processing Unit (IPU-2T4-E-B)
               virent8090DEVCR8DIPU1T2MB(165914),   -- V8R24C00 for CR8DIPU1T2MB(SBOM) Integrated Network Processing Unit (IPU-1T2-E-BU)
               virent8090DEVTNRDIPU2T4M1(165915),   -- V8R24C00 for TNRDIPU2T4M1(SBOM) Integrated Network Processing Unit (IPU-2T4-A)
               virent8090DEVTNRDIPU1T2M1(165916),   -- V8R24C00 for TNRDIPU1T2M1(SBOM) Integrated Network Processing Unit (IPU-1T2-AU)
               virent8090DEVTNRDIPU2T4M2(165917),   -- V8R24C00 for TNRDIPU2T4M2(SBOM) Integrated Network Processing Unit (IPU-2T4-E-B)
               virent8090DEVTNRDIPU1T2M2(165918),   -- V8R24C00 for TNRDIPU1T2M2(SBOM) Integrated Network Processing Unit (IPU-1T2-E-BU)
               virent8090DEVANPM001AICT5(215891),   -- V8R24C00 for ANPM001AICT5(SBOM) Customer Premise Equipment,ATN 905-L System,AC,4*GE/FE(o),4*GE/FE(e)
               virent8090DEVCP8PHST10A13(215892),   -- V8R24C00 for CP8PHST10A13(SBOM) Customer Premise Equipment,NetEngine A816 AC System (4*GE/FE(o)+4*GE/FE(e), includes advanced features and auxiliary materials)
               virent8090DEVCP8PHST2EA53(215893),   -- V8R24C00 for CP8PHST2EA53(SBOM) NetEngine A816 E Basic Configuration(Includes A816 E Chassis(A),Fixed Interface, 4*GE/FE (o),4*GE/FE (e), no software or doc, with auxiliary materials)
               virent8090DEVCP8PHST2EA54(215894),   -- V8R24C00 for CP8PHST2EA54(SBOM) NetEngine A816 E Basic Configuration(Includes A816 E Chassis,Fixed Interface,4*GE/FE (o),4*GE/FE (e), no software or doc, with auxiliary materials)
			   virent8090DEVCR8D8SFU9TA0(523683),   -- V8R23C10 for CR8D8SFU9TA0(SBOM) NetEngine 8800 X4 9.6Tbps Switch Fabric Unit(SFUI-9T6-A)
               virent8090DEVCR8D8LPF1TL0(313604),   -- V8R23C10 for CR8D8LPF1TL0(SBOM) Flexible Card Line Processing Unit L(LPUF-1T-L)
               virent8090DEVCR8DELPF1TL0(313612),   -- V8R24C10 for CR8DELPF1TL0(SBOM) Flexible Card Line Processing Unit L(LPUF-1T-L)
               virent8090DEVCR8DELPF1TC0(313613),   -- V8R24C10 for CR8DELPF1TC0(SBOM) Flexible Card Line Processing Unit (LPUF-1T)
               virent8090DEVCR8DELPF1TE0(313614),   -- V8R24C10 for CR8DELPF1TE0(SBOM) Flexible Card Line Processing Unit E(LPUF-1T-E)
               virent8090DEVWDNDNNSRCPA1(313615),   -- V8R25C00 for WDNDNNSRCPA1(SBOM) S-Router Control Process Unit
			   virent8090DEVCR8D0IPU3TM1(834277),   -- V8R23C10 for CR8D0IPU3TM1(SBOM) Integrated Network Processing Unit (IPU-3T6-A)
               virent8090DEVXHMD0IPU3TC1(900004),   -- V8R25C00 for XHMD0IPU3TC1(SBOM) Integrated Network Processing Unit(IPUA-3T6-A)
               virent8090DEVXHMD0IPU3TC2(900005),   -- V8R25C00 for XHMD0IPU3TC2(SBOM) Integrated Network Processing Unit(IPUA-3T6-A)
               virent8090DEVCR8D0IPU3TM2(803803),   -- V8R23C10 for CR8D0IPU3TM2(SBOM) Integrated Network Processing Unit (IPU-3T6-E-B)
               virent8090DEVCR8DUIPU2TM1(803804),   -- V8R23C10 for CR8DUIPU2TM1(SBOM) Integrated Network Processing Unit (IPU-2T-AU)
               virent8090DEVCR8DUIPU2TM2(803805),   -- V8R23C10 for CR8DUIPU2TM2(SBOM) Integrated Network Processing Unit (IPU-2T-E-BU)
               virent8090DEVTNRD0IPU3T91(803806),   -- V8R23C10 for TNRD0IPU3T91(SBOM) Integrated Network Processing Unit (IPU-3T6-A)
               virent8090DEVTNRD0IPU3T92(803807),   -- V8R23C10 for TNRD0IPU3T92(SBOM) Integrated Network Processing Unit (IPU-3T6-E-B)
               virent8090DEVTNRDUIPU2T91(803808),   -- V8R23C10 for TNRDUIPU2T91(SBOM) Integrated Network Processing Unit (IPU-2T-AU)
               virent8090DEVTNRDUIPU2T92(803809),   -- V8R23C10 for TNRDUIPU2T92(SBOM) Integrated Network Processing Unit (IPU-2T-E-BU)
               virent8090DEVCR5D0IPU3TM1(803810),   -- V8R23C10 for CR5D0IPU3TM1(SBOM) Integrated Network Processing Unit (IPU-3T6-A)
               virent8090DEVCR5D0IPU3TM2(803811),   -- V8R23C10 for CR5D0IPU3TM2(SBOM) Integrated Network Processing Unit (IPU-3T6-E-B)
               virent8090DEVCR5DUIPU2TM1(803812),   -- V8R23C10 for CR5DUIPU2TM1(SBOM) Integrated Network Processing Unit (IPU-2T-AU)
               virent8090DEVCR5DUIPU2TM2(803813),   -- V8R23C10 for CR5DUIPU2TM2(SBOM) Integrated Network Processing Unit (IPU-2T-E-BU)
               virent8090DEVCR8D0IPU3TM3(803814),   -- V8R23C10 for CR8D0IPU3TM3(SBOM) Integrated Network Processing Unit (IPUA-3T6-A)
               virent8090DEVCR8DUIPU2TM3(803815),   -- V8R23C10 for CR8DUIPU2TM3(SBOM) Integrated Network Processing Unit (IPUA-2T-AU)
               virent8090DEVCR8D0IPU3TM5(803816),   -- V8R23C10 for CR8D0IPU3TM5(SBOM) Integrated Network Processing Unit (IPUA-3T6-A)
               virent8090DEVCR8DUIPU2TM5(803817),   -- V8R23C10 for CR8DUIPU2TM5(SBOM) Integrated Network Processing Unit (IPUA-2T-AU)
               virent8090DEVCR8DE6LEJKLP(849654),   -- V8R24C00 for CR8DE6LEJKLP(SBOM) 6-Port 800GBase-QSFP-DD + 36-Port 400GBase-QSFP-DD Integrated Line Processing Unit L CM(LPUI-19T2-L-CM,Enable 6*400GE + 36*100GE by default)
               virent8090DEVCR8D8E6LJKLP(462881),   -- V8R24C00 for CR8D8E6LJKLP(SBOM) 6-Port 800GBase-QSFP-DD + 36-Port 400GBase-QSFP-DD Integrated Line Processing Unit L CM(LPUI-19T2-L-CM,Enable 6*400GE + 36*100GE by default)
               virent8090DEVXHEDE6LEJKXS(462882),   -- V8R25C00 for XHEDE6LEJKXS(SBOM) 6-Port 800GBase-QSFP-DD + 36-Port 400GBase-QSFP-DD Integrated Line Processing Unit CM(LPUI-19T2-CM,Enable 36*100GE by default)
               virent8090DEVCR5DVSUIK092(314240),   -- V8R24C00 for CR5DVSUIK092(SBOM) Integrated Service Unit 400(VSUI-400A)
               virent8090DEVCR5DVSUIK094(853637),   -- V8R24C00 for CR5DVSUIK094(SBOM) Integrated Service Unit 400(VSUI-400A-S)
               virent8090DEVME0DVSUIK07H(285785),   -- V8R24C00 for ME0DVSUIK07H(SBOM) Integrated Service Unit 400(VSUI-400D)
               virent8090DEVME0DVSUIK07I(224241),   -- V8R24C00 for ME0DVSUIK07I(SBOM) Integrated Service Unit 400(VSUI-400A)
               virent8090DEVME0DVSUIK07J(434372),   -- V8R24C00 for ME0DVSUIK07J(SBOM) Integrated Service Unit 400(VSUI-400A-S)
               virent8090DEVCR8DSFU19TA0(896523),   -- V8R24C00 for CR8DSFU19TA0(SBOM) NetEngine 8000 X4 19.2Tbps Switch Fabric Unit(SFUI-19T2-A)
               virent8090DEVCR8DSFU19TB0(896524),   -- V8R24C00 for CR8DSFU19TB0(SBOM) NetEngine 8000 X8 19.2Tbps Switch Fabric Unit(SFUI-19T2-B)
               virent8090DEVCR8DSFU14TD0(896525),   -- V8R24C00 for CR8DSFU14TD0(SBOM) NetEngine 8000 X16 14.4Tbps Switch Fabric Unit(SFUI-14T4-D)
               virent8090DEVCR8DSFU14TD0A(896526),   -- V8R24C00 for CR8DSFU14TD0A(SBOM) NetEngine 8000 X16 14.4Tbps Switch Fabric Unit(SFUIA-14T4-D)
               virent8090DEVCR8DSFU19TA0A(896527),   -- V8R24C00 for CR8DSFU19TA0A(SBOM) NetEngine 8000 X4 19.2Tbps Switch Fabric Unit(SFUIA-19T2-A)
               virent8090DEVCR8DSFU19TB0A(896528),   -- V8R24C00 for CR8DSFU19TB0A(SBOM) NetEngine 8000 X8 19.2Tbps Switch Fabric Unit(SFUIA-19T2-B)
               virent8090DEVCR8DSFU09TA0(896529),   -- V8R24C10 for CR8DSFU09TA0(SBOM) NetEngine 8000 X4 9.6Tbps Switch Fabric Unit(SFUI-9T6-A)
               virent8090DEVCR8DSFUI9TB5(896530),   -- V8R24C10 for CR8DSFUI9TB5(SBOM) NetEngine 8000 X4 9.6Tbps Switch Fabric Unit(SFUIA-9T6-A)
               virent8090DEVXHEDSFU19TBA(896531),   -- V8R25C00 for XHEDSFU19TBA(SBOM) NetEngine XH16000E X8 19.2Tbps Switch Fabric Unit(SFUIA-19T2-B)
               virent8090DEVCR5DLPUFF39D(336598),   -- V8R24C00 for CR5DLPUFF39D(SBOM) Integrated Network Processing Unit (LPUF-246-E)
               virent8090DEVCR5DLPUFF39F(336599),   -- V8R24C00 for CR5DLPUFF39F(SBOM) Integrated Network Processing Unit (LPUF-246A-E)
               virent8090DEVCR5DLPUFF39E(336600),   -- V8R24C00 for CR5DLPUFF39E(SBOM) Integrated Network Processing Unit (LPUF-246-E)
               virent8090DEVME0DBSUFM07Q(336601),   -- V8R24C00 for ME0DBSUFM07Q(SBOM) Integrated Network Processing Unit (BSUF-246)
               virent8090DEVME0DBSUFM07R(336602),   -- V8R24C00 for ME0DBSUFM07R(SBOM) Integrated Network Processing Unit (BSUF-246A)
               virent8090DEVME0DBSUFM07P(336603),   -- V8R24C00 for ME0DBSUFM07P(SBOM) Integrated Network Processing Unit (BSUF-246-E)
               virent8090DEVCR8D8MPUA1C1(364070),   -- V8R24C10 for CR8D8MPUA1C1(SBOM) NetEngine XH12000 Main Processing Unit A1A(MPUA1A)
               virent8090DEVCR8D8MPUA2C1(364071),   -- V8R24C10 for CR8D8MPUA2C1(SBOM) NetEngine XH12000 Main Processing Unit A2A(MPUA2A)
               virent8090DEVCR8D0MPUAX6(364080),    -- V8R24C10 for CR8D0MPUAX6(SBOM) NetEngine 8000E Main Processing Unit A1(MPUA1)
               virent8090DEVCR8D0MPUAXCB(364081),   -- V8R24C10 for CR8D0MPUAXCB(SBOM) NetEngine 8000E Main Processing Unit A1B(MPUA1B)
               virent8090DEVCR8D0MPUAXC8(364082),   -- V8R24C10 for CR8D0MPUAXC8(SBOM) NetEngine 8000E Main Processing Unit A2(MPUA2)
               virent8090DEVCR8D0MPUAXC6(364083),   -- V8R24C10 for CR8D0MPUAXC6(SBOM) NetEngine 8000E Main Processing Unit A2B(MPUA2B)
               virent8090DEVCR8D8SFU9TB1(364072),   -- V8R24C10 for CR8D8SFU9TB1(SBOM) NetEngine XH12000 X8 9.6Tbps Switch Fabric Unit(SFUIA-9T6-B)
               virent8090DEVCR8D8LPF6TL1(364073),   -- V8R25C00 for CR8D8LPF6TL1(SBOM) Flexible Card Line Processing Unit L(LPUF-6T4-L)
               virent8090DEVXHXDLPUF2TC0(364090),   -- V8R25C00 for XHXDLPUF2TC0(SBOM) Flexible Card Line Processing Unit(LPUF-2T4A)
               virent8090DEVXHXDLPUF4TC0(364091),   -- V8R24C10 for XHXDLPUF4TC0(SBOM) Flexible Card Line Processing Unit(LPUF-4T8A)
               virent8090DEVCR8DLPUF4TC0(364021),   -- V8R25C10 for CR8DLPUF4TC0(SBOM) Flexible Card Line Processing Unit(LPUF-4T8A)
               virent8090DEVCR8DSFUI4TCB(202519),   -- V8R25C10 for CR8DSFUI4TCB(SBOM) NetEngine 8100 X8 4.8Tbps Switch Fabric Unit(SFUIA-4.8T-C)
               virent8090DEVCR8D8LPF6TE1(364074),   -- V8R24C10 for CR8D8LPF6TE1(SBOM) Flexible Card Line Processing Unit E(LPUF-6T4-E)
               virent8090DEVCR8D8SFU9TC1(364075),   -- V8R24C10 for CR8D8SFU9TC1(SBOM) NetEngine XH12000 X16 9.6Tbps Switch Fabric Unit(SFUIA-9T6-C)
               virent8090DEVCR8DVSUIK0C6(364077),   -- V8R24C10 for CR8DVSUIK0C6(SBOM) Multi-Function Integrated Service Unit 400(MSUI-400-E)
               virent8090DEVCR8DVSUIK0C7(364078),   -- V8R24C10 for CR8DVSUIK0C7(SBOM) Multi-Function Integrated Service Unit 400(MSUI-400A-E)
               virent8090DEVCR8DLPUF3TC3(364076),   -- V8R24C10 for CR8DLPUF3TC3(SBOM) Flexible Card Line Processing Unit(LPUF-3T2)
			   virent8090DEVCR8D0MPUAXC5(364028),   -- V8R24C00 for CR8D0MPUAXC5(SBOM) NetEngine XH16000 Main Processing Unit A10B(MPUA10B)
			   virent8090DEVCR8D0MPUAXC9(364029),	-- V8R24C00 for CR8D0MPUAXC9(SBOM) NetEngine XH16000E Main Processing Unit A10B(MPUA10B)
			   virent8090DEVCR8D6MPUA1C0(679803),   -- V8R25C00 for CR8D6MPUA1C0(SBOM) NetEngine 6000 Main Processing Unit A1(MPUA1)
               virent8090DEVCR8DSFUI9TB2(678752),   -- V8R24C00 for CR8DSFUI9TB2(SBOM) NetEngine XH16000 X8 9.6Tbps Switch Fabric Unit(SFUIA-9T6-B)
			   virent8090DEVCR8DSFUI9TB9(678753),   -- V8R24C00 for CR8DSFUI9TB9(SBOM) NetEngine XH16000E X8 9.6Tbps Switch Fabric Unit(SFUIA-9T6-B)
			   virent8090DEVCR8DLPUFT6TB(165909),   -- V8R24C00 for CR8DLPUFT6TB(SBOM) Flexible Card Line Processing Unit(LPUF-6T4B)
			   virent8090DEVCR8XLPUFT6TA(165910),   -- V8R24C00 for CR8XLPUFT6TA(SBOM) Flexible Card Line Processing Unit(LPUF-6T4A)
			   virent8090DEVCR8DMPUF8AB1(560450),   -- V8R24C10 for CR8DMPUF8AB1(SBOM) NetEngine 8000E F Main Processing Unit B2A(MPUB2A)
			   virent8090DEVCR8DLPUF3TE1(359884),   -- V8R24C10 for CR8DLPUF3TE1(SBOM) Flexible Card Line Processing Unit E(LPUF-3T2-E)
			   virent8090DEVCR8DLPUF3TC1(718758),   -- V8R24C10 for CR8DLPUF3TC1(SBOM) Flexible Card Line Processing Unit(LPUF-3T2)
			   virent8090DEVCR8DLPUF3TC4(718759),   -- V8R24C10 for CR8DLPUF3TC4(SBOM) Flexible Card Line Processing Unit(LPUF-3T2)
               virent8090DEVCR8DLPUF3TL1(673964),   -- V8R24C10 for CR8DLPUF3TL1(SBOM) Flexible Card Line Processing Unit L(LPUF-3T2-L)
               virent8090DEVCR8D8LPU3TE1(743906),   -- V8R24C10 for CR8D8LPU3TE1(SBOM) Flexible Card Line Processing Unit E(LPUF-3T2-E)
               virent8090DEVCR8D8LPU3TC1(113208),   -- V8R24C10 for CR8D8LPU3TC1(SBOM) Flexible Card Line Processing Unit(LPUF-3T2)
               virent8090DEVCR8D8LPF3TL1(678178),   -- V8R24C10 for CR8D8LPF3TL1(SBOM) Flexible Card Line Processing Unit L(LPUF-3T2-L)
               virent8090DEVCR8DLPUF3TM2(516642),   -- V8R24C10 for CR8DLPUF3TM2(SBOM) Flexible Card Line Processing Unit E(LPUF-3T2A-E)
               virent8090DEVCR8DLPUF3TD3(737819),   -- V8R24C10 for CR8DLPUF3TD3(SBOM) Flexible Card Line Processing Unit(LPUF-3T2A)
               virent8090DEVCR8DLPUF3TL2(108614),   -- V8R24C10 for CR8DLPUF3TL2(SBOM) Flexible Card Line Processing Unit L(LPUF-3T2A-L)
               virent8090DEVCR8DLPUF3TE2(953479),   -- V8R24C10 for CR8DLPUF3TE2(SBOM) Flexible Card Line Processing Unit E(LPUF-3T2-E)
               virent8090DEVCR8DLPUF3TC2(400248),   -- V8R24C10 for CR8DLPUF3TC2(SBOM) Flexible Card Line Processing Unit(LPUF-3T2)
               virent8090DEVCR8DLPUF3TF2(584451),   -- V8R24C10 for CR8DLPUF3TF2(SBOM) Flexible Card Line Processing Unit L(LPUF-3T2-L)
			   virent8090DEVCR8D0IPU2TM3(759613),   -- V8R24C10 for CR8D0IPU2TM3(SBOM) Integrated Network Processing Unit (IPUA-2T-E)
               virent8090DEVCR8DIPU1T2M9(993660),   -- V8R24C10 for CR8DIPU1T2M9(SBOM) Integrated Network Processing Unit (IPUA-1T2-E)
               virent8090DEVCR8DIPU1T2ML(263593),   -- V8R24C10 for CR8DIPU1T2ML(SBOM) Integrated Network Processing Unit (IPU-1T2-EN)
               virent8090DEVCR8DIPU1T2MC(219921),   -- V8R24C10 for CR8DIPU1T2MC(SBOM) Integrated Network Processing Unit (IPU-1T2-E)
               virent8090DEVCR8D0IPU2TM4(219999),   -- V8R24C10 for CR8D0IPU2TM4(SBOM) Integrated Network Processing Unit (IPU-2T-E)
               virent8090DEVANND03CXPA01(165928),   -- V8R24C10 for ANND03CXPA01(SBOM) System Control,Cross-connect and Multi-protocol Process Unit with 800G
               virent8090DEVANND03CXPA02(165929),   -- V8R24C10 for ANND03CXPA02(SBOM) System Control,Cross-connect and Multi-protocol Process Unit with 1T6
               virent8090DEVANND03CXPA03(165930),   -- V8R24C10 for ANND03CXPA03(SBOM) System Control,Cross-connect and Multi-protocol Process Unit with 2T4
               virent8090DEVANOD00CXPA00(165931),   -- V8R24C10 for ANOD00CXPA00(SBOM) System Control,Cross-connect and Multi-protocol Process Unit with 2T4
               virent8090DEVANOD00CXPA01(165932),   -- V8R24C10 for ANOD00CXPA01(SBOM) System Control,Cross-connect and Multi-protocol Process Unit with 800G
               virent8090DEVANOD00CXPA02(165926),   -- V8R24C10 for ANOD00CXPA02(SBOM) System Control,Cross-connect and Multi-protocol Process Unit with 1T6
               virent8090DEVANOD00CXPA03(165927),   -- V8R24C10 for ANOD00CXPA03(SBOM) System Control,Cross-connect and Multi-protocol Process Unit with 2T4
               virent8090DEVCR8D0IPU3TM7(803818),   -- V8R24C10 for CR8D0IPU3TM7(SBOM) NetEngine XH16000 M14 Integrated Network Processing Unit (IPU-3T6-A)
               virent8090DEVXHMD0IPU3T6A(210018),    --V8R25C00 for XHMD0IPU3T6A(SBOM) NetEngine XH16000E M14 Integrated Network Processing Unit (IPU-3T6-A)
               virent8090DEVCR8D0IPU3TM9(660086),   -- V8R24C10 for CR8D0IPU3TM9(SBOM) Integrated Network Processing Unit (IPU-3T6-A)
               virent8090DEVCR8DUIPU2TM7(985137),   -- V8R24C10 for CR8DUIPU2TM7(SBOM) Integrated Network Processing Unit (IPU-2T-AU)
               virent8090DEVCR8D0IPU3TM8(213467),   -- V8R24C10 for CR8D0IPU3TM8(SBOM) Integrated Network Processing Unit (IPU-3T6-E-B)
               virent8090DEVCR8DUIPU2TM8(962666),   -- V8R24C10 for CR8DUIPU2TM8(SBOM) Integrated Network Processing Unit (IPU-2T-E-BU)
               virent8090DEVCR8D0SFUT6D3(441887),   -- V8R24C10 for CR8D0SFUT6D3(SBOM) NetEngine 8000E F 6T4 Switch Routing Unit(SRU-6T4-B)
               virent8090DEVCR8DSFUIK0D2(441888),   -- V8R24C10 for CR8DSFUIK0D2(SBOM) NetEngine 8000E F 2T Switch Routing Unit(SRU-2T-A)
               virent8090DEVCR8DMPUF8AF3(441889),   -- V8R24C10 for CR8DMPUF8AF3(SBOM) NetEngine 8000E F Main Processing Unit B2A(MPUB2)
               virent8090DEVCR8B0BKP03D8(230970),   -- V8R24C10 for CR8B0BKP03D8(SBOM) NetEngine 8000E F1A Integrated Chassis Components(Port-side Intake)
               virent8090DEVCR8B0BKP03D9(188350),   -- V8R24C10 for CR8B0BKP03D9(SBOM) NetEngine 8000E F1A Integrated Chassis Components(Port-side Exhaust)
               virent8090DEVCR8B0BKP03DA(964754),   -- V8R24C10 for CR8B0BKP03DA(SBOM) NetEngine 8000E F1A Integrated Chassis Components(Port-side Intake)
               virent8090DEVCR8B0BKP03DB(253627),   -- V8R24C10 for CR8B0BKP03DB(SBOM) NetEngine 8000E F1A Integrated Chassis Components(Port-side Exhaust)
               virent8090DEVCR8B0BKP03E5(884337),   -- V8R24C10 for CR8B0BKP03E5(SBOM) NetEngine 8000E F1A-C Integrated Chassis Components(Port-side Intake)
               virent8090DEVCR8B0BKP03E4(518968),   -- V8R24C10 for CR8B0BKP03E4(SBOM) NetEngine 8000E F1A-C Integrated Chassis Components(Port-side Intake)
               virent8090DEVCR8B0BKP03E6(193036),   -- V8R24C10 for CR8B0BKP03E6(SBOM) NetEngine 8000E F1A-C Integrated Chassis Components(Port-side Intake, excluding Power)
               virent8090DEVCR8D0IPU1T2MS(800026),  -- V8R24C10 for CR8D0IPU1T2MS(SBOM) Integrated Network Processing Unit (IPUA-1T2-E)
               virent8090DEVCR8DIPU480ME(800027),   -- V8R24C10 for CR8DIPU480ME(SBOM) Integrated Network Processing Unit (IPU-480-E)
               virent8090DEVCR8DIPU480MF(800110),   -- V8R25C10 for CR8DIPU480MF(SBOM) Integrated Network Processing Unit (IPUA-480-EN), M8
               virent8090DEVCR8DIPU480MI(800111),   -- V8R25C10 for CR8DIPU480MI(SBOM) Integrated Network Processing Unit (IPU-480-EN), M8
               virent8090DEVCR8D0IPU1T2MR(800028),  -- V8R24C10 for CR8D0IPU1T2MR(SBOM) Integrated Network Processing Unit (IPU-1T2-E)
               virent8090DEVCR8DIPU1T2M7(800029),   -- V8R24C10 for CR8DIPU1T2M7(SBOM) Integrated Network Processing Unit (IPU-1T2-AU)
               virent8090DEVCR8DIPU2T4MC(800030),   -- V8R24C10 for CR8DIPU2T4MC(SBOM) Integrated Network Processing Unit (IPU-2T4-A)
               virent8090DEVCR8DIPU1T2M8(800031),   -- V8R24C10 for CR8DIPU1T2M8(SBOM) Integrated Network Processing Unit (IPU-1T2-E-BU)
               virent8090DEVCR8DIPU2T4MD(800032),   -- V8R24C10 for CR8DIPU2T4MD(SBOM) Integrated Network Processing Unit (IPU-2T4-E-B)
               virent8090DEVANHMHSTA0204(359886),   -- V8R24C10 for ANHMHSTA0204(SBOM) NetEngine XH861, AC Power, Port Capacity 4*100GE/50GE+16*25GE/10GE/GE/FE+8*10GE/GE/FE, all the GE/FE ports is enabled
               virent8090DEVANHMHSTA0104(359887),   -- V8R24C10 for ANHMHSTA0104(SBOM) NetEngine XH861, DC Power, Port Capacity 4*100GE/50GE+16*25GE/10GE/GE/FE+8*10GE/GE/FE, all the GE/FE ports is enabled
               virent8090DEVANHMHSTA0334(359888),   -- V8R24C10 for ANHMHSTA0334(SBOM) NetEngine XH861, AC+DC Power, Port Capacity 4*100GE/50GE+16*25GE/10GE/GE/FE+8*10GE/GE/FE, all the GE/FE ports is enabled
               virent8090DEVXHAPHST3EA00(210006),   -- V8R25C00 for XHAPHST3EA00(SBOM) NetEngine XH861 E, AC Power, Port Capacity 4*100GE/50GE+16*25GE/10GE/GE/FE+8*10GE/GE/FE, all the GE/FE ports is enabled
               virent8090DEVXHAPHST3ED00(210005),   -- V8R25C00 for XHAPHST3ED00(SBOM) NetEngine XH861 E, DC Power, Port Capacity 4*100GE/50GE+16*25GE/10GE/GE/FE+8*10GE/GE/FE, all the GE/FE ports is enabled
               virent8090DEVXHAPHST3AD00(210007),   -- V8R25C00 for XHAPHST3AD00(SBOM) NetEngine XH861 E, AC+DC Power, Port Capacity 4*100GE/50GE+16*25GE/10GE/GE/FE+8*10GE/GE/FE, all the GE/FE ports is enabled
               virent8090DEVCR8PM4BASACD(883662),   -- V8R24C10 for CR8PM4BASACD(SBOM) NetEngine 8000E M4 Integrated AC Chassis Components(Including AC Power,Fan Box)
               virent8090DEVCR8PM4BASACC(468719),   -- V8R24C10 for CR8PM4BASACC(SBOM) NetEngine 8000E M4 Integrated AC Chassis Components(Including AC Power,Fan Box)
               virent8090DEVCR8PM4BASDCC(863701),   -- V8R24C10 for CR8PM4BASDCC(SBOM) NetEngine 8000E M4 Integrated DC Chassis Components(Including DC Power,Fan Box)
               virent8090DEVCR8PM4BASDCD(992877),   -- V8R24C10 for CR8PM4BASDCD(SBOM) NetEngine 8000E M4 Integrated DC Chassis Components(Including DC Power,Fan Box)
               virent8090DEVCR8PF8HALQX2(548780),            -- 24-Port 10GE/GE LAN/WAN-SFP+ MACsec + 48-port GE(100/1000Base-X-SFP) MACsec Combined Line Processing Unit(LPUC-300)
	       virent8090DEVCR8PF8HALQX3(548781),            -- 24-Port 10GE/GE LAN/WAN-SFP+ MACsec + 48-port GE(100/1000Base-X-SFP) MACsec Combined Line Processing Unit(LPUC-300)
               virent8090DEVCR8DE2KB00F0(548782),            -- 2-Port 400GBase-QSFP-DD Combined Line Processing Unit
	       virent8090DEVCR9DE8KE8N8Y(300368),    -- V8R23C10 for CR9DE8KE8N8Y(SBOM) 8-Port 400GE-QSFP-DD + 8-Port 100GE-QSFP28 Integrated Line Process Unit CM(LPUI-4T-CM, 8*100G RTU Enabled by default)
               virent8090DEVIG2D00SPUH01(359885),   -- V8R24C10 for IG2D00SPUH01(SBOM) Flexible Card High Performance Service Processing Unit-SPUH
               virent8090CR5D00ICUC52(567019), -- Cluster Internal Communication Unit C 
               virent8090TPT2CXPA(689210),   -- OptiX PTN 980B,TPT2CXPA,System Control,Cross-connect and Multi-protocol Process Unit
               virent8090CR8DLPUF2TL0(689211),   -- V8R25C00 for CR8DLPUF2TL0(SBOM) Flexible Card Line Processing Unit L(LPUF-2T-L)
               virent8090CR8DLPUF2TL1(689212),   -- V8R25C00 for CR8DLPUF2TL1(SBOM) Flexible Card Line Processing Unit L(LPUF-2TA-L)
               virent8090CR8DLPUF2TB0(689213),   -- V8R25C00 for CR8DLPUF2TB0(SBOM) Flexible Card Line Processing Unit(LPUF-2T)
               virent8090CR8DLPUF2TB1(689214),   -- V8R25C00 for CR8DLPUF2TB1(SBOM) Flexible Card Line Processing Unit(LPUF-2TA)
               virent8090DEVIG2D00SPUH02(359889),   -- V8R24C10 for IG2D00SPUH02(SBOM) Flexible Card High Performance Enhanced Service Processing Unit-SPUHE
               virent8090DEVCR8DGSUPA0C3(679808),  -- V8R25C10 for CR8DGSUPA0C3(SBOM) Multi-function Integrated Service Card(VSUPA-100)
               virent8090DEVCR8DGSUPA0C2(679809),  -- V8R25C10 for CR8DGSUPA0C2(SBOM) Multi-function Integrated Service Card(VSUP-100)
               virent8090DEVCR8DIPU800MA(203628),  -- V8R25C10 for CR8DIPU800MA(SBOM) Integrated Network Processing Unit (IPUA-800-EN)
               virent8090DEVCR8DIPU800MB(203629),  -- V8R25C10 for CR8DIPU800MB(SBOM) Integrated Network Processing Unit (IPU-800-EN)
			   virent8090DEVCR8D0MPU08WD(679810),  -- V8R25C10 for CR8D0MPU08WD(SBOM) NetEngine 8000E Main Processing Unit A1B-D(MPUA1B-D)
               virent8090DEVCR8D0MPU16WD(679811),  -- V8R25C10 for CR8D0MPU16WD(SBOM) NetEngine 8000E Main Processing Unit A2B-D(MPUA2B-D)
               virent8090DEVCR8D00EKWDD0(679812),  -- V8R25C10 for CR8D00EKWDD0(SBOM) Integrated Line Processing Unit(LPUI-4TA-D)
               virent8090DEVCR8DEANEWDD0(679813),  -- V8R25C10 for CR8DEANEWDD0(SBOM) 10-Port 100GBase-QSFP28 + 36-Port 25GE(SFP28)/10GE(SFP+)/GE(SFP) Integrated Line Processing Unit(LPUI-2TA-E-D)
               virent8090DEVCR8DVSUIWAE0(679814),  -- V8R25C10 for CR8DVSUIWAE0(SBOM) Dedicated Service Unit 400(VSUI-400A-E-D)
               virent8090DEVCR8DVSUFAWD0(679824),  -- V8R25C10 for CR8DVSUFAWD0(SBOM) Flexible Card Versatile Service Unit(VSUF-800A-D)
               virent8090DEVCR8DVSUFWAE0(679834),  -- V8R25C10 for CR8DVSUFWAE0(SBOM) Flexible Card Versatile Service Unit(VSUF-800A-G)
               virent8090DEVCR5DVSUIB070(696523),   -- V8R25C00 for CR5DVSUIB070(SBOM) Enhanced SA Service Unit 400(VSUI-400B-E)
               virent8090DEVCR8D00EKNBDP(679815),  -- V8R25C10 for CR8D00EKNBDP(SBOM) 40-Port 100GBase-QSFP28 Integrated Line Processing Unit(LPUI-4TA-E-D)
               virent8090DEVCR8DE8KE8NC5(109609),  -- V8R25C10 for CR8DE8KE8NC5(SBOM) 8-Port 400GBase-QSFP-DD + 8-Port 100GBase-QSFP28 Integrated Line Processing Unit CM(LPUI-4T-CM,Enable 16*100GE by default)
               virent8090DEVCR8DE8KE8EC5(514838),  -- V8R25C10 for CR8DE8KE8EC5(SBOM) 8-Port 400GBase-QSFP-DD + 8-Port 100GBase-QSFP28 Integrated Line Processing Unit E CM(LPUI-4T-E-CM,Enable 16*100GE by default)
               virent8090DEVCR8DE8KE8LC5(463239),  -- V8R25C10 for CR8DE8KE8LC5(SBOM) 8-Port 400GBase-QSFP-DD + 8-Port 100GBase-QSFP28 Integrated Line Processing Unit L CM(LPUI-4T-L-CM,Enable 16*100GE by default)
               virent8090DEVXHEDMSUF80C1(210036),    -- V8R25C10 for XHEDMSUF80C1(SBOM) Flexible Card Multi-Function Service Unit 800(MSUF-800A)
               virent8090DEVANPM001AICQ0(215896),   -- V8R25C10 for ANPM001AICQ0(SBOM) ATN 905-L System,AC,4*GE/FE(o),4*GE/FE(e)
               virent8090DEVCR8DIPU480Q0(800112),   -- V8R25C10 for CR8DIPU480Q0(SBOM) Integrated Network Processing Unit (IPUA-480), M8
               virent8090DEVCR8DVSUPA0Q0(679816)    -- V8R25C10 for CR8DVSUPA0Q0(SBOM) Integrated Service Card 100(VSUP-100A)
            }

        HWAdditionalEntityType ::= TEXTUAL-CONVENTION
            STATUS current
            DESCRIPTION
                "To show the relevant additional entity type in vender type object.
                "
            SYNTAX INTEGER
                {
                other(1),                      -- none of the following
-- MA5200:
                addentnameMA5200TCAM(135168),       -- TCAM  Module
                addentnameMA5200CPCD(135169),       -- CPCD  Module
-- 8090:
                addentname8090DEVFAD(561152),       -- FAD  Module
                addentname8090DEVTCAM(561153),      -- TCAM Module
                addentname8090DEVCLK(561154),       -- Clock Board
                addentname8090DEVMIF(561155),        -- MIF Module
                addentname8090DEVCR52CLKB(561156),  -- 1588 v2 Clock Board

-- ME60:
                addentnameME60DEVFAD(159744),       -- FAD  Module
                addentnameME60DEVTCAM(159745),      -- TCAM Module
                addentnameME60DEVCLK(159746),       -- Clock Board
                addentnameME60DEVMIF(159747),        -- MIF Module

-- CloudEngine: 0x000A8000~0x000A8fff(688128~692223)
                addentnameCMU(688128),               -- CMU  Module
                addentnamePDU(688129),               -- PDU  Module
                addentnameDMU(688130),               -- DMU  Module
                addentnameDACS(688131),               -- DACS  Module
                addentnamePM(688390)                 -- PM  Module
                }

        hwAlarmId OBJECT-TYPE
            SYNTAX Integer32
            MAX-ACCESS accessible-for-notify
            STATUS current
            DESCRIPTION
                "The trap id only valids in the alarm trap Varible binding parameters .
                 "
            ::= { huaweiTCMIB 1 }

        hwAlarmTime OBJECT-TYPE
            SYNTAX DateAndTime
            MAX-ACCESS accessible-for-notify
            STATUS current
            DESCRIPTION
                "The trap  time  only valids in the alarm trap Varible binding parameters .
                 "
            ::= { huaweiTCMIB 2 }

        hwAlarmSn OBJECT-TYPE
            SYNTAX Integer32
            MAX-ACCESS accessible-for-notify
            STATUS current
            DESCRIPTION
                "The serial number  only valids in the alarm trap Varible binding parameters .
                 "
            ::= { huaweiTCMIB 3 }

        hwCauseId OBJECT-TYPE
            SYNTAX Integer32
            MAX-ACCESS accessible-for-notify
            STATUS current
            DESCRIPTION
                "The cause for   sending  a trap .
                 "
            ::= { huaweiTCMIB 4 }

        hwTrapType OBJECT-TYPE
            SYNTAX INTEGER
            {
            eventAlarm(0),                  -- Event alarm
            faultAlarm(1),                  -- Fault alarm
            clearAlarm(2),                  -- Recovery alarm
            synAlarm(3),                    -- Synchronization alarm
            maitainTrap(10),                -- Maintenance trap
            topDiscovery(11),               -- Topology discovery trap
            debugTrap(12)                   -- Debugging trap
            }

            MAX-ACCESS accessible-for-notify
            STATUS current
            DESCRIPTION
                "The trap type .
                Options:
                1.eventAlarm(0)                 - Event alarm
                2.faultAlarm(1)                 - Fault alarm
                3.clearAlarm(2)                 - Recovery alarm
                4.synAlarm(3)                   - Synchronization alarm
                5.maitainTrap(10)               - Maintenance trap
                6.topDiscovery(11)              - Topology discovery trap
                7.debugTrap(12)                 - Debugging trap
                "
            ::= { huaweiTCMIB 5 }

        hwFrameTypeOid OBJECT-TYPE
            SYNTAX HWFrameType
            MAX-ACCESS read-only
            STATUS current
            DESCRIPTION
                "the Frames definition only for Entity-Mib use"
            ::= { huaweiTCMIB 11 }

        hwSlotTypeOid OBJECT-TYPE
            SYNTAX HWPCBType
            MAX-ACCESS read-only
            STATUS current
            DESCRIPTION
                "the slots definition only for Entity-Mib use"
            ::= { huaweiTCMIB 12}

        hwSubslotTypeOid OBJECT-TYPE
            SYNTAX HWSubPCBType
            MAX-ACCESS read-only
            STATUS current
            DESCRIPTION
                "the sub slots  definition only for Entity-Mib use"
            ::= { huaweiTCMIB 13}

        hwPortTypeOid    OBJECT-TYPE
            SYNTAX HWPortType
            MAX-ACCESS read-only
            STATUS current
            DESCRIPTION
                "the ports definition only for Entity-Mib use"
            ::= { huaweiTCMIB 14}
        hwVirtualEntityOid    OBJECT-TYPE
            SYNTAX HWVirtualEntityType
            MAX-ACCESS read-only
            STATUS current
            DESCRIPTION
                "The virtual entity definition only for Entity-mib."
            ::= { huaweiTCMIB 15}

        hwAdditionalEntityOid    OBJECT-TYPE
            SYNTAX HWAdditionalEntityType
            MAX-ACCESS read-only
            STATUS current
            DESCRIPTION
                "The additional entity definition only for Entity-mib."
            ::= { huaweiTCMIB 16}

    END
